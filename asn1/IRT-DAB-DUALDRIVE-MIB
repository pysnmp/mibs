--
-- IRT-DAB-DUALDRIVE-MIB.my
-- MIB generated by MG-SOFT Visual MIB Builder Version 6.0  Build 88
-- Friday, May 04, 2007 at 18:24:42
--

	IRT-DAB-DUALDRIVE-MIB DEFINITIONS ::= BEGIN
 
		IMPORTS
			eventTimeStamp, eventPriority, eventCounter, mibRelease			
				FROM IRT-COMMONVARBINDS-MIB			
			dab, Input1Input2, SelectManualAuto, SelectOnOff, PresentNotPresent, 
			FaultOK, WarningOK, LocalRemote, ReadyNotReady, OkNotOk, 
			MuteOk, ExecutedNotExecuted			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DateAndTime, DisplayString, TruthValue			
				FROM SNMPv2-TC;
	
	
		-- 1.3.6.1.4.1.19831.1.1.2.4
		dabDualDrive MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events               OBJECT IDENTIFIER ::= { dabDualDrive 0 }
				dabDDGeneral         OBJECT IDENTIFIER ::= { dabDualDrive 1 }
				dabDDExciterA        OBJECT IDENTIFIER ::= { dabDualDrive 2 }
				dabDDExciterB        OBJECT IDENTIFIER ::= { dabDualDrive 3 }
				dabDDEventEnable     OBJECT IDENTIFIER ::= { dabDualDrive 4 }
				dabDDEventPriority   OBJECT IDENTIFIER ::= { dabDualDrive 5 }
				groups               OBJECT IDENTIFIER ::= { dabDualDrive 6 }
				
				2nd level
				
				dabDDEventEnableGeneral   OBJECT IDENTIFIER ::= { dabDDEventEnable 1 }
				dabDDEventEnableExciterA  OBJECT IDENTIFIER ::= { dabDDEventEnable 2 }
				dabDDEventEnableExciterB  OBJECT IDENTIFIER ::= { dabDDEventEnable 3 }
				
				dabDDEventPriorityGeneral   OBJECT IDENTIFIER ::= { dabDDEventPriority 1 }
				dabDDEventPriorityExciterA  OBJECT IDENTIFIER ::= { dabDDEventPriority 2 }
				dabDDEventPriorityExciterB  OBJECT IDENTIFIER ::= { dabDDEventPriority 3 }
				
				end branch"
			REVISION "200705041400Z"		-- May 04, 2007 at 14:00 GMT
			DESCRIPTION 
				"change SFNMode, LocalMode (description) and Module-COMPLIANCE"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dab 4 }

		
	
	
--
-- Node definitions
--
	
-- dab dual drive events
		-- 1.3.6.1.4.1.19831.1.1.2.4.0
		dabEventsDD OBJECT IDENTIFIER ::= { dabDualDrive 0 }

		
		-- 1.3.6.1.4.1.19831.1.1.2.4.0.1
		dabDDInputPreselectionEvent NOTIFICATION-TYPE
			OBJECTS { sysDescr, sysName, sysLocation, eventTimeStamp, eventPriority, 
				eventCounter, dabDDInputPreselection }
			STATUS current
			DESCRIPTION 
				"Description. dabDDInputPreselection notification"
			::= { dabEventsDD 1 }

		
		-- 1.3.6.1.4.1.19831.1.1.2.4.0.2
		dabDDInputAutomaticEvent NOTIFICATION-TYPE
			OBJECTS { sysDescr, sysName, sysLocation, eventTimeStamp, eventPriority, 
				eventCounter, dabDDInputAutomatic }
			STATUS current
			DESCRIPTION 
				"Description. dabDDInputAutomatic notification"
			::= { dabEventsDD 2 }

		
		-- 1.3.6.1.4.1.19831.1.1.2.4.0.3
		dabDDPreselectionExciterEvent NOTIFICATION-TYPE
			OBJECTS { sysDescr, sysName, sysLocation, eventTimeStamp, eventPriority, 
				eventCounter, dabDDPreselectionExciter }
			STATUS current
			DESCRIPTION 
				"Description. dabDDPreselectionExciterEvent notification"
			::= { dabEventsDD 3 }

		
		-- 1.3.6.1.4.1.19831.1.1.2.4.0.4
		dabDDTransmitterOpModeEvent NOTIFICATION-TYPE
			OBJECTS { sysDescr, sysName, sysLocation, eventTimeStamp, eventPriority, 
				eventCounter, dabDDTransmitterOpMode }
			STATUS current
			DESCRIPTION 
				"Description. dabDDTransmitterOpMode notification"
			::= { dabEventsDD 4 }

		
		-- 1.3.6.1.4.1.19831.1.1.2.4.0.5
		dabDDReserveControlEvent NOTIFICATION-TYPE
			OBJECTS { sysDescr, sysName, sysLocation, eventTimeStamp, eventPriority, 
				eventCounter, dabDDReserveControl }
			STATUS current
			DESCRIPTION 
				"Description. dabDDReserveControl nitification"
			::= { dabEventsDD 5 }

		
		-- 1.3.6.1.4.1.19831.1.1.2.4.0.6
		dabDDRFPresentEvent NOTIFICATION-TYPE
			OBJECTS { sysDescr, sysName, sysLocation, eventTimeStamp, eventPriority, 
				eventCounter, dabDDRFPresent }
			STATUS current
			DESCRIPTION 
				"Description. dabDDRFPresent notification"
			::= { dabEventsDD 6 }

		
		-- 1.3.6.1.4.1.19831.1.1.2.4.0.7
		dabDDResetFaultEvent NOTIFICATION-TYPE
			OBJECTS { sysDescr, sysName, sysLocation, eventTimeStamp, eventPriority, 
				eventCounter, dabDDResetFault }
			STATUS obsolete
			DESCRIPTION 
				"Notification is inactive!
				
				Description. dabDDResetFault notification"
			::= { dabEventsDD 7 }

		
		-- 1.3.6.1.4.1.19831.1.1.2.4.0.8
		dabDDAmplifierFaultEvent NOTIFICATION-TYPE
			OBJECTS { sysDescr, sysName, sysLocation, eventTimeStamp, eventPriority, 
				eventCounter, dabDDAmplifierFault }
			STATUS current
			DESCRIPTION 
				"Description. dabDDAmplifierFault notification"
			::= { dabEventsDD 8 }

		
		-- 1.3.6.1.4.1.19831.1.1.2.4.0.9
		dabDDAmplifierWarningEvent NOTIFICATION-TYPE
			OBJECTS { sysDescr, sysName, sysLocation, eventTimeStamp, eventPriority, 
				eventCounter, dabDDAmplifierWarning }
			STATUS current
			DESCRIPTION 
				"Description. dabDDAmplifierWarning notification"
			::= { dabEventsDD 9 }

		
		-- 1.3.6.1.4.1.19831.1.1.2.4.0.10
		dabDDActiveExciterEvent NOTIFICATION-TYPE
			OBJECTS { sysDescr, sysName, sysLocation, eventTimeStamp, eventPriority, 
				eventCounter, dabDDActiveExciter }
			STATUS current
			DESCRIPTION 
				"Description. dabDDActiveExciter notification"
			::= { dabEventsDD 10 }

		
		-- 1.3.6.1.4.1.19831.1.1.2.4.0.11
		dabDDLocalModeEvent NOTIFICATION-TYPE
			OBJECTS { sysDescr, sysName, sysLocation, eventTimeStamp, eventPriority, 
				eventCounter, dabDDLocalMode }
			STATUS current
			DESCRIPTION 
				"Description. dabDDLocalMode notification"
			::= { dabEventsDD 11 }

		
		-- 1.3.6.1.4.1.19831.1.1.2.4.0.12
		dabDDControlUnitFaultEvent NOTIFICATION-TYPE
			OBJECTS { sysDescr, sysName, sysLocation, eventTimeStamp, eventPriority, 
				eventCounter, dabDDControlUnitFault }
			STATUS current
			DESCRIPTION 
				"Description. dabDDControlUnitFault notification"
			::= { dabEventsDD 12 }

		
		-- 1.3.6.1.4.1.19831.1.1.2.4.0.13
		dabDDSwitchOverModeEvent NOTIFICATION-TYPE
			OBJECTS { sysDescr, sysName, sysLocation, eventTimeStamp, eventPriority, 
				eventCounter, dabDDSwitchOverMode }
			STATUS current
			DESCRIPTION 
				"Description. dabDDSwitchOverMode notification"
			::= { dabEventsDD 13 }

		
		-- 1.3.6.1.4.1.19831.1.1.2.4.0.14
		dabDDSwitchOverReadyEvent NOTIFICATION-TYPE
			OBJECTS { sysDescr, sysName, sysLocation, eventTimeStamp, eventPriority, 
				eventCounter, dabDDSwitchOverReady }
			STATUS current
			DESCRIPTION 
				"Description. dabDDSwitchOverReady notification"
			::= { dabEventsDD 14 }

		
		-- 1.3.6.1.4.1.19831.1.1.2.4.0.15
		dabDDSwitchOverExecutedEvent NOTIFICATION-TYPE
			OBJECTS { sysDescr, sysName, sysLocation, eventTimeStamp, eventPriority, 
				eventCounter, dabDDSwitchOverExecuted }
			STATUS current
			DESCRIPTION 
				"Description. dabDDSwitchOverExecuted notification"
			::= { dabEventsDD 15 }

		
		-- 1.3.6.1.4.1.19831.1.1.2.4.0.16
		dabDDSwitchOverFaultEvent NOTIFICATION-TYPE
			OBJECTS { sysDescr, sysName, sysLocation, eventTimeStamp, eventPriority, 
				eventCounter, dabDDSwitchOverFault }
			STATUS current
			DESCRIPTION 
				"Description. dabDDSwitchOverFault notification"
			::= { dabEventsDD 16 }

		
		-- 1.3.6.1.4.1.19831.1.1.2.4.0.17
		dabDDExciterAInput1OKEvent NOTIFICATION-TYPE
			OBJECTS { sysDescr, sysName, sysLocation, eventTimeStamp, eventPriority, 
				eventCounter, dabDDExciterAInput1OK }
			STATUS current
			DESCRIPTION 
				"Description. dabDDExciterAInput1OK notification"
			::= { dabEventsDD 17 }

		
		-- 1.3.6.1.4.1.19831.1.1.2.4.0.18
		dabDDExciterAInput2OKEvent NOTIFICATION-TYPE
			OBJECTS { sysDescr, sysName, sysLocation, eventTimeStamp, eventPriority, 
				eventCounter, dabDDExciterAInput2OK }
			STATUS current
			DESCRIPTION 
				"Description. dabDDExciterAInput2OK notification"
			::= { dabEventsDD 18 }

		
		-- 1.3.6.1.4.1.19831.1.1.2.4.0.19
		dabDDExciterALocalModeEvent NOTIFICATION-TYPE
			OBJECTS { sysDescr, sysName, sysLocation, eventTimeStamp, eventPriority, 
				eventCounter, dabDDExciterALocalMode }
			STATUS current
			DESCRIPTION 
				"Description. dabDDExciterALocalMode notification"
			::= { dabEventsDD 19 }

		
		-- 1.3.6.1.4.1.19831.1.1.2.4.0.20
		dabDDExciterAFaultEvent NOTIFICATION-TYPE
			OBJECTS { sysDescr, sysName, sysLocation, eventTimeStamp, eventPriority, 
				eventCounter, dabDDExciterAFault }
			STATUS current
			DESCRIPTION 
				"Description. dabDDExciterAFault notification"
			::= { dabEventsDD 20 }

		
		-- 1.3.6.1.4.1.19831.1.1.2.4.0.21
		dabDDExciterAWarningEvent NOTIFICATION-TYPE
			OBJECTS { sysDescr, sysName, sysLocation, eventTimeStamp, eventPriority, 
				eventCounter, dabDDExciterAWarning }
			STATUS current
			DESCRIPTION 
				"Description. dabDDExciterAWarning notification"
			::= { dabEventsDD 21 }

		
		-- 1.3.6.1.4.1.19831.1.1.2.4.0.22
		dabDDExciterAActiveInputEvent NOTIFICATION-TYPE
			OBJECTS { sysDescr, sysName, sysLocation, eventTimeStamp, eventPriority, 
				eventCounter, dabDDExciterAActiveInput }
			STATUS current
			DESCRIPTION 
				"Description. dabDDExciterAActiveInput notification"
			::= { dabEventsDD 22 }

		
		-- 1.3.6.1.4.1.19831.1.1.2.4.0.23
		dabDDExciterASFNModeEvent NOTIFICATION-TYPE
			OBJECTS { sysDescr, sysName, sysLocation, eventTimeStamp, eventPriority, 
				eventCounter, dabDDExciterASFNMode }
			STATUS current
			DESCRIPTION 
				"Description. dabDDExciterASFNMode notification"
			::= { dabEventsDD 23 }

		
		-- 1.3.6.1.4.1.19831.1.1.2.4.0.24
		dabDDExciterARefFaultEvent NOTIFICATION-TYPE
			OBJECTS { sysDescr, sysName, sysLocation, eventTimeStamp, eventPriority, 
				eventCounter, dabDDExciterARefFault }
			STATUS current
			DESCRIPTION 
				"Description. dabDDExciterARefFault notification"
			::= { dabEventsDD 24 }

		
		-- 1.3.6.1.4.1.19831.1.1.2.4.0.25
		dabDDExciterAMuteEvent NOTIFICATION-TYPE
			OBJECTS { sysDescr, sysName, sysLocation, eventTimeStamp, eventPriority, 
				eventCounter, dabDDExciterAMute }
			STATUS current
			DESCRIPTION 
				"Description. dabDDExciterAMute notification"
			::= { dabEventsDD 25 }

		
		-- 1.3.6.1.4.1.19831.1.1.2.4.0.26
		dabDDExciterAWarningTimeStampEvent NOTIFICATION-TYPE
			OBJECTS { sysDescr, sysName, sysLocation, eventTimeStamp, eventPriority, 
				eventCounter, dabDDExciterAWarningTimeStamp }
			STATUS current
			DESCRIPTION 
				"Description. dabDDExciterAWarningTimeStamp notification"
			::= { dabEventsDD 26 }

		
		-- 1.3.6.1.4.1.19831.1.1.2.4.0.27
		dabDDExciterBInput1OKEvent NOTIFICATION-TYPE
			OBJECTS { sysDescr, sysName, sysLocation, eventTimeStamp, eventPriority, 
				eventCounter, dabDDExciterBInput1OK }
			STATUS current
			DESCRIPTION 
				"Description. dabDDExciterBInput1OK notification"
			::= { dabEventsDD 27 }

		
		-- 1.3.6.1.4.1.19831.1.1.2.4.0.28
		dabDDExciterBInput2OKEvent NOTIFICATION-TYPE
			OBJECTS { sysDescr, sysName, sysLocation, eventTimeStamp, eventPriority, 
				eventCounter, dabDDExciterBInput2OK }
			STATUS current
			DESCRIPTION 
				"Description. dabDDExciterBInput2OK notification"
			::= { dabEventsDD 28 }

		
		-- 1.3.6.1.4.1.19831.1.1.2.4.0.29
		dabDDExciterBLocalModeEvent NOTIFICATION-TYPE
			OBJECTS { sysDescr, sysName, sysLocation, eventTimeStamp, eventPriority, 
				eventCounter, dabDDExciterBLocalMode }
			STATUS current
			DESCRIPTION 
				"Description. dabDDExciterBLocalMode notification"
			::= { dabEventsDD 29 }

		
		-- 1.3.6.1.4.1.19831.1.1.2.4.0.30
		dabDDExciterBFaultEvent NOTIFICATION-TYPE
			OBJECTS { sysDescr, sysName, sysLocation, eventTimeStamp, eventPriority, 
				eventCounter, dabDDExciterBFault }
			STATUS current
			DESCRIPTION 
				"Description. dabDDExciterBFault notification"
			::= { dabEventsDD 30 }

		
		-- 1.3.6.1.4.1.19831.1.1.2.4.0.31
		dabDDExciterBWarningEvent NOTIFICATION-TYPE
			OBJECTS { sysDescr, sysName, sysLocation, eventTimeStamp, eventPriority, 
				eventCounter, dabDDExciterBWarning }
			STATUS current
			DESCRIPTION 
				"Description. dabDDExciterBWarning notification"
			::= { dabEventsDD 31 }

		
		-- 1.3.6.1.4.1.19831.1.1.2.4.0.32
		dabDDExciterBActiveInputEvent NOTIFICATION-TYPE
			OBJECTS { sysDescr, sysName, sysLocation, eventTimeStamp, eventPriority, 
				eventCounter, dabDDExciterBWarning }
			STATUS current
			DESCRIPTION 
				"Description. dabDDExciterBActiveInput notification"
			::= { dabEventsDD 32 }

		
		-- 1.3.6.1.4.1.19831.1.1.2.4.0.33
		dabDDExciterBSFNModeEvent NOTIFICATION-TYPE
			OBJECTS { sysDescr, sysName, sysLocation, eventTimeStamp, eventPriority, 
				eventCounter, dabDDExciterBSFNMode }
			STATUS current
			DESCRIPTION 
				"Description. dabDDExciterBSFNMode notification"
			::= { dabEventsDD 33 }

		
		-- 1.3.6.1.4.1.19831.1.1.2.4.0.34
		dabDDExciterBRefFaultEvent NOTIFICATION-TYPE
			OBJECTS { sysDescr, sysName, sysLocation, eventTimeStamp, eventPriority, 
				eventCounter, dabDDExciterBRefFault }
			STATUS current
			DESCRIPTION 
				"Description. dabDDExciterBRefFault notification"
			::= { dabEventsDD 34 }

		
		-- 1.3.6.1.4.1.19831.1.1.2.4.0.35
		dabDDExciterBMuteEvent NOTIFICATION-TYPE
			OBJECTS { sysDescr, sysName, sysLocation, eventTimeStamp, eventPriority, 
				eventCounter, dabDDExciterBMute }
			STATUS current
			DESCRIPTION 
				"Description. dabDDExciterBMute notification"
			::= { dabEventsDD 35 }

		
		-- 1.3.6.1.4.1.19831.1.1.2.4.0.36
		dabDDExciterBWarningTimeStampEvent NOTIFICATION-TYPE
			OBJECTS { sysDescr, sysName, sysLocation, eventTimeStamp, eventPriority, 
				eventCounter, dabDDExciterBWarningTimeStamp }
			STATUS current
			DESCRIPTION 
				"Description. dbDDExciterBWarningTimeStamp notification"
			::= { dabEventsDD 36 }

		
-- dab dual drive General
		-- 1.3.6.1.4.1.19831.1.1.2.4.1
		dabDDGeneral OBJECT IDENTIFIER ::= { dabDualDrive 1 }

		
		-- 1.3.6.1.4.1.19831.1.1.2.4.1.1
		dabDDInputPreselection OBJECT-TYPE
			SYNTAX Input1Input2
			MAX-ACCESS read-write
			STATUS current
			DESCRIPTION
				"Dual drive. Preselection input 
				
				(0) undefined
				(1) Input 1
				(2) Input 2"
			::= { dabDDGeneral 1 }

		
		-- 1.3.6.1.4.1.19831.1.1.2.4.1.2
		dabDDInputAutomatic OBJECT-TYPE
			SYNTAX SelectManualAuto
			MAX-ACCESS read-write
			STATUS current
			DESCRIPTION
				"Dual drive. Input selection mode: manual or automatic
				
				(0) undefined
				(1) manual 
				(2) automatic"
			::= { dabDDGeneral 2 }

		
		-- 1.3.6.1.4.1.19831.1.1.2.4.1.3
		dabDDPreselectionExciter OBJECT-TYPE
			SYNTAX INTEGER
				{
				undefined(0),
				exciterA(1),
				exciterB(2)
				}
			MAX-ACCESS read-write
			STATUS current
			DESCRIPTION
				"Dual drive. Preselection of the exciter 
				
				"
			::= { dabDDGeneral 3 }

		
		-- 1.3.6.1.4.1.19831.1.1.2.4.1.4
		dabDDTransmitterOpMode OBJECT-TYPE
			SYNTAX SelectOnOff
			MAX-ACCESS read-write
			STATUS current
			DESCRIPTION
				"Dual drive. Operation mode of main exciter 
				
				(0) undefined
				(1) ON
				(2) OFF"
			::= { dabDDGeneral 4 }

		
		-- 1.3.6.1.4.1.19831.1.1.2.4.1.5
		dabDDReserveControl OBJECT-TYPE
			SYNTAX SelectOnOff
			MAX-ACCESS read-write
			STATUS current
			DESCRIPTION
				"Dual drive. Operation mode of reserve exciter
				
				(0) undefined
				(1) ON 
				(2) OFF "
			::= { dabDDGeneral 5 }

		
		-- 1.3.6.1.4.1.19831.1.1.2.4.1.6
		dabDDRFPresent OBJECT-TYPE
			SYNTAX PresentNotPresent
			MAX-ACCESS read-only
			STATUS current
			DESCRIPTION
				"Dual drive. Output power is present
				
				(0) undefined
				(1) present
				(2) not present
				"
			::= { dabDDGeneral 6 }

		
		-- 1.3.6.1.4.1.19831.1.1.2.4.1.7
		dabDDResetFault OBJECT-TYPE
			SYNTAX Unsigned32
			MAX-ACCESS read-write
			STATUS obsolete
			DESCRIPTION
				"Massage is inactive!
				
				Dual drive. Reset fault: Clear fault of the whole reserve system
				
				<1>
				
				(1) reset sum fault
				"
			::= { dabDDGeneral 7 }

		
		-- 1.3.6.1.4.1.19831.1.1.2.4.1.8
		dabDDAmplifierFault OBJECT-TYPE
			SYNTAX FaultOK
			MAX-ACCESS read-only
			STATUS current
			DESCRIPTION
				"Dual drive. Fault state of amplifier 
				
				(0) undefined
				(1) fault
				(2) ok"
			::= { dabDDGeneral 8 }

		
		-- 1.3.6.1.4.1.19831.1.1.2.4.1.9
		dabDDAmplifierWarning OBJECT-TYPE
			SYNTAX WarningOK
			MAX-ACCESS read-only
			STATUS current
			DESCRIPTION
				"Dual drive. Warning state of amplifier 
				
				(0) undefined
				(1) warning
				(2) ok"
			::= { dabDDGeneral 9 }

		
		-- 1.3.6.1.4.1.19831.1.1.2.4.1.10
		dabDDActiveExciter OBJECT-TYPE
			SYNTAX INTEGER
				{
				undefined(0),
				exciterA(1),
				exciterB(2)
				}
			MAX-ACCESS read-only
			STATUS current
			DESCRIPTION
				"Dual drive. Active exciter 
				
				"
			::= { dabDDGeneral 10 }

		
		-- 1.3.6.1.4.1.19831.1.1.2.4.1.11
		dabDDLocalMode OBJECT-TYPE
			SYNTAX LocalRemote
			MAX-ACCESS read-only
			STATUS current
			DESCRIPTION
				"Dual drive. Local mode
				
				(0) undefined
				(1) local
				(2) remote"
			::= { dabDDGeneral 11 }

		
		-- 1.3.6.1.4.1.19831.1.1.2.4.1.12
		dabDDControlUnitFault OBJECT-TYPE
			SYNTAX FaultOK
			MAX-ACCESS read-only
			STATUS current
			DESCRIPTION
				"Dual drive. State of the control unit
				
				(0) undefined
				(1) fault
				(2) ok"
			::= { dabDDGeneral 12 }

		
		-- 1.3.6.1.4.1.19831.1.1.2.4.1.13
		dabDDSwitchOverMode OBJECT-TYPE
			SYNTAX SelectManualAuto
			MAX-ACCESS read-write
			STATUS current
			DESCRIPTION
				"Dual drive. Switch over mode: manual or automatic
				
				(0) undefined
				(1) manual 
				(2) automatic"
			::= { dabDDGeneral 13 }

		
		-- 1.3.6.1.4.1.19831.1.1.2.4.1.14
		dabDDSwitchOverReady OBJECT-TYPE
			SYNTAX ReadyNotReady
			MAX-ACCESS read-only
			STATUS current
			DESCRIPTION
				"Dual drive. State of the dual drive switch over unit
				
				(0) undefined
				(1) ready
				(2) not ready"
			::= { dabDDGeneral 14 }

		
		-- 1.3.6.1.4.1.19831.1.1.2.4.1.15
		dabDDSwitchOverExecuted OBJECT-TYPE
			SYNTAX ExecutedNotExecuted
			MAX-ACCESS read-only
			STATUS current
			DESCRIPTION
				"Dual drive. Showsif the reserve switch over unit it has executed
				
				(0) undefined
				(1) executed
				(2) not executed"
			::= { dabDDGeneral 15 }

		
		-- 1.3.6.1.4.1.19831.1.1.2.4.1.16
		dabDDSwitchOverFault OBJECT-TYPE
			SYNTAX FaultOK
			MAX-ACCESS read-only
			STATUS current
			DESCRIPTION
				"Dual drive. fault state of the switsch over unit
				
				(0) undefined
				(1) faulty
				(2) ok"
			::= { dabDDGeneral 16 }

		
-- dab dual drive. exiter A
		-- 1.3.6.1.4.1.19831.1.1.2.4.2
		dabDDExciterA OBJECT IDENTIFIER ::= { dabDualDrive 2 }

		
		-- 1.3.6.1.4.1.19831.1.1.2.4.2.1
		dabDDExciterAInput1OK OBJECT-TYPE
			SYNTAX OkNotOk
			MAX-ACCESS read-only
			STATUS current
			DESCRIPTION
				"Dual drive. Describes if the input signal at the input 1 of exciter A is ok
				
				(0) undefined
				(1) signal ok
				(2) signal is not ok"
			::= { dabDDExciterA 1 }

		
		-- 1.3.6.1.4.1.19831.1.1.2.4.2.2
		dabDDExciterAInput2OK OBJECT-TYPE
			SYNTAX OkNotOk
			MAX-ACCESS read-only
			STATUS current
			DESCRIPTION
				"Dual drive. Describes if the input signal at the input 2 of exciter A is ok
				
				(0) undefined
				(1) signal ok
				(2) signal is not ok"
			::= { dabDDExciterA 2 }

		
		-- 1.3.6.1.4.1.19831.1.1.2.4.2.3
		dabDDExciterALocalMode OBJECT-TYPE
			SYNTAX LocalRemote
			MAX-ACCESS read-only
			STATUS current
			DESCRIPTION
				"Dual drive. Local mode of exciter A
				
				(0) undefined
				(1) local
				(2) remote"
			::= { dabDDExciterA 3 }

		
		-- 1.3.6.1.4.1.19831.1.1.2.4.2.4
		dabDDExciterAFault OBJECT-TYPE
			SYNTAX FaultOK
			MAX-ACCESS read-only
			STATUS current
			DESCRIPTION
				"Dual drive. Fault state of exciter A
				
				(0) undefined
				(1) fault
				(2) ok"
			::= { dabDDExciterA 4 }

		
		-- 1.3.6.1.4.1.19831.1.1.2.4.2.5
		dabDDExciterAWarning OBJECT-TYPE
			SYNTAX WarningOK
			MAX-ACCESS read-only
			STATUS current
			DESCRIPTION
				"Dual drive.Warning state of exciter A 
				
				(0) undefined
				(1) warning
				(2) ok"
			::= { dabDDExciterA 5 }

		
		-- 1.3.6.1.4.1.19831.1.1.2.4.2.6
		dabDDExciterAActiveInput OBJECT-TYPE
			SYNTAX INTEGER
				{
				undefined(0),
				input1(1),
				input2(2),
				seamless(3),
				hmHierarchicalModulation(4)
				}
			MAX-ACCESS read-only
			STATUS current
			DESCRIPTION
				"Dual drive. Active input of the exciter A 
				
				"
			::= { dabDDExciterA 6 }

		
		-- 1.3.6.1.4.1.19831.1.1.2.4.2.7
		dabDDExciterASFNMode OBJECT-TYPE
			SYNTAX TruthValue
			MAX-ACCESS read-only
			STATUS current
			DESCRIPTION
				"Dual drive. SFN mode of exciter A
				
				(0) undefined
				(1) SFN
				(2) MFN"
			::= { dabDDExciterA 7 }

		
		-- 1.3.6.1.4.1.19831.1.1.2.4.2.8
		dabDDExciterARefFault OBJECT-TYPE
			SYNTAX FaultOK
			MAX-ACCESS read-only
			STATUS current
			DESCRIPTION
				"Dual drive. Fault state of the GPS input or the reference frequency of exciter A
				
				(0) undefined
				(1) fault
				(2) ok"
			::= { dabDDExciterA 8 }

		
		-- 1.3.6.1.4.1.19831.1.1.2.4.2.9
		dabDDExciterAMute OBJECT-TYPE
			SYNTAX MuteOk
			MAX-ACCESS read-only
			STATUS current
			DESCRIPTION
				"Dual drive. Mute state of exciter A
				
				(0) undefined
				(1) mute
				(2) ok"
			::= { dabDDExciterA 9 }

		
		-- 1.3.6.1.4.1.19831.1.1.2.4.2.10
		dabDDExciterAWarningTimeStamp OBJECT-TYPE
			SYNTAX WarningOK
			MAX-ACCESS read-only
			STATUS current
			DESCRIPTION
				"Dual drive.Time stamp warning state of exciter A 
				
				(0) undefined
				(1) warning
				(2) ok"
			::= { dabDDExciterA 10 }

		
-- dab dual drive. exiter B
		-- 1.3.6.1.4.1.19831.1.1.2.4.3
		dabDDExciterB OBJECT IDENTIFIER ::= { dabDualDrive 3 }

		
		-- 1.3.6.1.4.1.19831.1.1.2.4.3.1
		dabDDExciterBInput1OK OBJECT-TYPE
			SYNTAX OkNotOk
			MAX-ACCESS read-only
			STATUS current
			DESCRIPTION
				"Dual drive. Describes if the input signal at the input 1 of exciter B is ok
				
				(0) undefined
				(1) signal ok
				(2) signal is not ok"
			::= { dabDDExciterB 1 }

		
		-- 1.3.6.1.4.1.19831.1.1.2.4.3.2
		dabDDExciterBInput2OK OBJECT-TYPE
			SYNTAX OkNotOk
			MAX-ACCESS read-only
			STATUS current
			DESCRIPTION
				"Dual drive. Describes if the input signal at the input 2 of exciter B is ok
				
				(0) undefined
				(1) signal ok
				(2) signal is not ok"
			::= { dabDDExciterB 2 }

		
		-- 1.3.6.1.4.1.19831.1.1.2.4.3.3
		dabDDExciterBLocalMode OBJECT-TYPE
			SYNTAX LocalRemote
			MAX-ACCESS read-only
			STATUS current
			DESCRIPTION
				"Dual drive. Local mode of exciter B
				
				(0) undefined
				(1) local
				(2) remote"
			::= { dabDDExciterB 3 }

		
		-- 1.3.6.1.4.1.19831.1.1.2.4.3.4
		dabDDExciterBFault OBJECT-TYPE
			SYNTAX FaultOK
			MAX-ACCESS read-only
			STATUS current
			DESCRIPTION
				"Dual drive. Fault state of exciter B
				
				(0) undefined
				(1) fault
				(2) ok"
			::= { dabDDExciterB 4 }

		
		-- 1.3.6.1.4.1.19831.1.1.2.4.3.5
		dabDDExciterBWarning OBJECT-TYPE
			SYNTAX WarningOK
			MAX-ACCESS read-only
			STATUS current
			DESCRIPTION
				"Dual drive. Warning state of exciter B 
				
				(0) undefined
				(1) warning
				(2) ok"
			::= { dabDDExciterB 5 }

		
		-- 1.3.6.1.4.1.19831.1.1.2.4.3.6
		dabDDExciterBActiveInput OBJECT-TYPE
			SYNTAX INTEGER
				{
				undefined(0),
				input1(1),
				input2(2),
				seamless(3),
				hmHierarchicalModulation(4)
				}
			MAX-ACCESS read-only
			STATUS current
			DESCRIPTION
				"Dual drive. Active input of the exciter B 
				"
			::= { dabDDExciterB 6 }

		
		-- 1.3.6.1.4.1.19831.1.1.2.4.3.7
		dabDDExciterBSFNMode OBJECT-TYPE
			SYNTAX TruthValue
			MAX-ACCESS read-only
			STATUS current
			DESCRIPTION
				"Dual drive. SFN mode of exciter B
				
				(0) undefined
				(1) SFN
				(2) MFN"
			::= { dabDDExciterB 7 }

		
		-- 1.3.6.1.4.1.19831.1.1.2.4.3.8
		dabDDExciterBRefFault OBJECT-TYPE
			SYNTAX FaultOK
			MAX-ACCESS read-only
			STATUS current
			DESCRIPTION
				"Dual drive. Fault state of the GPS input or the reference frequency of exciter B
				
				(0) undefined
				(1) fault
				(2) ok"
			::= { dabDDExciterB 8 }

		
		-- 1.3.6.1.4.1.19831.1.1.2.4.3.9
		dabDDExciterBMute OBJECT-TYPE
			SYNTAX MuteOk
			MAX-ACCESS read-only
			STATUS current
			DESCRIPTION
				"Dual drive. Mute state of exciter B
				
				(0) undefined
				(1) mute
				(2) ok"
			::= { dabDDExciterB 9 }

		
		-- 1.3.6.1.4.1.19831.1.1.2.4.3.10
		dabDDExciterBWarningTimeStamp OBJECT-TYPE
			SYNTAX WarningOK
			MAX-ACCESS read-only
			STATUS current
			DESCRIPTION
				"Dual drive.Time stamp warning state of exciter B 
				
				(0) undefined
				(1) warning
				(2) ok"
			::= { dabDDExciterB 10 }

		
-- dab dual drive. Switch for event
		-- 1.3.6.1.4.1.19831.1.1.2.4.4
		dabDDEventEnable OBJECT IDENTIFIER ::= { dabDualDrive 4 }

		
		-- 1.3.6.1.4.1.19831.1.1.2.4.4.1
		dabDDEventEnableGeneral OBJECT IDENTIFIER ::= { dabDDEventEnable 1 }

		
		-- 1.3.6.1.4.1.19831.1.1.2.4.4.1.1
		dabDDInputPreselectionEnable OBJECT-TYPE
			SYNTAX TruthValue
			MAX-ACCESS read-write
			STATUS current
			DESCRIPTION
				"Description. Enable/Disable switch for dabDDInputPreselection event"
			::= { dabDDEventEnableGeneral 1 }

		
		-- 1.3.6.1.4.1.19831.1.1.2.4.4.1.2
		dabDDInputAutomaticEnable OBJECT-TYPE
			SYNTAX TruthValue
			MAX-ACCESS read-write
			STATUS current
			DESCRIPTION
				"Description. Enable/Disable switch for dabDDInputAutomatic event"
			::= { dabDDEventEnableGeneral 2 }

		
		-- 1.3.6.1.4.1.19831.1.1.2.4.4.1.3
		dabDDPreselectionExciterEnable OBJECT-TYPE
			SYNTAX TruthValue
			MAX-ACCESS read-write
			STATUS current
			DESCRIPTION
				"Description. Enable/Disable switch for dabDDPreselectionExciter event"
			::= { dabDDEventEnableGeneral 3 }

		
		-- 1.3.6.1.4.1.19831.1.1.2.4.4.1.4
		dabDDTransmitterOpModeEnable OBJECT-TYPE
			SYNTAX TruthValue
			MAX-ACCESS read-write
			STATUS current
			DESCRIPTION
				"Description. Enable/Disable switch for dabDDTransmitterOpMode event"
			::= { dabDDEventEnableGeneral 4 }

		
		-- 1.3.6.1.4.1.19831.1.1.2.4.4.1.5
		dabDDReserveControlEnable OBJECT-TYPE
			SYNTAX TruthValue
			MAX-ACCESS read-write
			STATUS current
			DESCRIPTION
				"Description. Enable/Disable switch for dabDDIReserveControl event"
			::= { dabDDEventEnableGeneral 5 }

		
		-- 1.3.6.1.4.1.19831.1.1.2.4.4.1.6
		dabDDRFPresentEnable OBJECT-TYPE
			SYNTAX TruthValue
			MAX-ACCESS read-write
			STATUS current
			DESCRIPTION
				"Description. Enable/Disable switch for dabDDRFPresent event"
			::= { dabDDEventEnableGeneral 6 }

		
		-- 1.3.6.1.4.1.19831.1.1.2.4.4.1.7
		dabDDResetFaultEnable OBJECT-TYPE
			SYNTAX TruthValue
			MAX-ACCESS read-write
			STATUS obsolete
			DESCRIPTION
				"Massage is inactive!
				
				Description. Enable/Disable switch for dabDDResetFault event
				"
			::= { dabDDEventEnableGeneral 7 }

		
		-- 1.3.6.1.4.1.19831.1.1.2.4.4.1.8
		dabDDAmplifierFaultEnable OBJECT-TYPE
			SYNTAX TruthValue
			MAX-ACCESS read-write
			STATUS current
			DESCRIPTION
				"Description. Enable/Disable switch for dabDDAmplifierFault event"
			::= { dabDDEventEnableGeneral 8 }

		
		-- 1.3.6.1.4.1.19831.1.1.2.4.4.1.9
		dabDDAmplifierWarningEnable OBJECT-TYPE
			SYNTAX TruthValue
			MAX-ACCESS read-write
			STATUS current
			DESCRIPTION
				"Description. Enable/Disable switch for dabDDAmplifierWarning event"
			::= { dabDDEventEnableGeneral 9 }

		
		-- 1.3.6.1.4.1.19831.1.1.2.4.4.1.10
		dabDDActiveExciterEnable OBJECT-TYPE
			SYNTAX TruthValue
			MAX-ACCESS read-write
			STATUS current
			DESCRIPTION
				"Description. Enable/Disable switch for dabDDActiveExciter event
				"
			::= { dabDDEventEnableGeneral 10 }

		
		-- 1.3.6.1.4.1.19831.1.1.2.4.4.1.11
		dabDDLocalModeEnable OBJECT-TYPE
			SYNTAX TruthValue
			MAX-ACCESS read-write
			STATUS current
			DESCRIPTION
				"Description. Enable/Disable switch for dabDDLocalMode event"
			::= { dabDDEventEnableGeneral 11 }

		
		-- 1.3.6.1.4.1.19831.1.1.2.4.4.1.12
		dabDDControlUnitFaultEnable OBJECT-TYPE
			SYNTAX TruthValue
			MAX-ACCESS read-write
			STATUS current
			DESCRIPTION
				"Description. Enable/Disable switch for dabDDControlUnitFault event"
			::= { dabDDEventEnableGeneral 12 }

		
		-- 1.3.6.1.4.1.19831.1.1.2.4.4.1.13
		dabDDSwitchOverModeEnable OBJECT-TYPE
			SYNTAX TruthValue
			MAX-ACCESS read-write
			STATUS current
			DESCRIPTION
				"Description. Enable/Disable switch for dabDDSwitchOverMode event"
			::= { dabDDEventEnableGeneral 13 }

		
		-- 1.3.6.1.4.1.19831.1.1.2.4.4.1.14
		dabDDSwitchOverReadyEnable OBJECT-TYPE
			SYNTAX TruthValue
			MAX-ACCESS read-write
			STATUS current
			DESCRIPTION
				"Description. Enable/Disable switch for dabDDSwitchOverReady event"
			::= { dabDDEventEnableGeneral 14 }

		
		-- 1.3.6.1.4.1.19831.1.1.2.4.4.1.15
		dabDDSwitchOverExecutedEnable OBJECT-TYPE
			SYNTAX TruthValue
			MAX-ACCESS read-write
			STATUS current
			DESCRIPTION
				"Description. Enable/Disable switch for dabDDSwitchOverExecuted event"
			::= { dabDDEventEnableGeneral 15 }

		
		-- 1.3.6.1.4.1.19831.1.1.2.4.4.1.16
		dabDDSwitchOverFaultEnable OBJECT-TYPE
			SYNTAX TruthValue
			MAX-ACCESS read-write
			STATUS current
			DESCRIPTION
				"Description. Enable/Disable switch for dabDDSwitchOverFault event"
			::= { dabDDEventEnableGeneral 16 }

		
		-- 1.3.6.1.4.1.19831.1.1.2.4.4.2
		dabDDEventEnableExciterA OBJECT IDENTIFIER ::= { dabDDEventEnable 2 }

		
		-- 1.3.6.1.4.1.19831.1.1.2.4.4.2.1
		dabDDExciterAInput1OKEnable OBJECT-TYPE
			SYNTAX TruthValue
			MAX-ACCESS read-write
			STATUS current
			DESCRIPTION
				"Description. Enable/Disable switch for dabDDExciterAInput1OK event"
			::= { dabDDEventEnableExciterA 1 }

		
		-- 1.3.6.1.4.1.19831.1.1.2.4.4.2.2
		dabDDExciterAInput2OKEnable OBJECT-TYPE
			SYNTAX TruthValue
			MAX-ACCESS read-write
			STATUS current
			DESCRIPTION
				"Description. Enable/Disable switch for dabDDExciterAInput2OK event"
			::= { dabDDEventEnableExciterA 2 }

		
		-- 1.3.6.1.4.1.19831.1.1.2.4.4.2.3
		dabDDExciterALocalModeEnable OBJECT-TYPE
			SYNTAX TruthValue
			MAX-ACCESS read-write
			STATUS current
			DESCRIPTION
				"Description. Enable/Disable switch for dabDDExciterALocalMode event"
			::= { dabDDEventEnableExciterA 3 }

		
		-- 1.3.6.1.4.1.19831.1.1.2.4.4.2.4
		dabDDExciterAFaultEnable OBJECT-TYPE
			SYNTAX TruthValue
			MAX-ACCESS read-write
			STATUS current
			DESCRIPTION
				"Description. Enable/Disable switch for dabDDExciterAFault  event"
			::= { dabDDEventEnableExciterA 4 }

		
		-- 1.3.6.1.4.1.19831.1.1.2.4.4.2.5
		dabDDExciterAWarningEnable OBJECT-TYPE
			SYNTAX TruthValue
			MAX-ACCESS read-write
			STATUS current
			DESCRIPTION
				"Description. Enable/Disable switch for dabDDExciterAWarning event"
			::= { dabDDEventEnableExciterA 5 }

		
		-- 1.3.6.1.4.1.19831.1.1.2.4.4.2.6
		dabDDExciterAActiveInputEnable OBJECT-TYPE
			SYNTAX TruthValue
			MAX-ACCESS read-write
			STATUS current
			DESCRIPTION
				"Description. Enable/Disable switch for dabDDExciterAActiveInput event"
			::= { dabDDEventEnableExciterA 6 }

		
		-- 1.3.6.1.4.1.19831.1.1.2.4.4.2.7
		dabDDExciterASFNModeEnable OBJECT-TYPE
			SYNTAX TruthValue
			MAX-ACCESS read-write
			STATUS current
			DESCRIPTION
				"Description. Enable/Disable switch for dabDDExciterASFNMode event"
			::= { dabDDEventEnableExciterA 7 }

		
		-- 1.3.6.1.4.1.19831.1.1.2.4.4.2.8
		dabDDExciterARefFaultEnable OBJECT-TYPE
			SYNTAX TruthValue
			MAX-ACCESS read-write
			STATUS current
			DESCRIPTION
				"Description. Enable/Disable switch for dabDDExciterARefFault event"
			::= { dabDDEventEnableExciterA 8 }

		
		-- 1.3.6.1.4.1.19831.1.1.2.4.4.2.9
		dabDDExciterAMuteEnable OBJECT-TYPE
			SYNTAX TruthValue
			MAX-ACCESS read-write
			STATUS current
			DESCRIPTION
				"Description. Enable/Disable switch for dabDDExciterAMute event"
			::= { dabDDEventEnableExciterA 9 }

		
		-- 1.3.6.1.4.1.19831.1.1.2.4.4.2.10
		dabDDExciterAWarningTimeStampEnable OBJECT-TYPE
			SYNTAX TruthValue
			MAX-ACCESS read-write
			STATUS current
			DESCRIPTION
				"Description. Enable/Disable switch for dabDDExciterAWarningTimeStamp event"
			::= { dabDDEventEnableExciterA 10 }

		
		-- 1.3.6.1.4.1.19831.1.1.2.4.4.3
		dabDDEventEnableExciterB OBJECT IDENTIFIER ::= { dabDDEventEnable 3 }

		
		-- 1.3.6.1.4.1.19831.1.1.2.4.4.3.1
		dabDDExciterBInput1OKEnable OBJECT-TYPE
			SYNTAX TruthValue
			MAX-ACCESS read-write
			STATUS current
			DESCRIPTION
				"Description. Enable/Disable switch for dabDDExciterBInput1OK event"
			::= { dabDDEventEnableExciterB 1 }

		
		-- 1.3.6.1.4.1.19831.1.1.2.4.4.3.2
		dabDDExciterBInput2OKEnable OBJECT-TYPE
			SYNTAX TruthValue
			MAX-ACCESS read-write
			STATUS current
			DESCRIPTION
				"Description. Enable/Disable switch for dabDDExciterBInput2OK event"
			::= { dabDDEventEnableExciterB 2 }

		
		-- 1.3.6.1.4.1.19831.1.1.2.4.4.3.3
		dabDDExciterBLocalModeEnable OBJECT-TYPE
			SYNTAX TruthValue
			MAX-ACCESS read-write
			STATUS current
			DESCRIPTION
				"Description. Enable/Disable switch for dabDDExciterBLocalMode event"
			::= { dabDDEventEnableExciterB 3 }

		
		-- 1.3.6.1.4.1.19831.1.1.2.4.4.3.4
		dabDDExciterBFaultEnable OBJECT-TYPE
			SYNTAX TruthValue
			MAX-ACCESS read-write
			STATUS current
			DESCRIPTION
				"Description. Enable/Disable switch for dabDDExciterBFault event"
			::= { dabDDEventEnableExciterB 4 }

		
		-- 1.3.6.1.4.1.19831.1.1.2.4.4.3.5
		dabDDExciterBWarningEnable OBJECT-TYPE
			SYNTAX TruthValue
			MAX-ACCESS read-write
			STATUS current
			DESCRIPTION
				"Description. Enable/Disable switch for dabDDExciterBWarning event"
			::= { dabDDEventEnableExciterB 5 }

		
		-- 1.3.6.1.4.1.19831.1.1.2.4.4.3.6
		dabDDExciterBActiveInputEnable OBJECT-TYPE
			SYNTAX TruthValue
			MAX-ACCESS read-write
			STATUS current
			DESCRIPTION
				"Description. Enable/Disable switch for dabDDExciterBActiveInput event"
			::= { dabDDEventEnableExciterB 6 }

		
		-- 1.3.6.1.4.1.19831.1.1.2.4.4.3.7
		dabDDExciterBSFNModeEnable OBJECT-TYPE
			SYNTAX TruthValue
			MAX-ACCESS read-write
			STATUS current
			DESCRIPTION
				"Description. Enable/Disable switch for dabDDExciterBSFNMode event"
			::= { dabDDEventEnableExciterB 7 }

		
		-- 1.3.6.1.4.1.19831.1.1.2.4.4.3.8
		dabDDExciterBRefFaultEnable OBJECT-TYPE
			SYNTAX TruthValue
			MAX-ACCESS read-write
			STATUS current
			DESCRIPTION
				"Description. Enable/Disable switch for dabDDExciterBRefFault event"
			::= { dabDDEventEnableExciterB 8 }

		
		-- 1.3.6.1.4.1.19831.1.1.2.4.4.3.9
		dabDDExciterBMuteEnable OBJECT-TYPE
			SYNTAX TruthValue
			MAX-ACCESS read-write
			STATUS current
			DESCRIPTION
				"Description. Enable/Disable switch for dabDDExciterBMute event"
			::= { dabDDEventEnableExciterB 9 }

		
		-- 1.3.6.1.4.1.19831.1.1.2.4.4.3.10
		dabDDExciterBWarningTimeStampEnable OBJECT-TYPE
			SYNTAX TruthValue
			MAX-ACCESS read-write
			STATUS current
			DESCRIPTION
				"Description. Enable/Disable switch for dabDDExciterBWarningTimeStamp event"
			::= { dabDDEventEnableExciterB 10 }

		
-- dab dual drive event priority
		-- 1.3.6.1.4.1.19831.1.1.2.4.5
		dabDDEventPriority OBJECT IDENTIFIER ::= { dabDualDrive 5 }

		
		-- 1.3.6.1.4.1.19831.1.1.2.4.5.1
		dabDDEventPriorityGeneral OBJECT IDENTIFIER ::= { dabDDEventPriority 1 }

		
		-- 1.3.6.1.4.1.19831.1.1.2.4.5.1.1
		dabDDInputPreselectionPriority OBJECT-TYPE
			SYNTAX Unsigned32
			MAX-ACCESS read-write
			STATUS current
			DESCRIPTION
				"Description. Priority for dabDDInputPreselection event"
			::= { dabDDEventPriorityGeneral 1 }

		
		-- 1.3.6.1.4.1.19831.1.1.2.4.5.1.2
		dabDDInputAutomaticPriority OBJECT-TYPE
			SYNTAX Unsigned32
			MAX-ACCESS read-write
			STATUS current
			DESCRIPTION
				"Description. Priority for dabDDInputAutomatic event"
			::= { dabDDEventPriorityGeneral 2 }

		
		-- 1.3.6.1.4.1.19831.1.1.2.4.5.1.3
		dabDDPreselectionExciterPriority OBJECT-TYPE
			SYNTAX Unsigned32
			MAX-ACCESS read-write
			STATUS current
			DESCRIPTION
				"Description. Priority for dabDDInputExciter event"
			::= { dabDDEventPriorityGeneral 3 }

		
		-- 1.3.6.1.4.1.19831.1.1.2.4.5.1.4
		dabDDTransmitterOpModePriority OBJECT-TYPE
			SYNTAX Unsigned32
			MAX-ACCESS read-write
			STATUS current
			DESCRIPTION
				"Description. Priority for dabDDTransmitterOpMode event"
			::= { dabDDEventPriorityGeneral 4 }

		
		-- 1.3.6.1.4.1.19831.1.1.2.4.5.1.5
		dabDDReserveControlPriority OBJECT-TYPE
			SYNTAX Unsigned32
			MAX-ACCESS read-write
			STATUS current
			DESCRIPTION
				"Description. Priority for dabDDReserveControl event"
			::= { dabDDEventPriorityGeneral 5 }

		
		-- 1.3.6.1.4.1.19831.1.1.2.4.5.1.6
		dabDDRFPresentPriority OBJECT-TYPE
			SYNTAX Unsigned32
			MAX-ACCESS read-write
			STATUS current
			DESCRIPTION
				"Description. Priority for dabDDRFPresent event"
			::= { dabDDEventPriorityGeneral 6 }

		
		-- 1.3.6.1.4.1.19831.1.1.2.4.5.1.7
		dabDDResetFaultPriority OBJECT-TYPE
			SYNTAX Unsigned32
			MAX-ACCESS read-write
			STATUS obsolete
			DESCRIPTION
				"Massage is inactive!
				
				Description. Priority for dabDDResetFault event"
			::= { dabDDEventPriorityGeneral 7 }

		
		-- 1.3.6.1.4.1.19831.1.1.2.4.5.1.8
		dabDDAmplifierFaultPriority OBJECT-TYPE
			SYNTAX Unsigned32
			MAX-ACCESS read-write
			STATUS current
			DESCRIPTION
				"Description. Priority for dabDDAmplifierFault event"
			::= { dabDDEventPriorityGeneral 8 }

		
		-- 1.3.6.1.4.1.19831.1.1.2.4.5.1.9
		dabDDAmplifierWarningPriority OBJECT-TYPE
			SYNTAX Unsigned32
			MAX-ACCESS read-write
			STATUS current
			DESCRIPTION
				"Description. Priority for dabDDAmplifierWarning event"
			::= { dabDDEventPriorityGeneral 9 }

		
		-- 1.3.6.1.4.1.19831.1.1.2.4.5.1.10
		dabDDActiveExciterPriority OBJECT-TYPE
			SYNTAX Unsigned32
			MAX-ACCESS read-write
			STATUS current
			DESCRIPTION
				"Description. Priority for dabDDActiveExciter event"
			::= { dabDDEventPriorityGeneral 10 }

		
		-- 1.3.6.1.4.1.19831.1.1.2.4.5.1.11
		dabDDLocalModePriority OBJECT-TYPE
			SYNTAX Unsigned32
			MAX-ACCESS read-write
			STATUS current
			DESCRIPTION
				"Description. Priority for dabDDLocalMode event"
			::= { dabDDEventPriorityGeneral 11 }

		
		-- 1.3.6.1.4.1.19831.1.1.2.4.5.1.12
		dabDDControlUnitFaultPriority OBJECT-TYPE
			SYNTAX Unsigned32
			MAX-ACCESS read-write
			STATUS current
			DESCRIPTION
				"Description. Priority for dabDDControlUnitFault event"
			::= { dabDDEventPriorityGeneral 12 }

		
		-- 1.3.6.1.4.1.19831.1.1.2.4.5.1.13
		dabDDSwitchOverModePriority OBJECT-TYPE
			SYNTAX Unsigned32
			MAX-ACCESS read-write
			STATUS current
			DESCRIPTION
				"Description. Priority for dabDDSwitchOverMode event"
			::= { dabDDEventPriorityGeneral 13 }

		
		-- 1.3.6.1.4.1.19831.1.1.2.4.5.1.14
		dabDDSwitchOverReadyPriority OBJECT-TYPE
			SYNTAX Unsigned32
			MAX-ACCESS read-write
			STATUS current
			DESCRIPTION
				"Description. Priority for dabDDSwitchOverReady event"
			::= { dabDDEventPriorityGeneral 14 }

		
		-- 1.3.6.1.4.1.19831.1.1.2.4.5.1.15
		dabDDSwitchOverExecutedPriority OBJECT-TYPE
			SYNTAX Unsigned32
			MAX-ACCESS read-write
			STATUS current
			DESCRIPTION
				"Description. Priority for dabDDSwitchOverExecuted event"
			::= { dabDDEventPriorityGeneral 15 }

		
		-- 1.3.6.1.4.1.19831.1.1.2.4.5.1.16
		dabDDSwitchOverFaultPriority OBJECT-TYPE
			SYNTAX Unsigned32
			MAX-ACCESS read-write
			STATUS current
			DESCRIPTION
				"Description. Priority for dabDDSwitchOverFault event"
			::= { dabDDEventPriorityGeneral 16 }

		
		-- 1.3.6.1.4.1.19831.1.1.2.4.5.2
		dabDDEventPriorityExciterA OBJECT IDENTIFIER ::= { dabDDEventPriority 2 }

		
		-- 1.3.6.1.4.1.19831.1.1.2.4.5.2.1
		dabDDExciterAInput1OKPriority OBJECT-TYPE
			SYNTAX Unsigned32
			MAX-ACCESS read-write
			STATUS current
			DESCRIPTION
				"Description. Priority for dabDDExciterAInput1OK event"
			::= { dabDDEventPriorityExciterA 1 }

		
		-- 1.3.6.1.4.1.19831.1.1.2.4.5.2.2
		dabDDExciterAInput2OKPriority OBJECT-TYPE
			SYNTAX Unsigned32
			MAX-ACCESS read-write
			STATUS current
			DESCRIPTION
				"Description. Priority for dabDDExciterAInput2OK event"
			::= { dabDDEventPriorityExciterA 2 }

		
		-- 1.3.6.1.4.1.19831.1.1.2.4.5.2.3
		dabDDExciterALocalModePriority OBJECT-TYPE
			SYNTAX Unsigned32
			MAX-ACCESS read-write
			STATUS current
			DESCRIPTION
				"Description. Priority for dabDDExciterALocalMode event"
			::= { dabDDEventPriorityExciterA 3 }

		
		-- 1.3.6.1.4.1.19831.1.1.2.4.5.2.4
		dabDDExciterAFaultPriority OBJECT-TYPE
			SYNTAX Unsigned32
			MAX-ACCESS read-write
			STATUS current
			DESCRIPTION
				"Description. Priority for dabDDExciterAFault event"
			::= { dabDDEventPriorityExciterA 4 }

		
		-- 1.3.6.1.4.1.19831.1.1.2.4.5.2.5
		dabDDExciterAWarningPriority OBJECT-TYPE
			SYNTAX Unsigned32
			MAX-ACCESS read-write
			STATUS current
			DESCRIPTION
				"Description. Priority for dabDDExciterAWarning event"
			::= { dabDDEventPriorityExciterA 5 }

		
		-- 1.3.6.1.4.1.19831.1.1.2.4.5.2.6
		dabDDExciterAActiveInputPriority OBJECT-TYPE
			SYNTAX Unsigned32
			MAX-ACCESS read-write
			STATUS current
			DESCRIPTION
				"Description. Priority for dabDDExciterAActiveInput event"
			::= { dabDDEventPriorityExciterA 6 }

		
		-- 1.3.6.1.4.1.19831.1.1.2.4.5.2.7
		dabDDExciterASFNModePriority OBJECT-TYPE
			SYNTAX Unsigned32
			MAX-ACCESS read-write
			STATUS current
			DESCRIPTION
				"Description. Priority for dabDDExciterASFNMode event"
			::= { dabDDEventPriorityExciterA 7 }

		
		-- 1.3.6.1.4.1.19831.1.1.2.4.5.2.8
		dabDDExciterARefFaultPriority OBJECT-TYPE
			SYNTAX Unsigned32
			MAX-ACCESS read-write
			STATUS current
			DESCRIPTION
				"Description. Priority for dabDDExciterARefFault event"
			::= { dabDDEventPriorityExciterA 8 }

		
		-- 1.3.6.1.4.1.19831.1.1.2.4.5.2.9
		dabDDExciterAMutePriority OBJECT-TYPE
			SYNTAX Unsigned32
			MAX-ACCESS read-write
			STATUS current
			DESCRIPTION
				"Description. Priority for dabDDExciterAMute event"
			::= { dabDDEventPriorityExciterA 9 }

		
		-- 1.3.6.1.4.1.19831.1.1.2.4.5.2.10
		dabDDExciterAWarningTimeStampPriority OBJECT-TYPE
			SYNTAX Unsigned32
			MAX-ACCESS read-write
			STATUS current
			DESCRIPTION
				"Description. Priority for dabDDExciterAWarningTimeStamp event"
			::= { dabDDEventPriorityExciterA 10 }

		
		-- 1.3.6.1.4.1.19831.1.1.2.4.5.3
		dabDDEventPriorityExciterB OBJECT IDENTIFIER ::= { dabDDEventPriority 3 }

		
		-- 1.3.6.1.4.1.19831.1.1.2.4.5.3.1
		dabDDExciterBInput1OKPriority OBJECT-TYPE
			SYNTAX Unsigned32
			MAX-ACCESS read-write
			STATUS current
			DESCRIPTION
				"Description. Priority for dabDDExciterBInput1OK event"
			::= { dabDDEventPriorityExciterB 1 }

		
		-- 1.3.6.1.4.1.19831.1.1.2.4.5.3.2
		dabDDExciterBInput2OKPriority OBJECT-TYPE
			SYNTAX Unsigned32
			MAX-ACCESS read-write
			STATUS current
			DESCRIPTION
				"Description. Priority for dabDDExciterBInput2OK event"
			::= { dabDDEventPriorityExciterB 2 }

		
		-- 1.3.6.1.4.1.19831.1.1.2.4.5.3.3
		dabDDExciterBLocalModePriority OBJECT-TYPE
			SYNTAX Unsigned32
			MAX-ACCESS read-write
			STATUS current
			DESCRIPTION
				"Description. Priority for dabDDExciterBLocalMode event"
			::= { dabDDEventPriorityExciterB 3 }

		
		-- 1.3.6.1.4.1.19831.1.1.2.4.5.3.4
		dabDDExciterBFaultPriority OBJECT-TYPE
			SYNTAX Unsigned32
			MAX-ACCESS read-write
			STATUS current
			DESCRIPTION
				"Description. Priority for dabDDExciterBFault event"
			::= { dabDDEventPriorityExciterB 4 }

		
		-- 1.3.6.1.4.1.19831.1.1.2.4.5.3.5
		dabDDExciterBWarningPriority OBJECT-TYPE
			SYNTAX Unsigned32
			MAX-ACCESS read-write
			STATUS current
			DESCRIPTION
				"Description. Priority for dabDDExciterBWarning event"
			::= { dabDDEventPriorityExciterB 5 }

		
		-- 1.3.6.1.4.1.19831.1.1.2.4.5.3.6
		dabDDExciterBActiveInputPriority OBJECT-TYPE
			SYNTAX Unsigned32
			MAX-ACCESS read-write
			STATUS current
			DESCRIPTION
				"Description. Priority for dabDDExciterBActiveInput event"
			::= { dabDDEventPriorityExciterB 6 }

		
		-- 1.3.6.1.4.1.19831.1.1.2.4.5.3.7
		dabDDExciterBSFNModePriority OBJECT-TYPE
			SYNTAX Unsigned32
			MAX-ACCESS read-write
			STATUS current
			DESCRIPTION
				"Description. Priority for dabDDExciterBSFNMode event"
			::= { dabDDEventPriorityExciterB 7 }

		
		-- 1.3.6.1.4.1.19831.1.1.2.4.5.3.8
		dabDDExciterBRefFaultPriority OBJECT-TYPE
			SYNTAX Unsigned32
			MAX-ACCESS read-write
			STATUS current
			DESCRIPTION
				"Description. Priority for dabDDExciterBRefFault event"
			::= { dabDDEventPriorityExciterB 8 }

		
		-- 1.3.6.1.4.1.19831.1.1.2.4.5.3.9
		dabDDExciterBMutePriority OBJECT-TYPE
			SYNTAX Unsigned32
			MAX-ACCESS read-write
			STATUS current
			DESCRIPTION
				"Description. Priority for dabDDExciterBMute event"
			::= { dabDDEventPriorityExciterB 9 }

		
		-- 1.3.6.1.4.1.19831.1.1.2.4.5.3.10
		dabDDExciterBWarningTimeStampPriority OBJECT-TYPE
			SYNTAX Unsigned32
			MAX-ACCESS read-write
			STATUS current
			DESCRIPTION
				"Description. Priority for dabDDExciterBWarningTimeStamp event"
			::= { dabDDEventPriorityExciterB 10 }

		
		-- 1.3.6.1.4.1.19831.1.1.2.4.6
		groupsDD OBJECT IDENTIFIER ::= { dabDualDrive 6 }

		
		-- 1.3.6.1.4.1.19831.1.1.2.4.6.1
		eventGroupDD NOTIFICATION-GROUP
			NOTIFICATIONS { dabDDInputPreselectionEvent, dabDDInputAutomaticEvent, dabDDPreselectionExciterEvent, dabDDTransmitterOpModeEvent, dabDDReserveControlEvent, 
				dabDDRFPresentEvent, dabDDAmplifierFaultEvent, dabDDActiveExciterEvent, dabDDLocalModeEvent, dabDDControlUnitFaultEvent, 
				dabDDSwitchOverModeEvent, dabDDSwitchOverReadyEvent, dabDDSwitchOverExecutedEvent, dabDDSwitchOverFaultEvent, dabDDExciterAInput1OKEvent, 
				dabDDExciterAInput2OKEvent, dabDDExciterALocalModeEvent, dabDDExciterAFaultEvent, dabDDExciterAWarningEvent, dabDDExciterAActiveInputEvent, 
				dabDDExciterASFNModeEvent, dabDDExciterARefFaultEvent, dabDDExciterAMuteEvent, dabDDExciterAWarningTimeStampEvent, dabDDExciterBInput1OKEvent, 
				dabDDExciterBInput2OKEvent, dabDDExciterBLocalModeEvent, dabDDExciterBFaultEvent, dabDDExciterBWarningEvent, dabDDExciterBActiveInputEvent, 
				dabDDExciterBSFNModeEvent, dabDDExciterBRefFaultEvent, dabDDExciterBMuteEvent, dabDDExciterBWarningTimeStampEvent, dabDDAmplifierWarningEvent
				 }
			STATUS current
			DESCRIPTION 
				"Description. dual drive: events group"
			::= { groupsDD 1 }

		
		-- 1.3.6.1.4.1.19831.1.1.2.4.6.2
		objectGroupDD OBJECT-GROUP
			OBJECTS { dabDDInputPreselection, dabDDInputAutomatic, dabDDPreselectionExciter, dabDDTransmitterOpMode, dabDDReserveControl, 
				dabDDRFPresent, dabDDAmplifierFault, dabDDActiveExciter, dabDDLocalMode, dabDDControlUnitFault, 
				dabDDSwitchOverMode, dabDDSwitchOverReady, dabDDSwitchOverExecuted, dabDDSwitchOverFault, dabDDExciterAInput1OK, 
				dabDDExciterAInput2OK, dabDDExciterALocalMode, dabDDExciterAFault, dabDDExciterAWarning, dabDDExciterAActiveInput, 
				dabDDExciterASFNMode, dabDDExciterARefFault, dabDDExciterAMute, dabDDExciterAWarningTimeStamp, dabDDExciterBInput1OK, 
				dabDDExciterBInput2OK, dabDDExciterBLocalMode, dabDDExciterBFault, dabDDExciterBWarning, dabDDExciterBActiveInput, 
				dabDDExciterBSFNMode, dabDDExciterBRefFault, dabDDExciterBMute, dabDDExciterBWarningTimeStamp, dabDDInputPreselectionEnable, 
				dabDDInputAutomaticEnable, dabDDPreselectionExciterEnable, dabDDTransmitterOpModeEnable, dabDDReserveControlEnable, dabDDRFPresentEnable, 
				dabDDAmplifierFaultEnable, dabDDActiveExciterEnable, dabDDLocalModeEnable, dabDDControlUnitFaultEnable, dabDDSwitchOverModeEnable, 
				dabDDSwitchOverReadyEnable, dabDDSwitchOverExecutedEnable, dabDDSwitchOverFaultEnable, dabDDExciterAInput1OKEnable, dabDDExciterAInput2OKEnable, 
				dabDDExciterALocalModeEnable, dabDDExciterAFaultEnable, dabDDExciterAWarningEnable, dabDDExciterAActiveInputEnable, dabDDExciterASFNModeEnable, 
				dabDDExciterARefFaultEnable, dabDDExciterAMuteEnable, dabDDExciterAWarningTimeStampEnable, dabDDExciterBInput1OKEnable, dabDDExciterBInput2OKEnable, 
				dabDDExciterBLocalModeEnable, dabDDExciterBFaultEnable, dabDDExciterBWarningEnable, dabDDExciterBActiveInputEnable, dabDDExciterBSFNModeEnable, 
				dabDDExciterBRefFaultEnable, dabDDExciterBMuteEnable, dabDDExciterBWarningTimeStampEnable, dabDDInputPreselectionPriority, dabDDInputAutomaticPriority, 
				dabDDPreselectionExciterPriority, dabDDTransmitterOpModePriority, dabDDReserveControlPriority, dabDDRFPresentPriority, dabDDAmplifierFaultPriority, 
				dabDDActiveExciterPriority, dabDDLocalModePriority, dabDDControlUnitFaultPriority, dabDDSwitchOverModePriority, dabDDSwitchOverReadyPriority, 
				dabDDSwitchOverExecutedPriority, dabDDSwitchOverFaultPriority, dabDDExciterAInput1OKPriority, dabDDExciterAInput2OKPriority, dabDDExciterALocalModePriority, 
				dabDDExciterAFaultPriority, dabDDExciterAWarningPriority, dabDDExciterAActiveInputPriority, dabDDExciterASFNModePriority, dabDDExciterARefFaultPriority, 
				dabDDExciterAMutePriority, dabDDExciterAWarningTimeStampPriority, dabDDExciterBInput1OKPriority, dabDDExciterBInput2OKPriority, dabDDExciterBLocalModePriority, 
				dabDDExciterBFaultPriority, dabDDExciterBWarningPriority, dabDDExciterBActiveInputPriority, dabDDExciterBSFNModePriority, dabDDExciterBRefFaultPriority, 
				dabDDExciterBMutePriority, dabDDExciterBWarningTimeStampPriority, dabDDAmplifierWarning, dabDDAmplifierWarningEnable, dabDDAmplifierWarningPriority
				 }
			STATUS current
			DESCRIPTION 
				"Description.dual drive: object group"
			::= { groupsDD 2 }

		
		-- 1.3.6.1.4.1.19831.1.1.2.4.6.3
		eventGroupDDobsolete NOTIFICATION-GROUP
			NOTIFICATIONS { dabDDResetFaultEvent }
			STATUS obsolete
			DESCRIPTION 
				"Description. Inactive events"
			::= { groupsDD 3 }

		
		-- 1.3.6.1.4.1.19831.1.1.2.4.6.4
		objectGroupDDobsolete OBJECT-GROUP
			OBJECTS { dabDDResetFault, dabDDResetFaultEnable, dabDDResetFaultPriority }
			STATUS obsolete
			DESCRIPTION 
				"Description.Inactive objects"
			::= { groupsDD 4 }

		
		-- 1.3.6.1.4.1.19831.1.1.2.4.7
		complianceDD OBJECT IDENTIFIER ::= { dabDualDrive 7 }

		
		-- 1.3.6.1.4.1.19831.1.1.2.4.7.1
		dabDualDriveCompliance MODULE-COMPLIANCE
			STATUS current
			DESCRIPTION 
				"Compliance Statement"
			MODULE -- this module
				MANDATORY-GROUPS { eventGroupDD, objectGroupDD }
			::= { complianceDD 1 }

		
	
	END

--
-- IRT-DAB-DUALDRIVE-MIB.my
--
