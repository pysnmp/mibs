--
-- IRT-FM-DUALDRIVE-MIB.my
-- MIB generated by MG-SOFT Visual MIB Builder Version 6.0  Build 88
-- Friday, May 04, 2007 at 19:06:17
--

	IRT-FM-DUALDRIVE-MIB DEFINITIONS ::= BEGIN
 
		IMPORTS
			eventTimeStamp, eventPriority, eventCounter, mibRelease			
				FROM IRT-COMMONVARBINDS-MIB			
			fm, SelectOnOff, PresentNotPresent, FaultOK, WarningOK, 
			LocalRemote, SelectManualAuto, ReadyNotReady, ExecutedNotExecuted			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			TruthValue			
				FROM SNMPv2-TC;
	
	
		-- 1.3.6.1.4.1.19831.1.1.3.4
		fmDualDrive MODULE-IDENTITY 
			LAST-UPDATED "200705041400Z"		-- May 04, 2007 at 14:00 GMT
			ORGANIZATION 
				"IRT for WORKING-GROUP-TC-MIB"
			CONTACT-INFO 
				"
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events               OBJECT IDENTIFIER ::= { fmDualDrive 0 }
				fmDDGeneral          OBJECT IDENTIFIER ::= { fmDualDrive 1 }
				fmDDExciterA         OBJECT IDENTIFIER ::= { fmDualDrive 2 }
				fmDDExciterB         OBJECT IDENTIFIER ::= { fmDualDrive 3 }
				fmDDEventEnable      OBJECT IDENTIFIER ::= { fmDualDrive 4 }
				fmDDEventPriority    OBJECT IDENTIFIER ::= { fmDualDrive 5 }
				groups               OBJECT IDENTIFIER ::= { fmDualDrive 6 }
				
				2nd level
				
				fmDDEventEnableGeneral   OBJECT IDENTIFIER ::= { fmDDEventEnable 1 }
				fmDDEventEnableExciterA  OBJECT IDENTIFIER ::= { fmDDEventEnable 2 }
				fmDDEventEnableExciterB  OBJECT IDENTIFIER ::= { fmDDEventEnable 3 }
				
				fmDDEventPriorityGeneral   OBJECT IDENTIFIER ::= { fmDDEventPriority 1 }
				fmDDEventPriorityExciterA  OBJECT IDENTIFIER ::= { fmDDEventPriority 2 }
				fmDDEventPriorityExciterB  OBJECT IDENTIFIER ::= { fmDDEventPriority 3 }
				
				end branch"
			REVISION "200705041400Z"		-- May 04, 2007 at 14:00 GMT
			DESCRIPTION 
				"change LocalMode (description) and Module-COMPLIANCE change numbering: OIDs 1.3.6.1.4.1.19831.1.1.3.4.0.14-19"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { fm 4 }

		
	
	
--
-- Node definitions
--
	
-- fm dual drive events
		-- 1.3.6.1.4.1.19831.1.1.3.4.0
		fmEventsDD OBJECT IDENTIFIER ::= { fmDualDrive 0 }

		
		-- 1.3.6.1.4.1.19831.1.1.3.4.0.1
		fmDDPreselectionExciterEvent NOTIFICATION-TYPE
			OBJECTS { sysDescr, sysName, sysLocation, eventTimeStamp, eventPriority, 
				eventCounter, fmDDPreselectionExciter }
			STATUS current
			DESCRIPTION 
				"Description. fmDDPreselectionExciterEvent notification"
			::= { fmEventsDD 1 }

		
		-- 1.3.6.1.4.1.19831.1.1.3.4.0.2
		fmDDTransmitterOpModeEvent NOTIFICATION-TYPE
			OBJECTS { sysDescr, sysName, sysLocation, eventTimeStamp, eventPriority, 
				eventCounter, fmDDTransmitterOpMode }
			STATUS current
			DESCRIPTION 
				"Description. fmDDTransmitterOpMode notification"
			::= { fmEventsDD 2 }

		
		-- 1.3.6.1.4.1.19831.1.1.3.4.0.3
		fmDDReserveControlEvent NOTIFICATION-TYPE
			OBJECTS { sysDescr, sysName, sysLocation, eventTimeStamp, eventPriority, 
				eventCounter, fmDDReserveControl }
			STATUS current
			DESCRIPTION 
				"Description. fmDDReserveControl nitification"
			::= { fmEventsDD 3 }

		
		-- 1.3.6.1.4.1.19831.1.1.3.4.0.4
		fmDDRFPresentEvent NOTIFICATION-TYPE
			OBJECTS { sysDescr, sysName, sysLocation, eventTimeStamp, eventPriority, 
				eventCounter, fmDDRFPresent }
			STATUS current
			DESCRIPTION 
				"Description. fmDDRFPresent notification"
			::= { fmEventsDD 4 }

		
		-- 1.3.6.1.4.1.19831.1.1.3.4.0.5
		fmDDAmplifierFaultEvent NOTIFICATION-TYPE
			OBJECTS { sysDescr, sysName, sysLocation, eventTimeStamp, eventPriority, 
				eventCounter, fmDDAmplifierFault }
			STATUS current
			DESCRIPTION 
				"Description. fmDDAmplifierFault notification"
			::= { fmEventsDD 5 }

		
		-- 1.3.6.1.4.1.19831.1.1.3.4.0.6
		fmDDAmplifierWarningEvent NOTIFICATION-TYPE
			OBJECTS { sysDescr, sysName, sysLocation, eventTimeStamp, eventPriority, 
				eventCounter, fmDDAmplifierWarning }
			STATUS current
			DESCRIPTION 
				"Description. fmDDAmplifierWarning notification"
			::= { fmEventsDD 6 }

		
		-- 1.3.6.1.4.1.19831.1.1.3.4.0.7
		fmDDActiveExciterEvent NOTIFICATION-TYPE
			OBJECTS { sysDescr, sysName, sysLocation, eventTimeStamp, eventPriority, 
				eventCounter, fmDDActiveExciter }
			STATUS current
			DESCRIPTION 
				"Description.fmDDActiveExciter notification"
			::= { fmEventsDD 7 }

		
		-- 1.3.6.1.4.1.19831.1.1.3.4.0.8
		fmDDLocalModeEvent NOTIFICATION-TYPE
			OBJECTS { sysDescr, sysName, sysLocation, eventTimeStamp, eventPriority, 
				eventCounter, fmDDLocalMode }
			STATUS current
			DESCRIPTION 
				"Description. fmDDLocalMode notification"
			::= { fmEventsDD 8 }

		
		-- 1.3.6.1.4.1.19831.1.1.3.4.0.9
		fmDDControlUnitFaultEvent NOTIFICATION-TYPE
			OBJECTS { sysDescr, sysName, sysLocation, eventTimeStamp, eventPriority, 
				eventCounter, fmDDControlUnitFault }
			STATUS current
			DESCRIPTION 
				"Description. fmDDControlUnitFault notification"
			::= { fmEventsDD 9 }

		
		-- 1.3.6.1.4.1.19831.1.1.3.4.0.10
		fmDDSwitchOverModeEvent NOTIFICATION-TYPE
			OBJECTS { sysDescr, sysName, sysLocation, eventTimeStamp, eventPriority, 
				eventCounter, fmDDSwitchOverMode }
			STATUS current
			DESCRIPTION 
				"Description. fmDDSwitchOverMode notification"
			::= { fmEventsDD 10 }

		
		-- 1.3.6.1.4.1.19831.1.1.3.4.0.11
		fmDDSwitchOverReadyEvent NOTIFICATION-TYPE
			OBJECTS { sysDescr, sysName, sysLocation, eventTimeStamp, eventPriority, 
				eventCounter, fmDDSwitchOverReady }
			STATUS current
			DESCRIPTION 
				"Description. fmDDSwitchOverReady notification"
			::= { fmEventsDD 11 }

		
		-- 1.3.6.1.4.1.19831.1.1.3.4.0.12
		fmDDSwitchOverExecutedEvent NOTIFICATION-TYPE
			OBJECTS { sysDescr, sysName, sysLocation, eventTimeStamp, eventPriority, 
				eventCounter, fmDDSwitchOverExecuted }
			STATUS current
			DESCRIPTION 
				"Description. fmDDSwitchOverExecuted notification"
			::= { fmEventsDD 12 }

		
		-- 1.3.6.1.4.1.19831.1.1.3.4.0.13
		fmDDSwitchOverFaultEvent NOTIFICATION-TYPE
			OBJECTS { sysDescr, sysName, sysLocation, eventTimeStamp, eventPriority, 
				eventCounter, fmDDSwitchOverFault }
			STATUS current
			DESCRIPTION 
				"Description. fmDDSwitchOverFault notification"
			::= { fmEventsDD 13 }

		
		-- 1.3.6.1.4.1.19831.1.1.3.4.0.14
		fmDDExciterALocalModeEvent NOTIFICATION-TYPE
			OBJECTS { sysDescr, sysName, sysLocation, eventTimeStamp, eventPriority, 
				eventCounter, fmDDExciterALocalMode }
			STATUS current
			DESCRIPTION 
				"Description. fmDDExciterALocalMode notification"
			::= { fmEventsDD 14 }

		
		-- 1.3.6.1.4.1.19831.1.1.3.4.0.15
		fmDDExciterAFaultEvent NOTIFICATION-TYPE
			OBJECTS { sysDescr, sysName, sysLocation, eventTimeStamp, eventPriority, 
				eventCounter, fmDDExciterAFault }
			STATUS current
			DESCRIPTION 
				"Description. fmDDExciterAFault notification"
			::= { fmEventsDD 15 }

		
		-- 1.3.6.1.4.1.19831.1.1.3.4.0.16
		fmDDExciterAWarningEvent NOTIFICATION-TYPE
			OBJECTS { sysDescr, sysName, sysLocation, eventTimeStamp, eventPriority, 
				eventCounter, fmDDExciterAWarning }
			STATUS current
			DESCRIPTION 
				"Description. fmDDExciterAWarning notification"
			::= { fmEventsDD 16 }

		
		-- 1.3.6.1.4.1.19831.1.1.3.4.0.17
		fmDDExciterBLocalModeEvent NOTIFICATION-TYPE
			OBJECTS { sysDescr, sysName, sysLocation, eventTimeStamp, eventPriority, 
				eventCounter, fmDDExciterBLocalMode }
			STATUS current
			DESCRIPTION 
				"Description. fmDDExciterBLocalMode notification"
			::= { fmEventsDD 17 }

		
		-- 1.3.6.1.4.1.19831.1.1.3.4.0.18
		fmDDExciterBFaultEvent NOTIFICATION-TYPE
			OBJECTS { sysDescr, sysName, sysLocation, eventTimeStamp, eventPriority, 
				eventCounter, fmDDExciterBFault }
			STATUS current
			DESCRIPTION 
				"Description. fmDDExciterBFault notification"
			::= { fmEventsDD 18 }

		
		-- 1.3.6.1.4.1.19831.1.1.3.4.0.19
		fmDDExciterBWarningEvent NOTIFICATION-TYPE
			OBJECTS { sysDescr, sysName, sysLocation, eventTimeStamp, eventPriority, 
				eventCounter, fmDDExciterBWarning }
			STATUS current
			DESCRIPTION 
				"Description. fmDDExciterBWarning notification"
			::= { fmEventsDD 19 }

		
-- fm dual drive general
		-- 1.3.6.1.4.1.19831.1.1.3.4.1
		fmDDGeneral OBJECT IDENTIFIER ::= { fmDualDrive 1 }

		
		-- 1.3.6.1.4.1.19831.1.1.3.4.1.1
		fmDDPreselectionExciter OBJECT-TYPE
			SYNTAX INTEGER
				{
				undefined(0),
				exciterA(1),
				exciterB(2)
				}
			MAX-ACCESS read-write
			STATUS current
			DESCRIPTION
				"fm. Preselection of the exciter 
				
				"
			::= { fmDDGeneral 1 }

		
		-- 1.3.6.1.4.1.19831.1.1.3.4.1.2
		fmDDTransmitterOpMode OBJECT-TYPE
			SYNTAX SelectOnOff
			MAX-ACCESS read-write
			STATUS current
			DESCRIPTION
				"Dual drive. Operation mode of main exciter 
				
				(0) undefined
				(1) ON
				(2) OFF"
			::= { fmDDGeneral 2 }

		
		-- 1.3.6.1.4.1.19831.1.1.3.4.1.3
		fmDDReserveControl OBJECT-TYPE
			SYNTAX SelectOnOff
			MAX-ACCESS read-write
			STATUS current
			DESCRIPTION
				"Dual drive. Operation mode of reserve exciter
				
				(0) undefined
				(1) ON 
				(2) OFF "
			::= { fmDDGeneral 3 }

		
		-- 1.3.6.1.4.1.19831.1.1.3.4.1.4
		fmDDRFPresent OBJECT-TYPE
			SYNTAX PresentNotPresent
			MAX-ACCESS read-only
			STATUS current
			DESCRIPTION
				"Dual drive. Output power is present
				
				(0) undefined
				(1) present
				(2) not present
				"
			::= { fmDDGeneral 4 }

		
		-- 1.3.6.1.4.1.19831.1.1.3.4.1.5
		fmDDAmplifierFault OBJECT-TYPE
			SYNTAX FaultOK
			MAX-ACCESS read-only
			STATUS current
			DESCRIPTION
				"Dual drive. Fault state of amplifier 
				
				(0) undefined
				(1) fault
				(2) ok"
			::= { fmDDGeneral 5 }

		
		-- 1.3.6.1.4.1.19831.1.1.3.4.1.6
		fmDDAmplifierWarning OBJECT-TYPE
			SYNTAX WarningOK
			MAX-ACCESS read-only
			STATUS current
			DESCRIPTION
				"Dual drive. Warning state of amplifier 
				
				(0) undefined
				(1) warning
				(2) ok"
			::= { fmDDGeneral 6 }

		
		-- 1.3.6.1.4.1.19831.1.1.3.4.1.7
		fmDDActiveExciter OBJECT-TYPE
			SYNTAX INTEGER
				{
				undefined(0),
				exciterA(1),
				exciterB(2)
				}
			MAX-ACCESS read-only
			STATUS current
			DESCRIPTION
				"Dual drive. Active exciter 
				
				"
			::= { fmDDGeneral 7 }

		
		-- 1.3.6.1.4.1.19831.1.1.3.4.1.8
		fmDDLocalMode OBJECT-TYPE
			SYNTAX LocalRemote
			MAX-ACCESS read-only
			STATUS current
			DESCRIPTION
				"Dual drive. Local mode
				
				(0) undefined
				(1) local
				(2) remote"
			::= { fmDDGeneral 8 }

		
		-- 1.3.6.1.4.1.19831.1.1.3.4.1.9
		fmDDControlUnitFault OBJECT-TYPE
			SYNTAX FaultOK
			MAX-ACCESS read-only
			STATUS current
			DESCRIPTION
				"Dual drive. State of the control unit
				
				(0) undefined
				(1) fault
				(2) ok"
			::= { fmDDGeneral 9 }

		
		-- 1.3.6.1.4.1.19831.1.1.3.4.1.10
		fmDDSwitchOverMode OBJECT-TYPE
			SYNTAX SelectManualAuto
			MAX-ACCESS read-write
			STATUS current
			DESCRIPTION
				"Dual drive. Switch over mode: manual or automatic
				
				(0) undefined
				(1) manual 
				(2) automatic"
			::= { fmDDGeneral 10 }

		
		-- 1.3.6.1.4.1.19831.1.1.3.4.1.11
		fmDDSwitchOverReady OBJECT-TYPE
			SYNTAX ReadyNotReady
			MAX-ACCESS read-only
			STATUS current
			DESCRIPTION
				"Dual drive. State of the dual drive switch over unit
				
				(0) undefined
				(1) ready
				(2) not ready"
			::= { fmDDGeneral 11 }

		
		-- 1.3.6.1.4.1.19831.1.1.3.4.1.12
		fmDDSwitchOverExecuted OBJECT-TYPE
			SYNTAX ExecutedNotExecuted
			MAX-ACCESS read-only
			STATUS current
			DESCRIPTION
				"Dual drive. Showsif the reserve switch over unit it has executed
				
				(0) undefined
				(1) executed
				(2) not executed"
			::= { fmDDGeneral 12 }

		
		-- 1.3.6.1.4.1.19831.1.1.3.4.1.13
		fmDDSwitchOverFault OBJECT-TYPE
			SYNTAX FaultOK
			MAX-ACCESS read-only
			STATUS current
			DESCRIPTION
				"Dual drive. fault state of the switsch over unit
				
				(0) undefined
				(1) faulty
				(2) ok"
			::= { fmDDGeneral 13 }

		
-- fm dual drive exciter A
		-- 1.3.6.1.4.1.19831.1.1.3.4.2
		fmDDExciterA OBJECT IDENTIFIER ::= { fmDualDrive 2 }

		
--   
		-- 1.3.6.1.4.1.19831.1.1.3.4.2.1
		fmDDExciterALocalMode OBJECT-TYPE
			SYNTAX LocalRemote
			MAX-ACCESS read-only
			STATUS current
			DESCRIPTION
				"Dual drive. Local mode of exciter A
				
				(0) undefined
				(1) local
				(2) remote"
			::= { fmDDExciterA 1 }

		
--   
		-- 1.3.6.1.4.1.19831.1.1.3.4.2.2
		fmDDExciterAFault OBJECT-TYPE
			SYNTAX FaultOK
			MAX-ACCESS read-only
			STATUS current
			DESCRIPTION
				"Dual drive. Fault state of exciter A
				
				(0) undefined
				(1) fault
				(2) ok"
			::= { fmDDExciterA 2 }

		
--  
		-- 1.3.6.1.4.1.19831.1.1.3.4.2.3
		fmDDExciterAWarning OBJECT-TYPE
			SYNTAX WarningOK
			MAX-ACCESS read-only
			STATUS current
			DESCRIPTION
				"Dual drive.Warning state of exciter A 
				
				(0) undefined
				(1) warning
				(2) ok"
			::= { fmDDExciterA 3 }

		
--  fm dual drive exciter B 
		-- 1.3.6.1.4.1.19831.1.1.3.4.3
		fmDDExciterB OBJECT IDENTIFIER ::= { fmDualDrive 3 }

		
--  
		-- 1.3.6.1.4.1.19831.1.1.3.4.3.1
		fmDDExciterBLocalMode OBJECT-TYPE
			SYNTAX LocalRemote
			MAX-ACCESS read-only
			STATUS current
			DESCRIPTION
				"Dual drive. Local mode of exciter B
				
				(0) undefined
				(1) local
				(2) remote"
			::= { fmDDExciterB 1 }

		
--   
		-- 1.3.6.1.4.1.19831.1.1.3.4.3.2
		fmDDExciterBFault OBJECT-TYPE
			SYNTAX FaultOK
			MAX-ACCESS read-only
			STATUS current
			DESCRIPTION
				"Dual drive. Fault state of exciter B
				
				(0) undefined
				(1) fault
				(2) ok"
			::= { fmDDExciterB 2 }

		
--   
		-- 1.3.6.1.4.1.19831.1.1.3.4.3.3
		fmDDExciterBWarning OBJECT-TYPE
			SYNTAX WarningOK
			MAX-ACCESS read-only
			STATUS current
			DESCRIPTION
				"Dual drive. Warning state of exciter B 
				
				(0) undefined
				(1) warning
				(2) ok"
			::= { fmDDExciterB 3 }

		
-- fm dual drive: switch for Event
		-- 1.3.6.1.4.1.19831.1.1.3.4.4
		fmDDEventEnable OBJECT IDENTIFIER ::= { fmDualDrive 4 }

		
-- fm dual drive general: switch for Event
		-- 1.3.6.1.4.1.19831.1.1.3.4.4.1
		fmDDEventEnableGeneral OBJECT IDENTIFIER ::= { fmDDEventEnable 1 }

		
		-- 1.3.6.1.4.1.19831.1.1.3.4.4.1.1
		fmDDPreselectionExciterEnable OBJECT-TYPE
			SYNTAX TruthValue
			MAX-ACCESS read-write
			STATUS current
			DESCRIPTION
				"Description. Enable/Disable switch for fmDDPreselectionExciter"
			::= { fmDDEventEnableGeneral 1 }

		
		-- 1.3.6.1.4.1.19831.1.1.3.4.4.1.2
		fmDDTransmitterOpModeEnable OBJECT-TYPE
			SYNTAX TruthValue
			MAX-ACCESS read-write
			STATUS current
			DESCRIPTION
				"Description. Enable/Disable switch for fmDDTransmitterOpMode event"
			::= { fmDDEventEnableGeneral 2 }

		
		-- 1.3.6.1.4.1.19831.1.1.3.4.4.1.3
		fmDDReserveControlEnable OBJECT-TYPE
			SYNTAX TruthValue
			MAX-ACCESS read-write
			STATUS current
			DESCRIPTION
				"Description. Enable/Disable switch for fmDDIReserveControl event"
			::= { fmDDEventEnableGeneral 3 }

		
		-- 1.3.6.1.4.1.19831.1.1.3.4.4.1.4
		fmDDRFPresentEnable OBJECT-TYPE
			SYNTAX TruthValue
			MAX-ACCESS read-write
			STATUS current
			DESCRIPTION
				"Description. Enable/Disable switch for fmDDRFPresent event"
			::= { fmDDEventEnableGeneral 4 }

		
		-- 1.3.6.1.4.1.19831.1.1.3.4.4.1.5
		fmDDAmplifierFaultEnable OBJECT-TYPE
			SYNTAX TruthValue
			MAX-ACCESS read-write
			STATUS current
			DESCRIPTION
				"Description. Enable/Disable switch for fmDDAmplifierFault event"
			::= { fmDDEventEnableGeneral 5 }

		
		-- 1.3.6.1.4.1.19831.1.1.3.4.4.1.6
		fmDDAmplifierWarningEnable OBJECT-TYPE
			SYNTAX TruthValue
			MAX-ACCESS read-write
			STATUS current
			DESCRIPTION
				"Description. Enable/Disable switch for fmDDAmplifierWarning event"
			::= { fmDDEventEnableGeneral 6 }

		
		-- 1.3.6.1.4.1.19831.1.1.3.4.4.1.7
		fmDDActiveExciterEnable OBJECT-TYPE
			SYNTAX TruthValue
			MAX-ACCESS read-write
			STATUS current
			DESCRIPTION
				"Description. Enable/Disable switch for fmDDActiveExciter event
				"
			::= { fmDDEventEnableGeneral 7 }

		
		-- 1.3.6.1.4.1.19831.1.1.3.4.4.1.8
		fmDDLocalModeEnable OBJECT-TYPE
			SYNTAX TruthValue
			MAX-ACCESS read-write
			STATUS current
			DESCRIPTION
				"Description. Enable/Disable switch for fmDDLocalMode event"
			::= { fmDDEventEnableGeneral 8 }

		
		-- 1.3.6.1.4.1.19831.1.1.3.4.4.1.9
		fmDDControlUnitFaultEnable OBJECT-TYPE
			SYNTAX TruthValue
			MAX-ACCESS read-write
			STATUS current
			DESCRIPTION
				"Description. Enable/Disable switch for fmDDControlUnitFault event"
			::= { fmDDEventEnableGeneral 9 }

		
		-- 1.3.6.1.4.1.19831.1.1.3.4.4.1.10
		fmDDSwitchOverModeEnable OBJECT-TYPE
			SYNTAX TruthValue
			MAX-ACCESS read-write
			STATUS current
			DESCRIPTION
				"Description. Enable/Disable switch for fmDDSwitchOverMode event"
			::= { fmDDEventEnableGeneral 10 }

		
		-- 1.3.6.1.4.1.19831.1.1.3.4.4.1.11
		fmDDSwitchOverReadyEnable OBJECT-TYPE
			SYNTAX TruthValue
			MAX-ACCESS read-write
			STATUS current
			DESCRIPTION
				"Description. Enable/Disable switch for fmDDSwitchOverReady event"
			::= { fmDDEventEnableGeneral 11 }

		
		-- 1.3.6.1.4.1.19831.1.1.3.4.4.1.12
		fmDDSwitchOverExecutedEnable OBJECT-TYPE
			SYNTAX TruthValue
			MAX-ACCESS read-write
			STATUS current
			DESCRIPTION
				"Description. Enable/Disable switch for fmDDSwitchOverExecuted event"
			::= { fmDDEventEnableGeneral 12 }

		
		-- 1.3.6.1.4.1.19831.1.1.3.4.4.1.13
		fmDDSwitchOverFaultEnable OBJECT-TYPE
			SYNTAX TruthValue
			MAX-ACCESS read-write
			STATUS current
			DESCRIPTION
				"Description. Enable/Disable switch for fmDDSwitchOverFault event"
			::= { fmDDEventEnableGeneral 13 }

		
-- fm dual drive exciter A: switch for Event
		-- 1.3.6.1.4.1.19831.1.1.3.4.4.2
		fmDDEventEnableExciterA OBJECT IDENTIFIER ::= { fmDDEventEnable 2 }

		
--   
		-- 1.3.6.1.4.1.19831.1.1.3.4.4.2.1
		fmDDExciterALocalModeEnable OBJECT-TYPE
			SYNTAX TruthValue
			MAX-ACCESS read-write
			STATUS current
			DESCRIPTION
				"Description. Enable/Disable switch for fmDDExciterALocalMode event"
			::= { fmDDEventEnableExciterA 1 }

		
--   
		-- 1.3.6.1.4.1.19831.1.1.3.4.4.2.2
		fmDDExciterAFaultEnable OBJECT-TYPE
			SYNTAX TruthValue
			MAX-ACCESS read-write
			STATUS current
			DESCRIPTION
				"Description. Enable/Disable switch for fmDDExciterAFault  event"
			::= { fmDDEventEnableExciterA 2 }

		
--  
		-- 1.3.6.1.4.1.19831.1.1.3.4.4.2.3
		fmDDExciterAWarningEnable OBJECT-TYPE
			SYNTAX TruthValue
			MAX-ACCESS read-write
			STATUS current
			DESCRIPTION
				"Description. Enable/Disable switch for fmDDExciterAWarning event"
			::= { fmDDEventEnableExciterA 3 }

		
-- fm dual drive exciter B: switch for Event
		-- 1.3.6.1.4.1.19831.1.1.3.4.4.3
		fmDDEventEnableExciterB OBJECT IDENTIFIER ::= { fmDDEventEnable 3 }

		
--   
		-- 1.3.6.1.4.1.19831.1.1.3.4.4.3.1
		fmDDExciterBLocalModeEnable OBJECT-TYPE
			SYNTAX TruthValue
			MAX-ACCESS read-write
			STATUS current
			DESCRIPTION
				"Description. Enable/Disable switch for fmDDExciterBLocalMode event"
			::= { fmDDEventEnableExciterB 1 }

		
--   
		-- 1.3.6.1.4.1.19831.1.1.3.4.4.3.2
		fmDDExciterBFaultEnable OBJECT-TYPE
			SYNTAX TruthValue
			MAX-ACCESS read-write
			STATUS current
			DESCRIPTION
				"Description. Enable/Disable switch for fmDDExciterBFault event"
			::= { fmDDEventEnableExciterB 2 }

		
--   
		-- 1.3.6.1.4.1.19831.1.1.3.4.4.3.3
		fmDDExciterBWarningEnable OBJECT-TYPE
			SYNTAX TruthValue
			MAX-ACCESS read-write
			STATUS current
			DESCRIPTION
				"Description. Enable/Disable switch for fmDDExciterBWarning event"
			::= { fmDDEventEnableExciterB 3 }

		
-- fm dual drive event priority
		-- 1.3.6.1.4.1.19831.1.1.3.4.5
		fmDDEventPriority OBJECT IDENTIFIER ::= { fmDualDrive 5 }

		
-- fm dual drive: general event priority
		-- 1.3.6.1.4.1.19831.1.1.3.4.5.1
		fmDDEventPriorityGeneral OBJECT IDENTIFIER ::= { fmDDEventPriority 1 }

		
		-- 1.3.6.1.4.1.19831.1.1.3.4.5.1.1
		fmDDPreselectionExciterPriority OBJECT-TYPE
			SYNTAX Unsigned32
			MAX-ACCESS read-write
			STATUS current
			DESCRIPTION
				"Description. Priority for fmDDPreselectionExciter event"
			::= { fmDDEventPriorityGeneral 1 }

		
		-- 1.3.6.1.4.1.19831.1.1.3.4.5.1.2
		fmDDTransmitterOpModePriority OBJECT-TYPE
			SYNTAX Unsigned32
			MAX-ACCESS read-write
			STATUS current
			DESCRIPTION
				"Description. Priority for fmDDTransmitterOpMode event"
			::= { fmDDEventPriorityGeneral 2 }

		
		-- 1.3.6.1.4.1.19831.1.1.3.4.5.1.3
		fmDDReserveControlPriority OBJECT-TYPE
			SYNTAX Unsigned32
			MAX-ACCESS read-write
			STATUS current
			DESCRIPTION
				"Description. Priority for fmDDReserveControl event"
			::= { fmDDEventPriorityGeneral 3 }

		
		-- 1.3.6.1.4.1.19831.1.1.3.4.5.1.4
		fmDDRFPresentPriority OBJECT-TYPE
			SYNTAX Unsigned32
			MAX-ACCESS read-write
			STATUS current
			DESCRIPTION
				"Description. Priority for fmDDRFPresent event"
			::= { fmDDEventPriorityGeneral 4 }

		
		-- 1.3.6.1.4.1.19831.1.1.3.4.5.1.5
		fmDDAmplifierFaultPriority OBJECT-TYPE
			SYNTAX Unsigned32
			MAX-ACCESS read-write
			STATUS current
			DESCRIPTION
				"Description. Priority for fmDDAmplifierFault event"
			::= { fmDDEventPriorityGeneral 5 }

		
		-- 1.3.6.1.4.1.19831.1.1.3.4.5.1.6
		fmDDAmplifierWarningPriority OBJECT-TYPE
			SYNTAX Unsigned32
			MAX-ACCESS read-write
			STATUS current
			DESCRIPTION
				"Description. Priority for fmDDAmplifierWarning event"
			::= { fmDDEventPriorityGeneral 6 }

		
		-- 1.3.6.1.4.1.19831.1.1.3.4.5.1.7
		fmDDActiveExciterPriority OBJECT-TYPE
			SYNTAX Unsigned32
			MAX-ACCESS read-write
			STATUS current
			DESCRIPTION
				"Description. Priority for fmDDActiveExciter event"
			::= { fmDDEventPriorityGeneral 7 }

		
		-- 1.3.6.1.4.1.19831.1.1.3.4.5.1.8
		fmDDLocalModePriority OBJECT-TYPE
			SYNTAX Unsigned32
			MAX-ACCESS read-write
			STATUS current
			DESCRIPTION
				"Description. Priority for fmDDLocalMode event"
			::= { fmDDEventPriorityGeneral 8 }

		
		-- 1.3.6.1.4.1.19831.1.1.3.4.5.1.9
		fmDDControlUnitFaultPriority OBJECT-TYPE
			SYNTAX Unsigned32
			MAX-ACCESS read-write
			STATUS current
			DESCRIPTION
				"Description. Priority for fmDDControlUnitFault event"
			::= { fmDDEventPriorityGeneral 9 }

		
		-- 1.3.6.1.4.1.19831.1.1.3.4.5.1.10
		fmDDSwitchOverModePriority OBJECT-TYPE
			SYNTAX Unsigned32
			MAX-ACCESS read-write
			STATUS current
			DESCRIPTION
				"Description. Priority for fmDDSwitchOverMode event"
			::= { fmDDEventPriorityGeneral 10 }

		
		-- 1.3.6.1.4.1.19831.1.1.3.4.5.1.11
		fmDDSwitchOverReadyPriority OBJECT-TYPE
			SYNTAX Unsigned32
			MAX-ACCESS read-write
			STATUS current
			DESCRIPTION
				"Description. Priority for fmDDSwitchOverReady event"
			::= { fmDDEventPriorityGeneral 11 }

		
		-- 1.3.6.1.4.1.19831.1.1.3.4.5.1.12
		fmDDSwitchOverExecutedPriority OBJECT-TYPE
			SYNTAX Unsigned32
			MAX-ACCESS read-write
			STATUS current
			DESCRIPTION
				"Description. Priority for fmDDSwitchOverExecuted event"
			::= { fmDDEventPriorityGeneral 12 }

		
		-- 1.3.6.1.4.1.19831.1.1.3.4.5.1.13
		fmDDSwitchOverFaultPriority OBJECT-TYPE
			SYNTAX Unsigned32
			MAX-ACCESS read-write
			STATUS current
			DESCRIPTION
				"Description. Priority for fmDDSwitchOverFault event"
			::= { fmDDEventPriorityGeneral 13 }

		
-- fm dual drive: ecxiter A event priority
		-- 1.3.6.1.4.1.19831.1.1.3.4.5.2
		fmDDEventPriorityExciterA OBJECT IDENTIFIER ::= { fmDDEventPriority 2 }

		
--   
		-- 1.3.6.1.4.1.19831.1.1.3.4.5.2.1
		fmDDExciterALocalModePriority OBJECT-TYPE
			SYNTAX Unsigned32
			MAX-ACCESS read-write
			STATUS current
			DESCRIPTION
				"Description. Priority for fmDDExciterALocalMode event event"
			::= { fmDDEventPriorityExciterA 1 }

		
--   
		-- 1.3.6.1.4.1.19831.1.1.3.4.5.2.2
		fmDDExciterAFaultPriority OBJECT-TYPE
			SYNTAX Unsigned32
			MAX-ACCESS read-write
			STATUS current
			DESCRIPTION
				"Description. Priority for fmDDExciterAFault event"
			::= { fmDDEventPriorityExciterA 2 }

		
--  
		-- 1.3.6.1.4.1.19831.1.1.3.4.5.2.3
		fmDDExciterAWarningPriority OBJECT-TYPE
			SYNTAX Unsigned32
			MAX-ACCESS read-write
			STATUS current
			DESCRIPTION
				"Description. Priority for fmDDExciterAWarning event"
			::= { fmDDEventPriorityExciterA 3 }

		
-- fm dual drive: exciter B event priority
		-- 1.3.6.1.4.1.19831.1.1.3.4.5.3
		fmDDEventPriorityExciterB OBJECT IDENTIFIER ::= { fmDDEventPriority 3 }

		
--   
		-- 1.3.6.1.4.1.19831.1.1.3.4.5.3.1
		fmDDExciterBLocalModePriority OBJECT-TYPE
			SYNTAX Unsigned32
			MAX-ACCESS read-write
			STATUS current
			DESCRIPTION
				"Description. Priority for fmDDExciterBLocalMode event event"
			::= { fmDDEventPriorityExciterB 1 }

		
--   
		-- 1.3.6.1.4.1.19831.1.1.3.4.5.3.2
		fmDDExciterBFaultPriority OBJECT-TYPE
			SYNTAX Unsigned32
			MAX-ACCESS read-write
			STATUS current
			DESCRIPTION
				"Description. Priority for fmDDExciterBFault event"
			::= { fmDDEventPriorityExciterB 2 }

		
--   
		-- 1.3.6.1.4.1.19831.1.1.3.4.5.3.3
		fmDDExciterBWarningPriority OBJECT-TYPE
			SYNTAX Unsigned32
			MAX-ACCESS read-write
			STATUS current
			DESCRIPTION
				"Description. Priority for fmDDExciterBWarning event"
			::= { fmDDEventPriorityExciterB 3 }

		
		-- 1.3.6.1.4.1.19831.1.1.3.4.6
		groupsDD OBJECT IDENTIFIER ::= { fmDualDrive 6 }

		
-- events
		-- 1.3.6.1.4.1.19831.1.1.3.4.6.1
		eventGroupDD NOTIFICATION-GROUP
			NOTIFICATIONS { fmDDTransmitterOpModeEvent, fmDDReserveControlEvent, fmDDRFPresentEvent, fmDDAmplifierFaultEvent, fmDDAmplifierWarningEvent, 
				fmDDActiveExciterEvent, fmDDLocalModeEvent, fmDDControlUnitFaultEvent, fmDDSwitchOverModeEvent, fmDDSwitchOverReadyEvent, 
				fmDDSwitchOverExecutedEvent, fmDDSwitchOverFaultEvent, fmDDExciterAFaultEvent, fmDDExciterAWarningEvent, fmDDExciterBFaultEvent, 
				fmDDExciterBWarningEvent, fmDDExciterALocalModeEvent, fmDDExciterBLocalModeEvent, fmDDPreselectionExciterEvent }
			STATUS current
			DESCRIPTION 
				"Description."
			::= { groupsDD 1 }

		
-- objecs
		-- 1.3.6.1.4.1.19831.1.1.3.4.6.2
		objectGroupDD OBJECT-GROUP
			OBJECTS { fmDDTransmitterOpMode, fmDDReserveControl, fmDDRFPresent, fmDDAmplifierFault, fmDDAmplifierWarning, 
				fmDDActiveExciter, fmDDLocalMode, fmDDControlUnitFault, fmDDSwitchOverMode, fmDDSwitchOverReady, 
				fmDDSwitchOverExecuted, fmDDSwitchOverFault, fmDDExciterAFault, fmDDExciterAWarning, fmDDExciterBFault, 
				fmDDExciterBWarning, fmDDTransmitterOpModeEnable, fmDDReserveControlEnable, fmDDRFPresentEnable, fmDDAmplifierFaultEnable, 
				fmDDAmplifierWarningEnable, fmDDActiveExciterEnable, fmDDLocalModeEnable, fmDDControlUnitFaultEnable, fmDDSwitchOverModeEnable, 
				fmDDSwitchOverReadyEnable, fmDDSwitchOverExecutedEnable, fmDDSwitchOverFaultEnable, fmDDExciterAFaultEnable, fmDDExciterAWarningEnable, 
				fmDDExciterBFaultEnable, fmDDExciterBWarningEnable, fmDDTransmitterOpModePriority, fmDDReserveControlPriority, fmDDRFPresentPriority, 
				fmDDAmplifierFaultPriority, fmDDAmplifierWarningPriority, fmDDActiveExciterPriority, fmDDLocalModePriority, fmDDControlUnitFaultPriority, 
				fmDDSwitchOverModePriority, fmDDSwitchOverReadyPriority, fmDDSwitchOverExecutedPriority, fmDDSwitchOverFaultPriority, fmDDExciterAFaultPriority, 
				fmDDExciterAWarningPriority, fmDDExciterBFaultPriority, fmDDPreselectionExciter, fmDDPreselectionExciterEnable, fmDDPreselectionExciterPriority, 
				fmDDExciterBWarningPriority, fmDDExciterALocalMode, fmDDExciterBLocalMode, fmDDExciterALocalModeEnable, fmDDExciterBLocalModeEnable, 
				fmDDExciterALocalModePriority, fmDDExciterBLocalModePriority }
			STATUS current
			DESCRIPTION 
				"Description.dual drive: object group"
			::= { groupsDD 2 }

		
		-- 1.3.6.1.4.1.19831.1.1.3.4.7
		complianceDD OBJECT IDENTIFIER ::= { fmDualDrive 7 }

		
		-- 1.3.6.1.4.1.19831.1.1.3.4.7.1
		fmDualDriveCompliance MODULE-COMPLIANCE
			STATUS current
			DESCRIPTION 
				"Compliance Statement"
			MODULE -- this module
				MANDATORY-GROUPS { eventGroupDD, objectGroupDD }
			::= { complianceDD 1 }

		
	
	END

--
-- IRT-FM-DUALDRIVE-MIB.my
--
