ACOS-FW-RESOURCE-USAGE-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwResourceUsageModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwResourceUsageModule OID for ACOS"
				::=  {  acosSchema 489 }

resourceUsage		 OBJECT IDENTIFIER ::= { fwResourceUsageModule 1}

resourceUsageOperTable OBJECT-TYPE
	 SYNTAX SEQUENCE OF ResourceUsageOperEntry
	 MAX-ACCESS not-accessible
	 STATUS current
	 DESCRIPTION
		 "Firewall resource usage from object 'fw.resource-usage'"
	::= {resourceUsage 2}

resourceUsageOperEntry OBJECT-TYPE
	SYNTAX ResourceUsageOperEntry
	MAX-ACCESS not-accessible
	STATUS current
	DESCRIPTION
		"The resourceUsageOper entry"
	INDEX {
		resourceUsageOperSlotId
	}
	::= { resourceUsageOperTable 1 }

ResourceUsageOperEntry ::=
	SEQUENCE {
		resourceUsageOperSlotId Integer32,
		resourceUsageOperFwObjectCurrentCount	 Integer32,
		resourceUsageOperFwObjectTotalCount	 Integer32,
		resourceUsageOperFwObjectGroupCurrentCount	 Integer32,
		resourceUsageOperFwObjectGroupTotalCount	 Integer32,
		resourceUsageOperFwRuleSetCurrentCount	 Integer32,
		resourceUsageOperFwRuleSetTotalCount	 Integer32,
		resourceUsageOperFwRuleCurrentCount	 Integer32,
		resourceUsageOperFwRuleTotalCount	 Integer32,
		resourceUsageOperFwZoneCurrentCount	 Integer32,
		resourceUsageOperFwZoneTotalCount	 Integer32,
		resourceUsageOperFwIpRangeCurrentCount	 Integer32,
		resourceUsageOperFwIpRangeTotalCount	 Integer32,
		resourceUsageOperFwHelperSessionsCurrentCount	 Integer32,
		resourceUsageOperFwHelperSessionsTotalCount	 Integer32,
		resourceUsageOperRadiusTableCurrentCount	 Integer32,
		resourceUsageOperRadiusTableTotalCount	 Integer32,
		resourceUsageOperClausePerObjGrpCurrentCount	 DisplayString,
		resourceUsageOperClausePerObjGrpTotalCount	 Integer32,
		resourceUsageOperObject	 DisplayString,
		resourceUsageOperObjectGroup	 DisplayString,
		resourceUsageOperRuleSet	 DisplayString,
		resourceUsageOperRule	 DisplayString,
		resourceUsageOperZone	 DisplayString,
		resourceUsageOperIpRange	 DisplayString,
		resourceUsageOperHelperSessions	 DisplayString,
		resourceUsageOperRadiusTableSize	 DisplayString,
		resourceUsageOperClausePerObjGrp	 DisplayString
	}

resourceUsageOperSlotId OBJECT-TYPE
	 SYNTAX Integer32
	 MAX-ACCESS read-only
	 STATUS current
	 DESCRIPTION
		 ""
	::= { resourceUsageOperEntry 1 }

resourceUsageOperFwObjectCurrentCount OBJECT-TYPE
	 SYNTAX Integer32
	 MAX-ACCESS read-only
	 STATUS current
	 DESCRIPTION
		 "fw-object-current-count"
	::= { resourceUsageOperEntry 2 }

resourceUsageOperFwObjectTotalCount OBJECT-TYPE
	 SYNTAX Integer32
	 MAX-ACCESS read-only
	 STATUS current
	 DESCRIPTION
		 "fw-object-total-count"
	::= { resourceUsageOperEntry 3 }

resourceUsageOperFwObjectGroupCurrentCount OBJECT-TYPE
	 SYNTAX Integer32
	 MAX-ACCESS read-only
	 STATUS current
	 DESCRIPTION
		 "fw-object-group-current-count"
	::= { resourceUsageOperEntry 4 }

resourceUsageOperFwObjectGroupTotalCount OBJECT-TYPE
	 SYNTAX Integer32
	 MAX-ACCESS read-only
	 STATUS current
	 DESCRIPTION
		 "fw-object-group-total-count"
	::= { resourceUsageOperEntry 5 }

resourceUsageOperFwRuleSetCurrentCount OBJECT-TYPE
	 SYNTAX Integer32
	 MAX-ACCESS read-only
	 STATUS current
	 DESCRIPTION
		 "fw-rule-set-current-count"
	::= { resourceUsageOperEntry 6 }

resourceUsageOperFwRuleSetTotalCount OBJECT-TYPE
	 SYNTAX Integer32
	 MAX-ACCESS read-only
	 STATUS current
	 DESCRIPTION
		 "fw-rule-set-total-count"
	::= { resourceUsageOperEntry 7 }

resourceUsageOperFwRuleCurrentCount OBJECT-TYPE
	 SYNTAX Integer32
	 MAX-ACCESS read-only
	 STATUS current
	 DESCRIPTION
		 "fw-rule-current-count"
	::= { resourceUsageOperEntry 8 }

resourceUsageOperFwRuleTotalCount OBJECT-TYPE
	 SYNTAX Integer32
	 MAX-ACCESS read-only
	 STATUS current
	 DESCRIPTION
		 "fw-rule-total-count"
	::= { resourceUsageOperEntry 9 }

resourceUsageOperFwZoneCurrentCount OBJECT-TYPE
	 SYNTAX Integer32
	 MAX-ACCESS read-only
	 STATUS current
	 DESCRIPTION
		 "fw-zone-current-count"
	::= { resourceUsageOperEntry 10 }

resourceUsageOperFwZoneTotalCount OBJECT-TYPE
	 SYNTAX Integer32
	 MAX-ACCESS read-only
	 STATUS current
	 DESCRIPTION
		 "fw-zone-total-count"
	::= { resourceUsageOperEntry 11 }

resourceUsageOperFwIpRangeCurrentCount OBJECT-TYPE
	 SYNTAX Integer32
	 MAX-ACCESS read-only
	 STATUS current
	 DESCRIPTION
		 "fw-ip-range-current-count"
	::= { resourceUsageOperEntry 12 }

resourceUsageOperFwIpRangeTotalCount OBJECT-TYPE
	 SYNTAX Integer32
	 MAX-ACCESS read-only
	 STATUS current
	 DESCRIPTION
		 "fw-ip-range-total-count"
	::= { resourceUsageOperEntry 13 }

resourceUsageOperFwHelperSessionsCurrentCount OBJECT-TYPE
	 SYNTAX Integer32
	 MAX-ACCESS read-only
	 STATUS current
	 DESCRIPTION
		 "fw-helper-sessions-current-count"
	::= { resourceUsageOperEntry 14 }

resourceUsageOperFwHelperSessionsTotalCount OBJECT-TYPE
	 SYNTAX Integer32
	 MAX-ACCESS read-only
	 STATUS current
	 DESCRIPTION
		 "fw-helper-sessions-total-count"
	::= { resourceUsageOperEntry 15 }

resourceUsageOperRadiusTableCurrentCount OBJECT-TYPE
	 SYNTAX Integer32
	 MAX-ACCESS read-only
	 STATUS current
	 DESCRIPTION
		 "radius-table-current-count"
	::= { resourceUsageOperEntry 16 }

resourceUsageOperRadiusTableTotalCount OBJECT-TYPE
	 SYNTAX Integer32
	 MAX-ACCESS read-only
	 STATUS current
	 DESCRIPTION
		 "radius-table-total-count"
	::= { resourceUsageOperEntry 17 }

resourceUsageOperClausePerObjGrpCurrentCount OBJECT-TYPE
	 SYNTAX DisplayString
	 MAX-ACCESS read-only
	 STATUS current
	 DESCRIPTION
		 "clause-per-obj-grp-current-count"
	::= { resourceUsageOperEntry 18 }

resourceUsageOperClausePerObjGrpTotalCount OBJECT-TYPE
	 SYNTAX Integer32
	 MAX-ACCESS read-only
	 STATUS current
	 DESCRIPTION
		 "clause-per-obj-grp-total-count"
	::= { resourceUsageOperEntry 19 }

resourceUsageOperObject OBJECT-TYPE
	 SYNTAX DisplayString
	 MAX-ACCESS read-only
	 STATUS current
	 DESCRIPTION
		 "object"
	::= { resourceUsageOperEntry 20 }

resourceUsageOperObjectGroup OBJECT-TYPE
	 SYNTAX DisplayString
	 MAX-ACCESS read-only
	 STATUS current
	 DESCRIPTION
		 "object-group"
	::= { resourceUsageOperEntry 21 }

resourceUsageOperRuleSet OBJECT-TYPE
	 SYNTAX DisplayString
	 MAX-ACCESS read-only
	 STATUS current
	 DESCRIPTION
		 "rule-set"
	::= { resourceUsageOperEntry 22 }

resourceUsageOperRule OBJECT-TYPE
	 SYNTAX DisplayString
	 MAX-ACCESS read-only
	 STATUS current
	 DESCRIPTION
		 "rule"
	::= { resourceUsageOperEntry 23 }

resourceUsageOperZone OBJECT-TYPE
	 SYNTAX DisplayString
	 MAX-ACCESS read-only
	 STATUS current
	 DESCRIPTION
		 "zone"
	::= { resourceUsageOperEntry 24 }

resourceUsageOperIpRange OBJECT-TYPE
	 SYNTAX DisplayString
	 MAX-ACCESS read-only
	 STATUS current
	 DESCRIPTION
		 "ip-range"
	::= { resourceUsageOperEntry 25 }

resourceUsageOperHelperSessions OBJECT-TYPE
	 SYNTAX DisplayString
	 MAX-ACCESS read-only
	 STATUS current
	 DESCRIPTION
		 "helper-sessions"
	::= { resourceUsageOperEntry 26 }

resourceUsageOperRadiusTableSize OBJECT-TYPE
	 SYNTAX DisplayString
	 MAX-ACCESS read-only
	 STATUS current
	 DESCRIPTION
		 "radius-table-size"
	::= { resourceUsageOperEntry 27 }

resourceUsageOperClausePerObjGrp OBJECT-TYPE
	 SYNTAX DisplayString
	 MAX-ACCESS read-only
	 STATUS current
	 DESCRIPTION
		 "clause-per-obj-grp"
	::= { resourceUsageOperEntry 28 }

END
