--          *****************************
--          *                           *
--          *         ONEOS MIB         *
--          *                           *
--          *****************************
--
--          ONEOS_MIB_STD_V05.1.R005_E001
--
--          Creation date : 14/03/2003
--
--          
--
--          Compatibility with ONEOS_V32
--

ONEACCESS-PING-MIB DEFINITIONS ::=BEGIN

IMPORTS

    MODULE-IDENTITY, OBJECT-TYPE, Integer32,
    Unsigned32, mib-2,
    NOTIFICATION-TYPE, OBJECT-IDENTITY
        FROM SNMPv2-SMI                  -- RFC2578
    MODULE-COMPLIANCE, OBJECT-GROUP,
    NOTIFICATION-GROUP
        FROM SNMPv2-CONF                 -- RFC2580
    pingCtlOwnerIndex,pingCtlTestName  
	FROM DISMAN-PING-MIB
    oneAccess,oacExpIMPing,oacMIBModules	  
	FROM ONEACCESS-GLOBAL-REG;



oacPingMIBModule MODULE-IDENTITY
        LAST-UPDATED    "201106150000Z"
        ORGANIZATION    " OneAccess "
         CONTACT-INFO
           "Pascal KESTELOOT
            Postal: ONE ACCESS
                    381 Avenue du Général de Gaulle
                    92140 Clamart, France
		    FRANCE

            Tel: (+33) 01 41 87 70 00
            Fax: (+33) 01 41 87 74 00

            E-mail: pascal.kesteloot@oneaccess-net.com"

         DESCRIPTION
                        "Contact updated"
        REVISION        "201106150000Z"
        
		DESCRIPTION
			"Fixed Minor correction added last revision."
		REVISION	"201007080001Z"
			
         DESCRIPTION
              "This MIB module describes proprietary extensions to DISMAN-PING-MIB."
	
	::= { oacMIBModules 6601 }

 oacPingNotifications              OBJECT IDENTIFIER ::= { oacExpIMPing 0 }
 oacPingObjects                    OBJECT IDENTIFIER ::= { oacExpIMPing 1 }
 oacPingConformance                OBJECT IDENTIFIER ::= { oacExpIMPing 2 }


oacPingResultsTable OBJECT-TYPE
    SYNTAX      SEQUENCE OF OacPingResultsEntry
    MAX-ACCESS  not-accessible
    STATUS      current
    DESCRIPTION
        "Defines the Ping Results Table for providing
        the capability of performing ping operations at
        a remote host.  This table contains objects outside 
	the scope of RFC2925.

        An entry is added to the oacPingResultsTable when an
        pingCtlEntry is started by successful transition
        of its pingCtlAdminStatus object to enabled(1).
        An entry is removed from the oaPingResultsTable when
        its corresponding pingCtlEntry is deleted."
   ::= { oacPingObjects 3 }

 oacPingResultsEntry OBJECT-TYPE
    SYNTAX      OacPingResultsEntry
    MAX-ACCESS  not-accessible
    STATUS      current
    DESCRIPTION
        "Defines an entry in the oacPingResultsTable.  The
        oacPingResultsTable has the same indexing as the
        pingCtlTable in order for a oaPingResultsEntry to
        correspond to the pingCtlEntry that caused it to
        be created."
    INDEX {
             pingCtlOwnerIndex,
             pingCtlTestName
          }
    ::= { oacPingResultsTable 1 }

 OacPingResultsEntry ::=
    SEQUENCE {
        oacPingJitterSamples      	Unsigned32,
	oacPingResultsMinJitter        	Unsigned32,
	oacPingResultsMaxJitter        	Unsigned32,
	oacPingResultsAverageJitter    	Unsigned32
     }

oacPingJitterSamples OBJECT-TYPE
    SYNTAX      Unsigned32 
    MAX-ACCESS  read-only
    STATUS      current
    DESCRIPTION
        "Reflects the number of jitter samples taken, 
	it is usually one less than pingResultsProbeResponses.
	If 0, then the values of oacPingResultsMinJitter, 
	oacPingResultsMaxJitter and oacPingResultsAverageJitter 
	are not valid."
    ::= { oacPingResultsEntry 1 }

 oacPingResultsMinJitter OBJECT-TYPE
    SYNTAX      Unsigned32
    UNITS       "microseconds"
    MAX-ACCESS  read-only
    STATUS      current
    DESCRIPTION
        "The minimum ping jitter value measured."
    ::= { oacPingResultsEntry 2 }

oacPingResultsMaxJitter OBJECT-TYPE
    SYNTAX      Unsigned32
    UNITS       "microseconds"
    MAX-ACCESS  read-only
    STATUS      current
    DESCRIPTION
        "The maximum ping jitter value measured."
    ::= { oacPingResultsEntry 3 }

oacPingResultsAverageJitter OBJECT-TYPE
    SYNTAX      Unsigned32
    UNITS       "microseconds"
    MAX-ACCESS  read-only
    STATUS      current
    DESCRIPTION
        "The average ping jitter value measured."
    ::= { oacPingResultsEntry 4 }

oacPingCompliances OBJECT IDENTIFIER ::= { oacPingConformance 1 }
oacPingGroups      OBJECT IDENTIFIER ::= { oacPingConformance 2 }

 -- Compliance statements

 oacPingCompliance MODULE-COMPLIANCE
    STATUS  current
    DESCRIPTION
            "The compliance statement for the ONEACCESS-PING-MIB."
    MODULE   -- this module
        MANDATORY-GROUPS {
                            oacPingGroup
                          }
    ::= { oacPingCompliances 1 }

 -- MIB groupings

 oacPingGroup OBJECT-GROUP
   OBJECTS {
        oacPingJitterSamples,
	oacPingResultsMinJitter,
	oacPingResultsMaxJitter,
	oacPingResultsAverageJitter
           }
   STATUS  current
   DESCRIPTION
       "The group of objects that comprise the OneAccess extensions 
	to the remote ping capability in RFC2925."
    ::= { oacPingGroups 1 }

END
--
