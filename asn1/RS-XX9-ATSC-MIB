--
-- RS-XX9-ATSC-MIB.mi2
-- MIB generated by MG-SOFT Visual MIB Builder 2010 Version 8.0  Build 403
-- Thursday, April 02, 2015 at 07:49:02
--

-- *****************************************************************************
-- *****************************************************************************
-- **                                                                           
-- **  COPYRIGHT      (c) 2012 Rohde & Schwarz GmbH & Co. KG                    
-- **                          Muehldorfstrasse 15                              
-- **    R & S                 D-81671 Muenchen                                 
-- **                                                                           
-- *****************************************************************************
-- **                                                                           
-- **  MODULE         RS-XX9-ATSC-MIB                                           
-- **                                                                           
-- *****************************************************************************
-- *****************************************************************************
-- 

    RS-XX9-ATSC-MIB DEFINITIONS ::= BEGIN
 
        IMPORTS
            commonNotificationAlarmClass            
                FROM RS-XX9-COMMON-MIB            
            rsXx9Atsc, rsXx9MibModule            
                FROM RS-XX9-SMI-MIB            
            IndexTransmitter, IndexAB, NotificationMask, NotificationPriority, NotificationState, 
            SwitchOnOff            
                FROM RS-XX9-TC-MIB            
            OBJECT-GROUP, MODULE-COMPLIANCE, NOTIFICATION-GROUP            
                FROM SNMPv2-CONF            
            Unsigned32, OBJECT-TYPE, MODULE-IDENTITY, NOTIFICATION-TYPE            
                FROM SNMPv2-SMI;
    
    
        rsXx9AtscMibModule MODULE-IDENTITY 
            LAST-UPDATED "201504020800Z"		-- April 02, 2015 at 08:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines ATSC specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB
                - RS-XX9-COMMON-MIB     - mandatory for this MIB"
            REVISION "201504020800Z"		-- April 02, 2015 at 08:00 GMT
            DESCRIPTION 
                "update enum range of atscConfigurationSfnSyncMode"
            REVISION "201412221600Z"		-- December 22, 2014 at 16:00 GMT
            DESCRIPTION 
                "updated description texts
                "
            REVISION "201207261000Z"		-- July 26, 2012 at 10:00 GMT
            DESCRIPTION 
                "Preliminary revision."
            ::= { rsXx9MibModule 7 }

        
    
    
--
-- Node definitions
--
    
        rsXx9AtscNotifications OBJECT IDENTIFIER ::= { rsXx9Atsc 0 }

        
        atscEncoderSummary NOTIFICATION-TYPE
            OBJECTS { commonNotificationAlarmClass, atscStatusNotificationPriority, atscStatusNotificationState }
            STATUS current
            DESCRIPTION 
                "Encoder summary state.
                
                Possible values:
                off(2)
                fault(3)
                warning(4)
                ok(5)
                
                Notification class: fault"
            ::= { rsXx9AtscNotifications 1 }

        
        atscContentFail NOTIFICATION-TYPE
            OBJECTS { commonNotificationAlarmClass, atscStatusNotificationPriority, atscStatusNotificationState }
            STATUS current
            DESCRIPTION 
                "No mobile data in data stream.
                Available only if atscConfigurationMobileDtv is on(1).
                
                Possible values:
                warning(4)
                ok(5)
                
                Notification class: warning"
            ::= { rsXx9AtscNotifications 2 }

        
        atscTest NOTIFICATION-TYPE
            OBJECTS { commonNotificationAlarmClass, atscStatusNotificationPriority, atscStatusNotificationState }
            STATUS current
            DESCRIPTION 
                "Possible values:
                off(2)     - no test signal generation
                warning(4) - test signal generation is activated
                
                Notification class: warning"
            ::= { rsXx9AtscNotifications 3 }

        
        rsXx9AtscObjects OBJECT IDENTIFIER ::= { rsXx9Atsc 1 }

        
        atscStatus OBJECT IDENTIFIER ::= { rsXx9AtscObjects 1 }

        
        atscStatusNotificationTable OBJECT-TYPE
            SYNTAX SEQUENCE OF AtscStatusNotificationEntry
            MAX-ACCESS not-accessible
            STATUS current
            DESCRIPTION
                "The context information/configuration for the
                ATSC status notifications."
            ::= { atscStatus 1 }

        
        atscStatusNotificationEntry OBJECT-TYPE
            SYNTAX AtscStatusNotificationEntry
            MAX-ACCESS not-accessible
            STATUS current
            DESCRIPTION
                "An entry in the atscStatusNotificationTable."
            INDEX { atscStatusNotificationTxIdx, atscStatusNotificationExcIdx, atscStatusNotificationIdx }
            ::= { atscStatusNotificationTable 1 }

        
        AtscStatusNotificationEntry ::=
            SEQUENCE { 
                atscStatusNotificationTxIdx
                    IndexTransmitter,
                atscStatusNotificationExcIdx
                    IndexAB,
                atscStatusNotificationIdx
                    Unsigned32,
                atscStatusNotificationName
                    INTEGER,
                atscStatusNotificationMask
                    NotificationMask,
                atscStatusNotificationPriority
                    NotificationPriority,
                atscStatusNotificationState
                    NotificationState
             }

        atscStatusNotificationTxIdx OBJECT-TYPE
            SYNTAX IndexTransmitter
            MAX-ACCESS not-accessible
            STATUS current
            DESCRIPTION
                "The transmitter index."
            ::= { atscStatusNotificationEntry 1 }

        
        atscStatusNotificationExcIdx OBJECT-TYPE
            SYNTAX IndexAB
            MAX-ACCESS not-accessible
            STATUS current
            DESCRIPTION
                "This index distinguishes the exiters.
                Necessary if you have dual drive transmitters."
            ::= { atscStatusNotificationEntry 2 }

        
        atscStatusNotificationIdx OBJECT-TYPE
            SYNTAX Unsigned32 (1..3)
            MAX-ACCESS not-accessible
            STATUS current
            DESCRIPTION
                "The notification number as below rsXx9AtscNotifications.
                This is a helper column and therefore not-accessible."
            ::= { atscStatusNotificationEntry 3 }

        
        atscStatusNotificationName OBJECT-TYPE
            SYNTAX INTEGER
                {
                atscEncoderSummary(1),
                atscContentFail(2),
                atscTest(3)
                }
            MAX-ACCESS read-write
            STATUS current
            DESCRIPTION
                "The notification number as an enumeration.
                The enumeration correlates with the notifications under rsXx9AtscNotifications."
            ::= { atscStatusNotificationEntry 4 }

        
        atscStatusNotificationMask OBJECT-TYPE
            SYNTAX NotificationMask
            MAX-ACCESS read-write
            STATUS current
            DESCRIPTION
                "See textual convention for details."
            ::= { atscStatusNotificationEntry 5 }

        
        atscStatusNotificationPriority OBJECT-TYPE
            SYNTAX NotificationPriority
            MAX-ACCESS read-write
            STATUS current
            DESCRIPTION
                "See textual convention for details."
            ::= { atscStatusNotificationEntry 6 }

        
        atscStatusNotificationState OBJECT-TYPE
            SYNTAX NotificationState
            MAX-ACCESS read-only
            STATUS current
            DESCRIPTION
                "See textual convention for details."
            ::= { atscStatusNotificationEntry 7 }

        
        atscSetup OBJECT IDENTIFIER ::= { rsXx9AtscObjects 2 }

        
        atscConfigurationTable OBJECT-TYPE
            SYNTAX SEQUENCE OF AtscConfigurationEntry
            MAX-ACCESS not-accessible
            STATUS current
            DESCRIPTION
                "General ATSC configuration."
            ::= { atscSetup 1 }

        
        atscConfigurationEntry OBJECT-TYPE
            SYNTAX AtscConfigurationEntry
            MAX-ACCESS not-accessible
            STATUS current
            DESCRIPTION
                "An entry in the atscConfigurationTable."
            INDEX { atscConfigurationTxIdx, atscConfigurationExcIdx }
            ::= { atscConfigurationTable 1 }

        
        AtscConfigurationEntry ::=
            SEQUENCE { 
                atscConfigurationTxIdx
                    IndexTransmitter,
                atscConfigurationExcIdx
                    IndexAB,
                atscConfigurationMobileDtv
                    SwitchOnOff,
                atscConfigurationMhePID
                    Unsigned32,
                atscConfigurationMobileTxID
                    SwitchOnOff,
                atscConfigurationWatermark
                    INTEGER,
                atscConfigurationTxID
                    Unsigned32,
                atscConfigurationMarketID
                    Unsigned32,
                atscConfigurationSfnSyncMode
                    INTEGER
             }

        atscConfigurationTxIdx OBJECT-TYPE
            SYNTAX IndexTransmitter
            MAX-ACCESS not-accessible
            STATUS current
            DESCRIPTION
                "The transmitter index."
            ::= { atscConfigurationEntry 1 }

        
        atscConfigurationExcIdx OBJECT-TYPE
            SYNTAX IndexAB
            MAX-ACCESS not-accessible
            STATUS current
            DESCRIPTION
                "This index distinguishes the exiters.
                Necessary if you have dual drive transmitters."
            ::= { atscConfigurationEntry 2 }

        
        atscConfigurationMobileDtv OBJECT-TYPE
            SYNTAX SwitchOnOff
            MAX-ACCESS read-write
            STATUS current
            DESCRIPTION
                "Switch coding for mobile DTV on or off."
            ::= { atscConfigurationEntry 3 }

        
        atscConfigurationMhePID OBJECT-TYPE
            SYNTAX Unsigned32 (0..8191)
            MAX-ACCESS read-write
            STATUS current
            DESCRIPTION
                "Packet ID for mobile data stream."
            ::= { atscConfigurationEntry 4 }

        
        atscConfigurationMobileTxID OBJECT-TYPE
            SYNTAX SwitchOnOff
            MAX-ACCESS read-write
            STATUS current
            DESCRIPTION
                "Switch mobile transmitter ID on or off."
            ::= { atscConfigurationEntry 5 }

        
        atscConfigurationWatermark OBJECT-TYPE
            SYNTAX INTEGER
                {
                disabled(1),
                db21(2),
                db24(3),
                db27(4),
                db30(5),
                db33(6),
                db36(7),
                db39(8)
                }
            MAX-ACCESS read-write
            STATUS current
            DESCRIPTION
                "Level of watermark signal relative to wanted signal."
            ::= { atscConfigurationEntry 6 }

        
        atscConfigurationTxID OBJECT-TYPE
            SYNTAX Unsigned32 (0..31)
            MAX-ACCESS read-write
            STATUS current
            DESCRIPTION
                "Indicates the set transmitter address. The setting can be 
                changed here. The transmitter address allows a distinction 
                to be made between the individual transmitters in a 
                single-frequency network.
                "
            ::= { atscConfigurationEntry 7 }

        
        atscConfigurationMarketID OBJECT-TYPE
            SYNTAX Unsigned32 (0..495)
            MAX-ACCESS read-write
            STATUS current
            DESCRIPTION
                "Market ID.
                For grouping several transmitters in a single frequency network.
                All transmitters of a group must have different transmitter IDs."
            ::= { atscConfigurationEntry 8 }

        
        atscConfigurationSfnSyncMode OBJECT-TYPE
            SYNTAX INTEGER
                {
                rsMobileTcp(1),
                rsA53Tcp(2),
                a110Tcp(3),
                rsA53DummyBytes(4),
                a110DummyBytes(5)
                }
            MAX-ACCESS read-write
            STATUS current
            DESCRIPTION
                "Used to define the type of time synchronization. This switch is available 
                only after the appropriate software options have been enabled. 
                With the synchronization types 'R&S Mobile' and 'A/110', a distinction can 
                also be made as to whether the time of transmission is to be synchronized 
                primarily using data from the TCP information or using data from the dummy bytes.
                
                
                rsMobileTcp(1) - For transmitting mobile content and when using a Rohde&Schwarz 
                                           AEM100 Emission Mux/SFN inserter. 
                rsA53Tcp(2) - When transmitting normal content and when using a Rohde&Schwarz 
                                      AEM100 Emission Mux/SFN inserter. 
                a110Tcp(3) - For standard-conforming SFN synchronization corresponding to 
                                    ATSC A/110B. It contains a compatible expansion to allow use of 
                                    Mobile DTV. 
                rsA53DummyBytes(4)
                a110DummyBytes(5)
                "
            ::= { atscConfigurationEntry 9 }

        
        atscTestTable OBJECT-TYPE
            SYNTAX SEQUENCE OF AtscTestEntry
            MAX-ACCESS not-accessible
            STATUS current
            DESCRIPTION
                "Configures the test mode of the exciter."
            ::= { atscSetup 2 }

        
        atscTestEntry OBJECT-TYPE
            SYNTAX AtscTestEntry
            MAX-ACCESS not-accessible
            STATUS current
            DESCRIPTION
                "An entry in the atscTestTable."
            AUGMENTS { atscConfigurationEntry }
            ::= { atscTestTable 1 }

        
        AtscTestEntry ::=
            SEQUENCE { 
                atscTestMode
                    INTEGER
             }

        atscTestMode OBJECT-TYPE
            SYNTAX INTEGER
                {
                off(1),
                prbs(2),
                singleCarrier(3)
                }
            MAX-ACCESS read-write
            STATUS current
            DESCRIPTION
                "off(1)           - no test mode
                singleCarrier(3) - produces an unmodulated carrier
                                   on a selected output frequency"
            ::= { atscTestEntry 1 }

        
        rsXx9AtscConformance OBJECT IDENTIFIER ::= { rsXx9Atsc 2 }

        
        rsXx9AtscCompliances OBJECT IDENTIFIER ::= { rsXx9AtscConformance 1 }

        
        atscBasicCompliance MODULE-COMPLIANCE
            STATUS current
            DESCRIPTION 
                "The compliance statement for XX9000 ATSC encoding."
            MODULE -- this module
                MANDATORY-GROUPS { atscObjBasic, atscNotifyBasic }
            ::= { rsXx9AtscCompliances 1 }

        
        rsXx9AtscGroups OBJECT IDENTIFIER ::= { rsXx9AtscConformance 2 }

        
        atscObjBasic OBJECT-GROUP
            OBJECTS { atscStatusNotificationName, atscStatusNotificationMask, atscStatusNotificationPriority, atscStatusNotificationState, atscConfigurationMobileDtv, 
                atscConfigurationMhePID, atscConfigurationMobileTxID, atscConfigurationWatermark, atscConfigurationTxID, atscConfigurationMarketID, 
                atscConfigurationSfnSyncMode, atscTestMode }
            STATUS current
            DESCRIPTION 
                "General ATSC objects."
            ::= { rsXx9AtscGroups 1 }

        
        atscNotifyBasic NOTIFICATION-GROUP
            NOTIFICATIONS { atscTest, atscContentFail, atscEncoderSummary }
            STATUS current
            DESCRIPTION 
                "General ATSC notifications."
            ::= { rsXx9AtscGroups 2 }

        
    
    END

--
-- RS-XX9-ATSC-MIB.mi2
--
