--
-- RS-XX9-MTX-MIB.mi2
-- MIB generated by MG-SOFT Visual MIB Builder 2010 Version 8.0  Build 403
-- Thursday, March 03, 2016 at 10:43:08
--

-- *****************************************************************************
-- *****************************************************************************
-- **
-- **  COPYRIGHT      (c) 2012 Rohde & Schwarz GmbH & Co. KG
-- **                          Muehldorfstrasse 15
-- **    R & S                 D-81671 Muenchen
-- **
-- *****************************************************************************
-- **
-- **  MODULE         RS-XX9-MTX-MIB
-- **  
-- *****************************************************************************
-- *****************************************************************************

    RS-XX9-MTX-MIB DEFINITIONS ::= BEGIN
 
        IMPORTS
            commonNotificationAlarmClass            
                FROM RS-XX9-COMMON-MIB            
            rsXx9MTx, rsXx9MibModule            
                FROM RS-XX9-SMI-MIB            
            SwitchOnOff, NotificationMask, NotificationPriority, NotificationState, IndexTransmitter, 
            Trigger            
                FROM RS-XX9-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI;
    
    
        rsXx9MtxMibModule MODULE-IDENTITY 
            LAST-UPDATED "201603031100Z"		-- March 03, 2016 at 11:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines system control specific objects of
                XX9000 transmitting systems from Rohde & Schwarz.
                
                Use this MIB for Multi-TX or N+1 system control.
                
                The following MIBs are related to this:
                - RS-COMMON-MIB         - mandatory for this MIB.
                - RS-XX9-TC-MIB         - mandatory for this MIB.
                - RS-XX9-SMI-MIB        - mandatory for this MIB."
            REVISION "201603031100Z"		-- March 03, 2016 at 11:00 GMT
            DESCRIPTION 
                "update description of np1AutoSwitchoverGuardTime 
                "
            REVISION "201602030900Z"		-- February 03, 2016 at 09:00 GMT
            DESCRIPTION 
                "add mtxBackupTx and notifications: mtxBackupTxSummary, mtxBackupTxReady, mtxBackupTxLink, mtxBackupTxRfSwitch, mtxBackupTxSwitchedOver"
            REVISION "201510201200Z"		-- October 20, 2015 at 12:00 GMT
            DESCRIPTION 
                "added np1AutoWhenTxBLocal 
                added np1AutoProgramRf, np1AutomaticReserveRf"
            REVISION "201412221600Z"		-- December 22, 2014 at 16:00 GMT
            DESCRIPTION 
                "updated description texts
                "
            REVISION "201410071400Z"		-- October 07, 2014 at 14:00 GMT
            DESCRIPTION 
                "extend range of np1AutoProgramPreset with unknownPreset(0)
                "
            REVISION "201403031600Z"		-- March 03, 2014 at 16:00 GMT
            DESCRIPTION 
                "added np1AutoReset
                added mtxMultiTx subtree"
            REVISION "201402061400Z"		-- February 06, 2014 at 14:00 GMT
            DESCRIPTION 
                "initial release
                updated description texts"
            REVISION "201210040800Z"		-- October 04, 2012 at 08:00 GMT
            DESCRIPTION 
                "Preliminary release."
            ::= { rsXx9MibModule 4 }

        
    
    
--
-- Node definitions
--
    
        rsXx9MtxNotifications OBJECT IDENTIFIER ::= { rsXx9MTx 0 }

        
        mtxNp1AutomaticSummary NOTIFICATION-TYPE
            OBJECTS { commonNotificationAlarmClass, mtxNotificationPriority, mtxNotificationState }
            STATUS current
            DESCRIPTION 
                "N+1 automatic summary state.
                
                Possible values:
                off(2)
                fault(3)
                warning(4)
                ok(5)
                
                Notification class: warning"
            ::= { rsXx9MtxNotifications 1 }

        
        mtxNp1AutomaticReady NOTIFICATION-TYPE
            OBJECTS { commonNotificationAlarmClass, mtxNotificationPriority, mtxNotificationState }
            STATUS current
            DESCRIPTION 
                "Indicates whether the n+1 automatic is ready. It shows not ready if a 
                changeover occurs and no higher priorized programs are available.
                
                Possible values:
                off(2) - not ready
                ok(5)  - ready
                
                Notification class: warning"
            ::= { rsXx9MtxNotifications 2 }

        
        mtxNp1AutomaticRfSwitch NOTIFICATION-TYPE
            OBJECTS { commonNotificationAlarmClass, mtxNotificationPriority, mtxNotificationState }
            STATUS current
            DESCRIPTION 
                "Indicates a fault if in the event of a switchover one of 
                the RF switches could not be turned correctly or if 
                one of the jumpers has not been positioned correctly 
                on the patch panel (if used).
                
                Possible values:
                off(2)   - RF switch ok
                fault(3) - RF switch faulty
                
                Notification class: warning"
            ::= { rsXx9MtxNotifications 3 }

        
        mtxNp1AutomaticInputChannel NOTIFICATION-TYPE
            OBJECTS { commonNotificationAlarmClass, mtxNotificationPriority, mtxNotificationState }
            STATUS current
            DESCRIPTION 
                "Indicates whether the TS distributor has directed the 
                correct transport stream to the input of transmitter B.
                
                Possible values:
                off(2)   - input to TxB is ok
                fault(3) - TS distributor fails to deliver input to TxB
                
                Notification class: warning"
            ::= { rsXx9MtxNotifications 4 }

        
        mtxNp1AutomaticChangeOver NOTIFICATION-TYPE
            OBJECTS { commonNotificationAlarmClass, mtxNotificationPriority, mtxNotificationState }
            STATUS current
            DESCRIPTION 
                "
                Possible values:
                off(2)     - 
                warning(4) - a changeover to TxB occured
                
                Notification class: warning"
            ::= { rsXx9MtxNotifications 5 }

        
        mtxLocal NOTIFICATION-TYPE
            OBJECTS { commonNotificationAlarmClass, mtxNotificationPriority, mtxNotificationState }
            STATUS current
            DESCRIPTION 
                "local/remote state of system control.
                
                Possible values:
                off(2)   - remote
                ok(5)    - local
                
                Notification class: info"
            ::= { rsXx9MtxNotifications 6 }

        
        mtxNp1AutomaticProgramRf NOTIFICATION-TYPE
            OBJECTS { commonNotificationAlarmClass, mtxNotificationPriority, mtxNotificationState }
            STATUS current
            DESCRIPTION 
                "indicates a warning/fault if RF power  of program transmitter falls below 
                the adjusted warning/fault limit. 
                "
            ::= { rsXx9MtxNotifications 7 }

        
        mtxMultiTxSummary NOTIFICATION-TYPE
            OBJECTS { commonNotificationAlarmClass, mtxNotificationPriority, mtxNotificationState }
            STATUS current
            DESCRIPTION 
                "Description."
            ::= { rsXx9MtxNotifications 100 }

        
        mtxMultiTxRfSwitch NOTIFICATION-TYPE
            OBJECTS { commonNotificationAlarmClass, mtxNotificationPriority, mtxNotificationState }
            STATUS current
            DESCRIPTION 
                "Description."
            ::= { rsXx9MtxNotifications 101 }

        
        mtxBackupTxSummary NOTIFICATION-TYPE
            OBJECTS { commonNotificationAlarmClass, btxAutoNotificationPriority, btxAutoNotificationState }
            STATUS current
            DESCRIPTION 
                "Indicates the overall state of the automatic
                
                Possible values:
                off(2) - the automatic is switched off
                fault(3) - the automatic cannot operate, e.g. the rf-switch is not connected
                warning(4) - the automatic signals a warning, e.g. the automatic has switched over
                ok(5)    - the automatic is on and operational
                 
                "
            ::= { rsXx9MtxNotifications 200 }

        
        mtxBackupTxReady NOTIFICATION-TYPE
            OBJECTS { commonNotificationAlarmClass, btxAutoNotificationPriority, btxAutoNotificationState }
            STATUS current
            DESCRIPTION 
                "Indicates whether the automatic is able to switch to the 
                inactive transmitter in case of a fault of the active one.
                
                Possible values:
                off(2) - not ready
                ok(5)    - ready
                 "
            ::= { rsXx9MtxNotifications 201 }

        
        mtxBackupTxLink NOTIFICATION-TYPE
            OBJECTS { commonNotificationAlarmClass, btxAutoNotificationPriority, btxAutoNotificationState }
            STATUS current
            DESCRIPTION 
                "Indicates, if an ethernet-connection between txA and txB exists. 
                If the connection fails and the automatic is enabled, the reserve 
                transmitter is switched to the antenna. 
                
                Possible values:
                warning(4)   - 
                ok(5)    - 
                "
            ::= { rsXx9MtxNotifications 202 }

        
        mtxBackupTxRfSwitch NOTIFICATION-TYPE
            OBJECTS { commonNotificationAlarmClass, btxAutoNotificationPriority, btxAutoNotificationState }
            STATUS current
            DESCRIPTION 
                "Indicates if the rf-switch is ready. 
                
                Possible values:
                undefined(1) - no electrical connection between automatic and rf-switch
                fault(3)   - 
                ok(5)    - 
                "
            ::= { rsXx9MtxNotifications 203 }

        
        mtxBackupTxSwitchedOver NOTIFICATION-TYPE
            OBJECTS { commonNotificationAlarmClass, btxAutoNotificationPriority, btxAutoNotificationState }
            STATUS current
            DESCRIPTION 
                "Indicates if the current switch position defers from the preselected switch position. 
                
                possible values:
                off(2) - switch position is the same as the preselected switch position
                warning(4) - switch position defers from the preselected switch position. 
                
                "
            ::= { rsXx9MtxNotifications 204 }

        
        rsXx9MtxObjects OBJECT IDENTIFIER ::= { rsXx9MTx 1 }

        
        mtxNotificationTable OBJECT-TYPE
            SYNTAX SEQUENCE OF MtxNotificationEntry
            MAX-ACCESS not-accessible
            STATUS current
            DESCRIPTION
                "Objects from the mtxNotificationTable."
            ::= { rsXx9MtxObjects 1 }

        
        mtxNotificationEntry OBJECT-TYPE
            SYNTAX MtxNotificationEntry
            MAX-ACCESS not-accessible
            STATUS current
            DESCRIPTION
                "An entry in the mtxNotificationTable."
            INDEX { mtxNotificationIdx }
            ::= { mtxNotificationTable 1 }

        
        MtxNotificationEntry ::=
            SEQUENCE { 
                mtxNotificationIdx
                    Unsigned32,
                mtxNotificationName
                    INTEGER,
                mtxNotificationMask
                    NotificationMask,
                mtxNotificationPriority
                    NotificationPriority,
                mtxNotificationState
                    NotificationState
             }

        mtxNotificationIdx OBJECT-TYPE
            SYNTAX Unsigned32 (1..6 | 100..101)
            MAX-ACCESS not-accessible
            STATUS current
            DESCRIPTION
                "The notification number as below rsXx9MtxNotifications.
                This is a helper column and therefore not-accessible.
                "
            ::= { mtxNotificationEntry 1 }

        
        mtxNotificationName OBJECT-TYPE
            SYNTAX INTEGER
                {
                mtxNp1AutomaticSummary(1),
                mtxNp1AutomaticReady(2),
                mtxNp1AutomaticRfSwitch(3),
                mtxNp1AutomaticInputChannel(4),
                mtxNp1AutomaticChangeOver(5),
                mtxLocal(6),
                mtxMultiTxSummary(100),
                mtxMultiTxRfSwitch(101)
                }
            MAX-ACCESS read-only
            STATUS current
            DESCRIPTION
                "The notification number as an enumeration.
                The enumeration correlates with the notifications under rsXx9MtxNotifications.
                "
            ::= { mtxNotificationEntry 2 }

        
        mtxNotificationMask OBJECT-TYPE
            SYNTAX NotificationMask
            MAX-ACCESS read-write
            STATUS current
            DESCRIPTION
                "See textual convention for details."
            ::= { mtxNotificationEntry 3 }

        
        mtxNotificationPriority OBJECT-TYPE
            SYNTAX NotificationPriority
            MAX-ACCESS read-write
            STATUS current
            DESCRIPTION
                "See textual convention for details."
            ::= { mtxNotificationEntry 4 }

        
        mtxNotificationState OBJECT-TYPE
            SYNTAX NotificationState
            MAX-ACCESS read-only
            STATUS current
            DESCRIPTION
                "See textual convention for details."
            ::= { mtxNotificationEntry 5 }

        
        mtxSystemControl OBJECT IDENTIFIER ::= { rsXx9MtxObjects 2 }

        
        mtxNplus1 OBJECT IDENTIFIER ::= { rsXx9MtxObjects 3 }

        
        nplus1AutomaticStatus OBJECT IDENTIFIER ::= { mtxNplus1 1 }

        
        np1AutomaticLoadedTx OBJECT-TYPE
            SYNTAX INTEGER
                {
                txA1(1),
                txA2(2),
                txA3(3),
                txA4(4),
                txA5(5),
                txA6(6),
                txA7(7),
                txA8(8),
                none(9),
                undefined(10)
                }
            MAX-ACCESS read-only
            STATUS current
            DESCRIPTION
                "If a switchover operation has taken place, shows which 
                program of an A transmitter the B transmitter has taken over.
                "
            ::= { nplus1AutomaticStatus 1 }

        
        np1AutomaticReserveRf OBJECT-TYPE
            SYNTAX NotificationState
            MAX-ACCESS read-only
            STATUS current
            DESCRIPTION
                "indicates a warning/fault if RF power of reserve transmitter falls below 
                the adjusted warning/fault limit. 
                "
            ::= { nplus1AutomaticStatus 2 }

        
        np1AutoSwitchesTable OBJECT-TYPE
            SYNTAX SEQUENCE OF Np1AutoSwitchesEntry
            MAX-ACCESS not-accessible
            STATUS current
            DESCRIPTION
                "Table with data about RfSwitches in an nplus1 system. "
            ::= { nplus1AutomaticStatus 100 }

        
        np1AutoSwitchesEntry OBJECT-TYPE
            SYNTAX Np1AutoSwitchesEntry
            MAX-ACCESS not-accessible
            STATUS current
            DESCRIPTION
                "An entry in the np1AutoSwitchesTable."
            INDEX { np1AutoSwitchIdx }
            ::= { np1AutoSwitchesTable 1 }

        
        Np1AutoSwitchesEntry ::=
            SEQUENCE { 
                np1AutoSwitchIdx
                    Integer32,
                np1AutoSwitchPos
                    INTEGER
             }

        np1AutoSwitchIdx OBJECT-TYPE
            SYNTAX Integer32 (1..8)
            MAX-ACCESS read-only
            STATUS current
            DESCRIPTION
                "Description."
            ::= { np1AutoSwitchesEntry 1 }

        
        np1AutoSwitchPos OBJECT-TYPE
            SYNTAX INTEGER
                {
                unknown(0),
                pos1(1),
                pos2(2)
                }
            MAX-ACCESS read-only
            STATUS current
            DESCRIPTION
                "The position of the rfSwitch.
                Usually, SwitchX is responsible for switching between antenna
                and dummyload for TransmitterX.
                Usually, pos1(1) means, that the transmitter is switched to antenna
                and pos2(2) means, that the transmitter is switched to dummyload. 
                "
            ::= { np1AutoSwitchesEntry 2 }

        
        nplus1AutomaticConfiguration OBJECT IDENTIFIER ::= { mtxNplus1 2 }

        
        np1AutomaticOperationMode OBJECT-TYPE
            SYNTAX SwitchOnOff
            MAX-ACCESS read-write
            STATUS current
            DESCRIPTION
                "Activates the n+1 automatic function. 
                If the n+1 automatic function is on(1), 
                a fault within an A transmitter causes 
                a switchover and the program of the 
                A transmitter is taken over by the 
                standby B transmitter.
                "
            ::= { nplus1AutomaticConfiguration 1 }

        
        np1AutoSwitchoverGuardTime OBJECT-TYPE
            SYNTAX Unsigned32 (1..60)
            UNITS "second"
            MAX-ACCESS read-write
            STATUS current
            DESCRIPTION
                "Checkout time which must pass before a 
                program transmitter with sum fault is replaced 
                by the standby transmitter. 
                A long Guard Time suppresses 
                switchover operations caused by brief faults, 
                but also reduces the availability of the program. 
                A guard time less than two seconds might lead 
                to an unnecessary switchover in case of a 
                phase break of amplifiers.
                "
            ::= { nplus1AutomaticConfiguration 2 }

        
        np1AutoSwitchMode OBJECT-TYPE
            SYNTAX INTEGER
                {
                severalTimes(1),
                singleShot(2)
                }
            MAX-ACCESS read-write
            STATUS current
            DESCRIPTION
                "Defines the switching behavior of the N+1 automatic function. 
                
                severalTimes(1) - Following a switchover operation, the system can 
                  switch back to the A transmitter automatically when the A transmitter 
                  no longer signals a fault but the B transmitter indicates a fault. 
                
                singleShot(2)   - Switchover of an A transmitter to the B transmitter can 
                  occur once only.
                "
            ::= { nplus1AutomaticConfiguration 3 }

        
        np1AutoProgramPreset OBJECT-TYPE
            SYNTAX INTEGER
                {
                unknownPreset(0),
                txA1(1),
                txA2(2),
                txA3(3),
                txA4(4),
                txA5(5),
                txA6(6),
                txA7(7),
                txA8(8)
                }
            MAX-ACCESS read-write
            STATUS current
            DESCRIPTION
                "Loads the program-specific settings of an A transmitter to the B transmitter.
                
                unknownPreset(0) can not be commanded.
                "
            ::= { nplus1AutomaticConfiguration 4 }

        
        np1AutoInputPreset OBJECT-TYPE
            SYNTAX INTEGER
                {
                channel1(1),
                channel2(2),
                channel3(3),
                channel4(4),
                channel5(5),
                channel6(6),
                channel7(7),
                channel8(8),
                channel9(9)
                }
            MAX-ACCESS read-write
            STATUS current
            DESCRIPTION
                "Determines the preconfigured transport stream for TX-B
                via the TS distributor."
            ::= { nplus1AutomaticConfiguration 5 }

        
        np1AutoPriorityEnable OBJECT-TYPE
            SYNTAX SwitchOnOff
            MAX-ACCESS read-write
            STATUS current
            DESCRIPTION
                "Activaes the priority-controlled n+1 switchover function. 
                If priority control is active, a further switchover of a program 
                with higher priority can take place following the switchover 
                of a low-priority program. In this case, the low-priority 
                program is switched back to its defective A transmitter."
            ::= { nplus1AutomaticConfiguration 7 }

        
        np1AutoToLoad OBJECT-TYPE
            SYNTAX IndexTransmitter
            MAX-ACCESS read-write
            STATUS current
            DESCRIPTION
                "Performs a manual switchover."
            ::= { nplus1AutomaticConfiguration 8 }

        
        np1AutoReserveOperationMode OBJECT-TYPE
            SYNTAX SwitchOnOff
            MAX-ACCESS read-write
            STATUS current
            DESCRIPTION
                "Switches reserve transmitter on or off."
            ::= { nplus1AutomaticConfiguration 9 }

        
        np1AutoProgramTable OBJECT-TYPE
            SYNTAX SEQUENCE OF Np1AutoProgramEntry
            MAX-ACCESS not-accessible
            STATUS current
            DESCRIPTION
                "Program specific configuration."
            ::= { nplus1AutomaticConfiguration 10 }

        
        np1AutoProgramEntry OBJECT-TYPE
            SYNTAX Np1AutoProgramEntry
            MAX-ACCESS not-accessible
            STATUS current
            DESCRIPTION
                "An entry in the np1AutoProgramTable."
            INDEX { np1AutoProgramIdx }
            ::= { np1AutoProgramTable 1 }

        
        Np1AutoProgramEntry ::=
            SEQUENCE { 
                np1AutoProgramIdx
                    Unsigned32,
                np1AutoProgramOperationMode
                    SwitchOnOff,
                np1AutoProgramPriority
                    Unsigned32,
                np1AutoProgramChangeover
                    SwitchOnOff,
                np1AutoProgramRf
                    NotificationState
             }

        np1AutoProgramIdx OBJECT-TYPE
            SYNTAX Unsigned32 (1..8)
            MAX-ACCESS not-accessible
            STATUS current
            DESCRIPTION
                "Program index - coincides with TxA index."
            ::= { np1AutoProgramEntry 1 }

        
        np1AutoProgramOperationMode OBJECT-TYPE
            SYNTAX SwitchOnOff
            MAX-ACCESS read-write
            STATUS current
            DESCRIPTION
                "Switches program transmitter on or off."
            ::= { np1AutoProgramEntry 2 }

        
        np1AutoProgramPriority OBJECT-TYPE
            SYNTAX Unsigned32 (1..8)
            MAX-ACCESS read-write
            STATUS current
            DESCRIPTION
                "Priority of the respective program. 
                1 is the highest priority and 8 is the lowest priority. 
                The specified program number corresponds to the 
                number of the A transmitter assigned in each case."
            ::= { np1AutoProgramEntry 3 }

        
        np1AutoProgramChangeover OBJECT-TYPE
            SYNTAX SwitchOnOff
            MAX-ACCESS read-write
            STATUS current
            DESCRIPTION
                "Used to activate the N+1 automatic function individually for 
                each A transmitter. This setting can be used to remove 
                A transmitters from the N+1 automatic function. 
                The same effect can be achieved by configuring the 
                respective A transmitter for local operation.
                "
            ::= { np1AutoProgramEntry 4 }

        
        np1AutoProgramRf OBJECT-TYPE
            SYNTAX NotificationState
            MAX-ACCESS read-only
            STATUS current
            DESCRIPTION
                "indicates a warning/fault if RF power  of program transmitter falls below 
                the adjusted warning/fault limit. 
                "
            ::= { np1AutoProgramEntry 5 }

        
        np1AutoReset OBJECT-TYPE
            SYNTAX Trigger
            MAX-ACCESS read-write
            STATUS current
            DESCRIPTION
                "Description."
            ::= { nplus1AutomaticConfiguration 11 }

        
        np1AutoWhenTxBLocal OBJECT-TYPE
            SYNTAX INTEGER
                {
                automaticAvailable(1),
                automaticNotAvailable(2)
                }
            MAX-ACCESS read-write
            STATUS current
            DESCRIPTION
                "TxB and n+1 automatic control are located in the same device and share one 
                local/remote button. 
                By default the n+1 automatic shall be disabled when TxB is set to local operation. 
                To test the n+1 automatic using the local display the n+1 automatic can be activated 
                even in local operation mode.
                
                "
            ::= { nplus1AutomaticConfiguration 12 }

        
        np1AutoProgramNotificationTable OBJECT-TYPE
            SYNTAX SEQUENCE OF Np1AutoProgramNotificationEntry
            MAX-ACCESS not-accessible
            STATUS current
            DESCRIPTION
                "The context information/configuration for the program status notifications.
                "
            ::= { mtxNplus1 3 }

        
        np1AutoProgramNotificationEntry OBJECT-TYPE
            SYNTAX Np1AutoProgramNotificationEntry
            MAX-ACCESS not-accessible
            STATUS current
            DESCRIPTION
                "An entry in the np1AutoProgramNotificationTable"
            INDEX { np1AutoProgramNotificationProgramIdx, np1AutoProgramNotificationIdx }
            ::= { np1AutoProgramNotificationTable 1 }

        
        Np1AutoProgramNotificationEntry ::=
            SEQUENCE { 
                np1AutoProgramNotificationProgramIdx
                    Unsigned32,
                np1AutoProgramNotificationIdx
                    Unsigned32,
                np1AutoProgramNotificationName
                    INTEGER,
                np1AutoProgramNotificationMask
                    NotificationMask,
                np1AutoProgramNotificationPriority
                    NotificationPriority,
                np1AutoProgramNotificationState
                    NotificationState
             }

        np1AutoProgramNotificationProgramIdx OBJECT-TYPE
            SYNTAX Unsigned32 (1..8)
            MAX-ACCESS read-only
            STATUS current
            DESCRIPTION
                "Description."
            ::= { np1AutoProgramNotificationEntry 1 }

        
        np1AutoProgramNotificationIdx OBJECT-TYPE
            SYNTAX Unsigned32 (7)
            MAX-ACCESS read-only
            STATUS current
            DESCRIPTION
                "The notification number as below rsXx9nplus1AutomaticProgramNotifications.
                This is a helper column and therefore not-accessible.
                "
            ::= { np1AutoProgramNotificationEntry 2 }

        
        np1AutoProgramNotificationName OBJECT-TYPE
            SYNTAX INTEGER { mtxNp1AutomaticProgramRf(7) }
            MAX-ACCESS read-only
            STATUS current
            DESCRIPTION
                "The notification number as an enumeration.
                The enumeration correlates with the notifications under rsXx9MtxNotifications.
                "
            ::= { np1AutoProgramNotificationEntry 3 }

        
        np1AutoProgramNotificationMask OBJECT-TYPE
            SYNTAX NotificationMask
            MAX-ACCESS read-write
            STATUS current
            DESCRIPTION
                "See textual convention for details."
            ::= { np1AutoProgramNotificationEntry 4 }

        
        np1AutoProgramNotificationPriority OBJECT-TYPE
            SYNTAX NotificationPriority
            MAX-ACCESS read-write
            STATUS current
            DESCRIPTION
                "See textual convention for details."
            ::= { np1AutoProgramNotificationEntry 5 }

        
        np1AutoProgramNotificationState OBJECT-TYPE
            SYNTAX NotificationState
            MAX-ACCESS read-only
            STATUS current
            DESCRIPTION
                "See textual convention for details."
            ::= { np1AutoProgramNotificationEntry 6 }

        
        mtxMultiTx OBJECT IDENTIFIER ::= { rsXx9MtxObjects 4 }

        
        multiTxTransmitterTable OBJECT-TYPE
            SYNTAX SEQUENCE OF MultiTxTransmitterEntry
            MAX-ACCESS not-accessible
            STATUS current
            DESCRIPTION
                "Description."
            ::= { mtxMultiTx 1 }

        
        multiTxTransmitterEntry OBJECT-TYPE
            SYNTAX MultiTxTransmitterEntry
            MAX-ACCESS not-accessible
            STATUS current
            DESCRIPTION
                "An entry in the multiTxTransmitterTable."
            INDEX { multiTxTxIdx }
            ::= { multiTxTransmitterTable 1 }

        
        MultiTxTransmitterEntry ::=
            SEQUENCE { 
                multiTxTxIdx
                    IndexTransmitter,
                multiTxLoadedOrAntenna
                    INTEGER,
                multiTxToLoad
                    Trigger,
                multiTxToAntenna
                    Trigger
             }

        multiTxTxIdx OBJECT-TYPE
            SYNTAX IndexTransmitter
            MAX-ACCESS not-accessible
            STATUS current
            DESCRIPTION
                "Description."
            ::= { multiTxTransmitterEntry 1 }

        
        multiTxLoadedOrAntenna OBJECT-TYPE
            SYNTAX INTEGER
                {
                unknown(1),
                antenna(2),
                load(3)
                }
            MAX-ACCESS read-write
            STATUS current
            DESCRIPTION
                "Description."
            ::= { multiTxTransmitterEntry 2 }

        
        multiTxToLoad OBJECT-TYPE
            SYNTAX Trigger
            MAX-ACCESS read-write
            STATUS current
            DESCRIPTION
                "Description."
            ::= { multiTxTransmitterEntry 3 }

        
        multiTxToAntenna OBJECT-TYPE
            SYNTAX Trigger
            MAX-ACCESS read-write
            STATUS current
            DESCRIPTION
                "Description."
            ::= { multiTxTransmitterEntry 4 }

        
        multiTxConfiguration OBJECT IDENTIFIER ::= { mtxMultiTx 2 }

        
        multiTxReset OBJECT-TYPE
            SYNTAX Trigger
            MAX-ACCESS read-write
            STATUS current
            DESCRIPTION
                "Description."
            ::= { multiTxConfiguration 1 }

        
        mtxBackupTx OBJECT IDENTIFIER ::= { rsXx9MtxObjects 5 }

        
        btxAutoNotificationTable OBJECT-TYPE
            SYNTAX SEQUENCE OF BtxAutoNotificationEntry
            MAX-ACCESS not-accessible
            STATUS current
            DESCRIPTION
                "Objects from the btxNotificationTable."
            ::= { mtxBackupTx 1 }

        
        btxAutoNotificationEntry OBJECT-TYPE
            SYNTAX BtxAutoNotificationEntry
            MAX-ACCESS not-accessible
            STATUS current
            DESCRIPTION
                "An entry in the btxAutoNotificationTable."
            INDEX { btxAutoNotificationAutomaticIdx, btxAutoNotificationIdx }
            ::= { btxAutoNotificationTable 1 }

        
        BtxAutoNotificationEntry ::=
            SEQUENCE { 
                btxAutoNotificationAutomaticIdx
                    INTEGER,
                btxAutoNotificationIdx
                    Integer32,
                btxAutoNotificationName
                    INTEGER,
                btxAutoNotificationMask
                    NotificationMask,
                btxAutoNotificationPriority
                    NotificationPriority,
                btxAutoNotificationState
                    NotificationState
             }

        btxAutoNotificationAutomaticIdx OBJECT-TYPE
            SYNTAX INTEGER (1)
            MAX-ACCESS not-accessible
            STATUS current
            DESCRIPTION
                "enumerates over all backupTx automatics."
            ::= { btxAutoNotificationEntry 1 }

        
        btxAutoNotificationIdx OBJECT-TYPE
            SYNTAX Integer32 (200..204)
            MAX-ACCESS not-accessible
            STATUS current
            DESCRIPTION
                "The notification number as below rsXx9MtxNotifications.
                This is a helper column and therefore not-accessible.
                "
            ::= { btxAutoNotificationEntry 2 }

        
        btxAutoNotificationName OBJECT-TYPE
            SYNTAX INTEGER
                {
                mtxBackupTxSummary(200),
                mtxBackupTxReady(201),
                mtxBackupTxLink(202),
                mtxBackupTxRfSwitch(203),
                mtxBackupTxSwitchedOver(204)
                }
            MAX-ACCESS read-only
            STATUS current
            DESCRIPTION
                "The notification number as an enumeration.
                The enumeration correlates with the notifications under rsXx9MtxNotifications.
                "
            ::= { btxAutoNotificationEntry 3 }

        
        btxAutoNotificationMask OBJECT-TYPE
            SYNTAX NotificationMask
            MAX-ACCESS read-write
            STATUS current
            DESCRIPTION
                "See textual convention for details."
            ::= { btxAutoNotificationEntry 4 }

        
        btxAutoNotificationPriority OBJECT-TYPE
            SYNTAX NotificationPriority
            MAX-ACCESS read-write
            STATUS current
            DESCRIPTION
                "See textual convention for details."
            ::= { btxAutoNotificationEntry 5 }

        
        btxAutoNotificationState OBJECT-TYPE
            SYNTAX NotificationState
            MAX-ACCESS read-only
            STATUS current
            DESCRIPTION
                "See textual convention for details."
            ::= { btxAutoNotificationEntry 6 }

        
        btxAutoStatusTable OBJECT-TYPE
            SYNTAX SEQUENCE OF BtxAutoStatusEntry
            MAX-ACCESS not-accessible
            STATUS current
            DESCRIPTION
                "The status of a backupTx automatic.
                "
            ::= { mtxBackupTx 2 }

        
        btxAutoStatusEntry OBJECT-TYPE
            SYNTAX BtxAutoStatusEntry
            MAX-ACCESS not-accessible
            STATUS current
            DESCRIPTION
                "An entry in the btxAutoStatusTable."
            INDEX { btxAutoNotificationAutomaticIdx }
            ::= { btxAutoStatusTable 1 }

        
        BtxAutoStatusEntry ::=
            SEQUENCE { 
                btxAutoStActiveTx
                    INTEGER
             }

        btxAutoStActiveTx OBJECT-TYPE
            SYNTAX INTEGER
                {
                undefined(1),
                txA(2),
                txB(3)
                }
            MAX-ACCESS read-only
            STATUS current
            DESCRIPTION
                "Indicates which transmitter is connected to the antenna via the rf-switch.
                "
            ::= { btxAutoStatusEntry 1 }

        
        btxAutoConfigurationTable OBJECT-TYPE
            SYNTAX SEQUENCE OF BtxAutoConfigurationEntry
            MAX-ACCESS not-accessible
            STATUS current
            DESCRIPTION
                "The configuration of a backupTx automatic.
                "
            ::= { mtxBackupTx 3 }

        
        btxAutoConfigurationEntry OBJECT-TYPE
            SYNTAX BtxAutoConfigurationEntry
            MAX-ACCESS not-accessible
            STATUS current
            DESCRIPTION
                "An entry in the btxAutoConfigurationTable."
            INDEX { btxAutoNotificationAutomaticIdx }
            ::= { btxAutoConfigurationTable 1 }

        
        BtxAutoConfigurationEntry ::=
            SEQUENCE { 
                btxAutoCfgReset
                    Trigger,
                btxAutoCfgOperationMode
                    SwitchOnOff,
                btxAutoCfgMode
                    INTEGER,
                btxAutoCfgGuardTime
                    Unsigned32,
                btxAutoCfgPreselectTx
                    INTEGER
             }

        btxAutoCfgReset OBJECT-TYPE
            SYNTAX Trigger
            MAX-ACCESS read-write
            STATUS current
            DESCRIPTION
                "Description."
            ::= { btxAutoConfigurationEntry 1 }

        
        btxAutoCfgOperationMode OBJECT-TYPE
            SYNTAX SwitchOnOff
            MAX-ACCESS read-write
            STATUS current
            DESCRIPTION
                "Indicates if the Backup Tx automatic is enabled.
                If the automatic is enabled, a switchover to a reserve transmitter 
                occurs after a configurable guard time, as soon as the preselected 
                transmitter signals a fault. 
                "
            ::= { btxAutoConfigurationEntry 2 }

        
        btxAutoCfgMode OBJECT-TYPE
            SYNTAX INTEGER
                {
                multipleShot(1),
                singleShot(2)
                }
            MAX-ACCESS read-write
            STATUS current
            DESCRIPTION
                "Indicates how the automatic behaves, when the reserve 
                transmitter signals a fault. 
                
                - multipleShot(1)
                  after a switch over to the reserve transmitter has happened, 
                  a switch over to the preselected transmitter happens, if the 
                  preselected transmitter signales no fault. A manual operator 
                  action is not necessary. 
                - singleShot(2): 
                  after a switch over to the reserve transmitter has happened, 
                  the reserve transmit stays active even if the reserve transmitter
                   signals a fault and the preselected transmitter could work 
                  without faults. A manual operator action is necessary to 
                  re-enable the automatic. 
                
                "
            ::= { btxAutoConfigurationEntry 3 }

        
        btxAutoCfgGuardTime OBJECT-TYPE
            SYNTAX Unsigned32 (0..60)
            UNITS "s"
            MAX-ACCESS read-write
            STATUS current
            DESCRIPTION
                "Indicates how long no a switchover shall be delayed after detecting a fault. 
                By increasing the guard time, switch overs caused by short temporary faults can be avoided. 
                "
            ::= { btxAutoConfigurationEntry 4 }

        
        btxAutoCfgPreselectTx OBJECT-TYPE
            SYNTAX INTEGER
                {
                txA(2),
                txB(3)
                }
            MAX-ACCESS read-write
            STATUS current
            DESCRIPTION
                "Indicates, which transmitter should be primarily used to transmit a program. "
            ::= { btxAutoConfigurationEntry 5 }

        
        rsXx9MtxConformance OBJECT IDENTIFIER ::= { rsXx9MTx 2 }

        
        rsXx9MtxCompliances OBJECT IDENTIFIER ::= { rsXx9MtxConformance 1 }

        
        mtxSystemControlCompliance MODULE-COMPLIANCE
            STATUS current
            DESCRIPTION 
                "The compliance statement for XX9000 MTX control."
            MODULE -- this module
                MANDATORY-GROUPS { mtxNotifySystemControl }
            ::= { rsXx9MtxCompliances 1 }

        
        mtxNplus1Compliance MODULE-COMPLIANCE
            STATUS current
            DESCRIPTION 
                "The compliance statement for XX9000 N+1 control."
            MODULE -- this module
                MANDATORY-GROUPS { mtxObjsNplus1, mtxNotifyNplus1, mtxObjsNotificationTable }
            ::= { rsXx9MtxCompliances 2 }

        
        rsXx9MtxGroups OBJECT IDENTIFIER ::= { rsXx9MtxConformance 2 }

        
        mtxObjsNotificationTable OBJECT-GROUP
            OBJECTS { mtxNotificationName, mtxNotificationMask, mtxNotificationPriority, mtxNotificationState }
            STATUS current
            DESCRIPTION 
                "common objects for systems."
            ::= { rsXx9MtxGroups 1 }

        
        mtxObjsNplus1 OBJECT-GROUP
            OBJECTS { np1AutoPriorityEnable, np1AutoSwitchoverGuardTime, np1AutoProgramPreset, np1AutoInputPreset, np1AutoProgramOperationMode, 
                np1AutoProgramPriority, np1AutoProgramChangeover, np1AutoToLoad, np1AutoReset, np1AutoWhenTxBLocal, 
                np1AutomaticReserveRf, np1AutoProgramRf, np1AutoSwitchPos, np1AutoSwitchIdx, np1AutoSwitchMode, 
                np1AutomaticLoadedTx, np1AutomaticOperationMode, np1AutoReserveOperationMode, np1AutoProgramNotificationState, np1AutoProgramNotificationPriority, 
                np1AutoProgramNotificationMask, np1AutoProgramNotificationName, np1AutoProgramNotificationIdx, np1AutoProgramNotificationProgramIdx }
            STATUS current
            DESCRIPTION 
                "All N+1 objects."
            ::= { rsXx9MtxGroups 2 }

        
        mtxNotifyNplus1 NOTIFICATION-GROUP
            NOTIFICATIONS { mtxNp1AutomaticProgramRf, mtxNp1AutomaticReady, mtxNp1AutomaticSummary, mtxNp1AutomaticRfSwitch, mtxNp1AutomaticInputChannel, 
                mtxNp1AutomaticChangeOver }
            STATUS current
            DESCRIPTION 
                "All N+1 notifications."
            ::= { rsXx9MtxGroups 3 }

        
        mtxNotifySystemControl NOTIFICATION-GROUP
            NOTIFICATIONS { mtxLocal }
            STATUS current
            DESCRIPTION 
                "All MTX notifications."
            ::= { rsXx9MtxGroups 4 }

        
        mtxObsMultiTx OBJECT-GROUP
            OBJECTS { multiTxReset }
            STATUS current
            DESCRIPTION 
                "multiTx objects."
            ::= { rsXx9MtxGroups 100 }

        
        mtxObjsMultiTxDummyLoads OBJECT-GROUP
            OBJECTS { multiTxLoadedOrAntenna }
            STATUS current
            DESCRIPTION 
                "multiTx with dummyLoads objects."
            ::= { rsXx9MtxGroups 101 }

        
        mtxObjsMultiTxDummyLoadSwitches OBJECT-GROUP
            OBJECTS { multiTxToLoad, multiTxToAntenna }
            STATUS current
            DESCRIPTION 
                "objects for switches of multiTx with dummyloads."
            ::= { rsXx9MtxGroups 102 }

        
        mtxNotifyMultiTx NOTIFICATION-GROUP
            NOTIFICATIONS { mtxMultiTxSummary }
            STATUS current
            DESCRIPTION 
                "multiTx notifications."
            ::= { rsXx9MtxGroups 150 }

        
        mtxNotifyMultiTxSwitches NOTIFICATION-GROUP
            NOTIFICATIONS { mtxMultiTxRfSwitch }
            STATUS current
            DESCRIPTION 
                "switches of multiTx notifications."
            ::= { rsXx9MtxGroups 151 }

        
        mtxObjsBackupTx OBJECT-GROUP
            OBJECTS { btxAutoNotificationName, btxAutoNotificationMask, btxAutoNotificationPriority, btxAutoNotificationState, btxAutoStActiveTx, 
                btxAutoCfgOperationMode, btxAutoCfgMode, btxAutoCfgGuardTime, btxAutoCfgPreselectTx, btxAutoCfgReset
                 }
            STATUS current
            DESCRIPTION 
                "backupTx objects."
            ::= { rsXx9MtxGroups 152 }

        
        mtxNotifyBackupTx NOTIFICATION-GROUP
            NOTIFICATIONS { mtxBackupTxSummary, mtxBackupTxLink, mtxBackupTxSwitchedOver, mtxBackupTxRfSwitch, mtxBackupTxReady
                 }
            STATUS current
            DESCRIPTION 
                "backupTx notifications."
            ::= { rsXx9MtxGroups 153 }

        
    
    END

--
-- RS-XX9-MTX-MIB.mi2
--
