--
-- RS-XX9-ATV-MIB.mi2
-- MIB generated by MG-SOFT Visual MIB Builder 2010 Version 8.0  Build 403
-- Monday, March 21, 2016 at 15:55:14
--

-- *****************************************************************************
-- *****************************************************************************
-- **
-- **  COPYRIGHT      (c) 2013 Rohde & Schwarz GmbH & Co. KG
-- **                          Muehldorfstrasse 15
-- **    R & S                 D-81671 Muenchen
-- **
-- *****************************************************************************
-- **
-- **  MODULE         RS-XX9-ATV-MIB
-- **  
-- *****************************************************************************
-- *****************************************************************************

    RS-XX9-ATV-MIB DEFINITIONS ::= BEGIN
 
        IMPORTS
            rsXx9Atv, rsXx9MibModule            
                FROM RS-XX9-SMI-MIB            
            IndexTransmitter, IndexAB, SwitchOnOff, NotificationState            
                FROM RS-XX9-TC-MIB            
            OBJECT-GROUP, MODULE-COMPLIANCE            
                FROM SNMPv2-CONF            
            Integer32, Unsigned32, OBJECT-TYPE, MODULE-IDENTITY            
                FROM SNMPv2-SMI            
            TruthValue, TEXTUAL-CONVENTION            
                FROM SNMPv2-TC;
    
    
        rsXx9AtvMibModule MODULE-IDENTITY 
            LAST-UPDATED "201412221600Z"		-- December 22, 2014 at 16:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines ATV specific objects
                of XX9000 transmitting systems from Rohde & Schwarz.
                
                The following MIBs are related to this:
                - RS-COMMON-MIB         - mandatory for this MIB
                - RS-XX9-SMI-MIB        - mandatory for this MIB
                - RS-XX9-TC-MIB         - mandatory for this MIB"
            REVISION "201412221600Z"		-- December 22, 2014 at 16:00 GMT
            DESCRIPTION 
                "updated description texts
                "
            REVISION "201409301600Z"		-- September 30, 2014 at 16:00 GMT
            DESCRIPTION 
                "added atvInputIrdetoMode
                "
            REVISION "201310011800Z"		-- October 01, 2013 at 18:00 GMT
            DESCRIPTION 
                "initial release. 
                removed atvInpCmnInputIdx from all atvInput tables. 
                atvNicamCfgPreemphasis is showing the correct value now. 
                added clarification to description of atvInpAudioClipping"
            REVISION "201302041600Z"		-- February 04, 2013 at 16:00 GMT
            DESCRIPTION 
                "Preliminary version."
            ::= { rsXx9MibModule 9 }

        
    
--
-- Textual conventions
--
    
        SoundMode ::= TEXTUAL-CONVENTION
            STATUS current
            DESCRIPTION 
                "Description."
            SYNTAX INTEGER
                {
                carrierOff(1),
                modulationOff(2),
                on(3)
                }

    
--
-- Node definitions
--
    
        rsXx9AtvNotifications OBJECT IDENTIFIER ::= { rsXx9Atv 0 }

        
        rsXx9AtvObjects OBJECT IDENTIFIER ::= { rsXx9Atv 1 }

        
        atvInput OBJECT IDENTIFIER ::= { rsXx9AtvObjects 1 }

        
        atvInputCommonTable OBJECT-TYPE
            SYNTAX SEQUENCE OF AtvInputCommonEntry
            MAX-ACCESS not-accessible
            STATUS current
            DESCRIPTION
                "Description."
            ::= { atvInput 1 }

        
        atvInputCommonEntry OBJECT-TYPE
            SYNTAX AtvInputCommonEntry
            MAX-ACCESS not-accessible
            STATUS current
            DESCRIPTION
                "Description."
            INDEX { atvInpCmnTxIdx, atvInpCmnExcIdx }
            ::= { atvInputCommonTable 1 }

        
        AtvInputCommonEntry ::=
            SEQUENCE { 
                atvInpCmnTxIdx
                    IndexTransmitter,
                atvInpCmnExcIdx
                    IndexAB,
                atvInpCmnInputIdx
                    INTEGER,
                atvInpCmnDatalineInfo
                    INTEGER,
                atvInpCmnInputImpedance
                    INTEGER,
                atvInpCmnAudioLowpass
                    SwitchOnOff,
                atvInpCmnNicam728Datastream
                    TruthValue,
                atvInputIrdetoMode
                    INTEGER
             }

        atvInpCmnTxIdx OBJECT-TYPE
            SYNTAX IndexTransmitter
            MAX-ACCESS not-accessible
            STATUS current
            DESCRIPTION
                "The transmitter index."
            ::= { atvInputCommonEntry 1 }

        
        atvInpCmnExcIdx OBJECT-TYPE
            SYNTAX IndexAB
            MAX-ACCESS not-accessible
            STATUS current
            DESCRIPTION
                "This index distinguishes the exiters.
                Necessary if you have dual drive transmitters."
            ::= { atvInputCommonEntry 2 }

        
        atvInpCmnInputIdx OBJECT-TYPE
            SYNTAX INTEGER
                {
                input1(1),
                input2(2)
                }
            MAX-ACCESS read-only
            STATUS obsolete
            DESCRIPTION
                "Obsolete input index."
            ::= { atvInputCommonEntry 3 }

        
        atvInpCmnDatalineInfo OBJECT-TYPE
            SYNTAX INTEGER
                {
                none(1),
                mono(2),
                stereo(3),
                dual(4)
                }
            MAX-ACCESS read-only
            STATUS current
            DESCRIPTION
                "Description."
            ::= { atvInputCommonEntry 4 }

        
        atvInpCmnInputImpedance OBJECT-TYPE
            SYNTAX INTEGER
                {
                sixHundredOhm(1),
                highImpedance(2)
                }
            MAX-ACCESS read-write
            STATUS current
            DESCRIPTION
                "Description."
            ::= { atvInputCommonEntry 5 }

        
        atvInpCmnAudioLowpass OBJECT-TYPE
            SYNTAX SwitchOnOff
            MAX-ACCESS read-write
            STATUS current
            DESCRIPTION
                "Switche lowpass filter for FM tone on or off."
            ::= { atvInputCommonEntry 6 }

        
        atvInpCmnNicam728Datastream OBJECT-TYPE
            SYNTAX TruthValue
            MAX-ACCESS read-only
            STATUS current
            DESCRIPTION
                "No digital nicam datastream was detected at Input Nicam. 
                If you want to use analog audio inputs set the 'Nicam Mode' 
                to 'Coder' in coder config menu.
                
                Available in modulator mode only.
                "
            ::= { atvInputCommonEntry 7 }

        
        atvInputIrdetoMode OBJECT-TYPE
            SYNTAX INTEGER
                {
                standard(1),
                irdeto(2)
                }
            MAX-ACCESS read-only
            STATUS current
            DESCRIPTION
                "Description."
            ::= { atvInputCommonEntry 8 }

        
        atvInputVideoTable OBJECT-TYPE
            SYNTAX SEQUENCE OF AtvInputVideoEntry
            MAX-ACCESS not-accessible
            STATUS current
            DESCRIPTION
                "Description."
            ::= { atvInput 2 }

        
        atvInputVideoEntry OBJECT-TYPE
            SYNTAX AtvInputVideoEntry
            MAX-ACCESS not-accessible
            STATUS current
            DESCRIPTION
                "Description."
            AUGMENTS { atvInputCommonEntry }
            ::= { atvInputVideoTable 1 }

        
        AtvInputVideoEntry ::=
            SEQUENCE { 
                atvInpVideoWhiteAmplitude
                    Unsigned32,
                atvInpVideoWhitePulseMonitoring
                    INTEGER,
                atvInpVideoSyncAmplitude
                    Unsigned32,
                atvInpVideoSyncMonitoring
                    INTEGER,
                atvInpVideoClipping
                    NotificationState,
                atvInpVideoNominalAmplitude
                    INTEGER
             }

        atvInpVideoWhiteAmplitude OBJECT-TYPE
            SYNTAX Unsigned32 (0..1300)
            UNITS "mV"
            MAX-ACCESS read-only
            STATUS current
            DESCRIPTION
                "Measured value input amplitude white."
            ::= { atvInputVideoEntry 1 }

        
        atvInpVideoWhitePulseMonitoring OBJECT-TYPE
            SYNTAX INTEGER
                {
                none(1),
                ok(2),
                lem40(3),
                lem30(4),
                gep30(5),
                gep40(6)
                }
            MAX-ACCESS read-only
            STATUS current
            DESCRIPTION
                "White pulse monitoring:
                none(1)  - check row with white impulse not found
                ok(2)    - white impulse found and level ok
                lem40(3) - level of white impulse more than 40% below nominal level
                lem30(4) - level of white impulse more than 30% below nominal level
                gep30(5) - level of white impulse more than 30% above nominal level
                gep40(6) - level of white impulse more than 40% above nominal level"
            ::= { atvInputVideoEntry 2 }

        
        atvInpVideoSyncAmplitude OBJECT-TYPE
            SYNTAX Unsigned32 (0..600)
            UNITS "mV"
            MAX-ACCESS read-only
            STATUS current
            DESCRIPTION
                "Indicates the measured input amplitude of the sync pulse."
            ::= { atvInputVideoEntry 3 }

        
        atvInpVideoSyncMonitoring OBJECT-TYPE
            SYNTAX INTEGER
                {
                ok(1),
                noV(2),
                noHV(3),
                lowLevel(4)
                }
            MAX-ACCESS read-only
            STATUS current
            DESCRIPTION
                "Indicates the status of sync-pulse monitoring of the input signal. 
                
                Ok:  A standard-compliant input signal is being applied. 
                No V:No V-pulse frame is detected. 
                No H+V: No V-pulse or H-pulse frame is detected. 
                Low Level: The sync-pulse amplitude is less than 50% of the nominal 
                sync-pulse amplitude; the processed signal is, however, available at 
                the encoder output.
                "
            ::= { atvInputVideoEntry 4 }

        
        atvInpVideoClipping OBJECT-TYPE
            SYNTAX NotificationState
            MAX-ACCESS read-only
            STATUS current
            DESCRIPTION
                "Indicates the status of possible video input signal clipping. 
                
                off(2)   - no clipping: The video input signal is within the valid range. 
                fault(3) - clipping: The video input signal is clipped.
                warning(4)   - no headroom: The video input signal is just off a clipping boundary. 
                "
            ::= { atvInputVideoEntry 5 }

        
        atvInpVideoNominalAmplitude OBJECT-TYPE
            SYNTAX INTEGER
                {
                dotSeven(1),
                one(2)
                }
            MAX-ACCESS read-write
            STATUS current
            DESCRIPTION
                "Indicates the set video input amplitude. Nominal input amplitude on 75 Ohm:
                dotSeven(1) - 0.7 V
                one(2)      - 1.0 V
                
                "
            ::= { atvInputVideoEntry 6 }

        
        atvInputAudioTable OBJECT-TYPE
            SYNTAX SEQUENCE OF AtvInputAudioEntry
            MAX-ACCESS not-accessible
            STATUS current
            DESCRIPTION
                "Description."
            ::= { atvInput 3 }

        
        atvInputAudioEntry OBJECT-TYPE
            SYNTAX AtvInputAudioEntry
            MAX-ACCESS not-accessible
            STATUS current
            DESCRIPTION
                "Description."
            INDEX { atvInpCmnTxIdx, atvInpCmnExcIdx, atvInpAudioNfSignalIdx }
            ::= { atvInputAudioTable 1 }

        
        AtvInputAudioEntry ::=
            SEQUENCE { 
                atvInpAudioNfSignalIdx
                    INTEGER,
                atvInpAudioCurrentLevel
                    Unsigned32,
                atvInpAudioClipping
                    TruthValue,
                atvInpAudioNominalLevel
                    Integer32
             }

        atvInpAudioNfSignalIdx OBJECT-TYPE
            SYNTAX INTEGER
                {
                af1(1),
                af2(2)
                }
            MAX-ACCESS not-accessible
            STATUS current
            DESCRIPTION
                "NF signal index."
            ::= { atvInputAudioEntry 1 }

        
        atvInpAudioCurrentLevel OBJECT-TYPE
            SYNTAX Unsigned32
            UNITS "per thousand"
            MAX-ACCESS read-only
            STATUS current
            DESCRIPTION
                "Indicates the current input level at the FM sound modulator for the
                AF signal (as a percentage of the maximum drive level)."
            ::= { atvInputAudioEntry 2 }

        
        atvInpAudioClipping OBJECT-TYPE
            SYNTAX TruthValue
            MAX-ACCESS read-only
            STATUS current
            DESCRIPTION
                "Indicates the status of possible clipping of the AF input signal. 
                The following displays (with color signalization) are possible: 
                
                NO CLIPPING: AF input signal AF2 is within the valid range. 
                CLIPPING: AF input signal AF2 is clipped because it has 
                exceeded the maximum permissible input level.
                "
            ::= { atvInputAudioEntry 3 }

        
        atvInpAudioNominalLevel OBJECT-TYPE
            SYNTAX Integer32 (-1200..1200)
            UNITS "1/100 dBu"
            MAX-ACCESS read-write
            STATUS current
            DESCRIPTION
                "Nominal input level of NF signal."
            ::= { atvInputAudioEntry 4 }

        
        atvInputNicamTable OBJECT-TYPE
            SYNTAX SEQUENCE OF AtvInputNicamEntry
            MAX-ACCESS not-accessible
            STATUS current
            DESCRIPTION
                "Description."
            ::= { atvInput 4 }

        
        atvInputNicamEntry OBJECT-TYPE
            SYNTAX AtvInputNicamEntry
            MAX-ACCESS not-accessible
            STATUS current
            DESCRIPTION
                "Description."
            AUGMENTS { atvInputAudioEntry }
            ::= { atvInputNicamTable 1 }

        
        AtvInputNicamEntry ::=
            SEQUENCE { 
                atvInpNicamCurrentLevel
                    Unsigned32,
                atvInpNicamClipping
                    TruthValue,
                atvInpNicamGainAdjustment
                    Integer32
             }

        atvInpNicamCurrentLevel OBJECT-TYPE
            SYNTAX Unsigned32
            UNITS "per thousand"
            MAX-ACCESS read-only
            STATUS current
            DESCRIPTION
                "Current input level on NICAM coder for NF signal.
                
                Available in coder mode only.
                
                "
            ::= { atvInputNicamEntry 1 }

        
        atvInpNicamClipping OBJECT-TYPE
            SYNTAX TruthValue
            MAX-ACCESS read-only
            STATUS current
            DESCRIPTION
                "The gain for nicam input is too high. 
                Reduce the gain setting in Input AF 2 menu.
                
                Available in coder mode only."
            ::= { atvInputNicamEntry 2 }

        
        atvInpNicamGainAdjustment OBJECT-TYPE
            SYNTAX Integer32 (-600..600)
            UNITS "milli Bel"
            MAX-ACCESS read-write
            STATUS current
            DESCRIPTION
                "Indicates the set input level for the NICAM signal that is fed 
                to the integrated NICAM coder. The setting can be changed 
                here for matching purposes.
                
                Available in coder mode only."
            ::= { atvInputNicamEntry 3 }

        
        atvCommon OBJECT IDENTIFIER ::= { rsXx9AtvObjects 2 }

        
        atvCommonStateTable OBJECT-TYPE
            SYNTAX SEQUENCE OF AtvCommonStateEntry
            MAX-ACCESS not-accessible
            STATUS current
            DESCRIPTION
                "Description."
            ::= { atvCommon 2 }

        
        atvCommonStateEntry OBJECT-TYPE
            SYNTAX AtvCommonStateEntry
            MAX-ACCESS not-accessible
            STATUS current
            DESCRIPTION
                "Description."
            INDEX { atvCmnStTxIdx, atvCmnStExcIdx }
            ::= { atvCommonStateTable 1 }

        
        AtvCommonStateEntry ::=
            SEQUENCE { 
                atvCmnStTxIdx
                    IndexTransmitter,
                atvCmnStExcIdx
                    IndexAB,
                atvCmnStCurrentAudioMode
                    INTEGER
             }

        atvCmnStTxIdx OBJECT-TYPE
            SYNTAX IndexTransmitter
            MAX-ACCESS not-accessible
            STATUS current
            DESCRIPTION
                "The transmitter index."
            ::= { atvCommonStateEntry 1 }

        
        atvCmnStExcIdx OBJECT-TYPE
            SYNTAX IndexAB
            MAX-ACCESS not-accessible
            STATUS current
            DESCRIPTION
                "This index distinguishes the exiters.
                Necessary if you have dual drive transmitters."
            ::= { atvCommonStateEntry 2 }

        
        atvCmnStCurrentAudioMode OBJECT-TYPE
            SYNTAX INTEGER
                {
                mono(1),
                stereo(2),
                dual(3)
                }
            MAX-ACCESS read-only
            STATUS current
            DESCRIPTION
                "The current audio mode."
            ::= { atvCommonStateEntry 3 }

        
        atvCommonConfigTable OBJECT-TYPE
            SYNTAX SEQUENCE OF AtvCommonConfigEntry
            MAX-ACCESS not-accessible
            STATUS current
            DESCRIPTION
                "Description."
            ::= { atvCommon 3 }

        
        atvCommonConfigEntry OBJECT-TYPE
            SYNTAX AtvCommonConfigEntry
            MAX-ACCESS not-accessible
            STATUS current
            DESCRIPTION
                "Description."
            AUGMENTS { atvCommonStateEntry }
            ::= { atvCommonConfigTable 1 }

        
        AtvCommonConfigEntry ::=
            SEQUENCE { 
                atvCmnCfgTvStandard
                    INTEGER,
                atvCmnCfgSoundCarrierSelect
                    INTEGER,
                atvCmnCfgCoderMode
                    INTEGER,
                atvCmnCfgVisionSound1
                    Integer32,
                atvCmnCfgVisionSound2
                    Integer32,
                atvCmnCfgResidual
                    Unsigned32
             }

        atvCmnCfgTvStandard OBJECT-TYPE
            SYNTAX INTEGER
                {
                dk(2),
                i(3),
                i1(4),
                k1(5),
                b(6),
                g(7),
                m(8),
                m1(9),
                n(10)
                }
            MAX-ACCESS read-write
            STATUS current
            DESCRIPTION
                "Selection of ATV standard."
            ::= { atvCommonConfigEntry 1 }

        
        atvCmnCfgSoundCarrierSelect OBJECT-TYPE
            SYNTAX INTEGER
                {
                singleCarrier(1),
                dualCarrier(2)
                }
            MAX-ACCESS read-write
            STATUS current
            DESCRIPTION
                "Number of sound subcarriers (for standards B, G, D/K, I, I1, K1). 
                
                The following settings are possible here: 
                Single Carrier: one sound subcarrier
                Dual Carrier: two sound subcarriers
                "
            ::= { atvCommonConfigEntry 2 }

        
        atvCmnCfgCoderMode OBJECT-TYPE
            SYNTAX INTEGER
                {
                off(1),
                mono(2),
                stereo(3),
                dual(4),
                auto(5)
                }
            MAX-ACCESS read-write
            STATUS current
            DESCRIPTION
                "Selection of audio mode.
                
                The following settings have a special meaning: 
                Off: Dual-sound is set as the audio mode. 
                Mono: The AF1 input signal is routed to audio carrier one. 
                Stereo: The two AF input signals contain the left and right channel of a stereo signal. 
                Dual: The two AF input signals provide independent audio information for dual-sound mode. 
                Auto (Dataline):The audio mode is read out from the audio data line present in the picture signal.
                "
            ::= { atvCommonConfigEntry 3 }

        
        atvCmnCfgVisionSound1 OBJECT-TYPE
            SYNTAX Integer32 (-150..-50)
            UNITS "centi Bel"
            MAX-ACCESS read-write
            STATUS current
            DESCRIPTION
                "value for sound subcarrier level 1 referenced to the peak envelope power of the vision carrier."
            ::= { atvCommonConfigEntry 4 }

        
        atvCmnCfgVisionSound2 OBJECT-TYPE
            SYNTAX Integer32 (-270..-170)
            UNITS "centi Bel"
            MAX-ACCESS read-write
            STATUS current
            DESCRIPTION
                "value for sound subcarrier level 2 referenced to the peak envelope power of the vision carrier."
            ::= { atvCommonConfigEntry 5 }

        
        atvCmnCfgResidual OBJECT-TYPE
            SYNTAX Unsigned32 (80..250)
            UNITS "per thousand"
            MAX-ACCESS read-write
            STATUS current
            DESCRIPTION
                "value for the residual carrier."
            ::= { atvCommonConfigEntry 6 }

        
        atvCommonTestTable OBJECT-TYPE
            SYNTAX SEQUENCE OF AtvCommonTestEntry
            MAX-ACCESS not-accessible
            STATUS current
            DESCRIPTION
                "Configures the test mode of the exciter."
            ::= { atvCommon 4 }

        
        atvCommonTestEntry OBJECT-TYPE
            SYNTAX AtvCommonTestEntry
            MAX-ACCESS not-accessible
            STATUS current
            DESCRIPTION
                "An entry in the atvCommonTestTable."
            AUGMENTS { atvCommonStateEntry }
            ::= { atvCommonTestTable 1 }

        
        AtvCommonTestEntry ::=
            SEQUENCE { 
                atvCommonTestSignal
                    INTEGER
             }

        atvCommonTestSignal OBJECT-TYPE
            SYNTAX INTEGER
                {
                off(1),
                singleCarrier(3)
                }
            MAX-ACCESS read-write
            STATUS current
            DESCRIPTION
                "off(1)           - no test mode
                singleCarrier(3) - produces an unmodulated carrier
                                   on a selected output frequency"
            ::= { atvCommonTestEntry 1 }

        
        atvVideo OBJECT IDENTIFIER ::= { rsXx9AtvObjects 3 }

        
        atvVideoStateTable OBJECT-TYPE
            SYNTAX SEQUENCE OF AtvVideoStateEntry
            MAX-ACCESS not-accessible
            STATUS current
            DESCRIPTION
                "Description."
            ::= { atvVideo 2 }

        
        atvVideoStateEntry OBJECT-TYPE
            SYNTAX AtvVideoStateEntry
            MAX-ACCESS not-accessible
            STATUS current
            DESCRIPTION
                "Description."
            INDEX { atvVideoStTxIdx, atvVideoStExcIdx }
            ::= { atvVideoStateTable 1 }

        
        AtvVideoStateEntry ::=
            SEQUENCE { 
                atvVideoStTxIdx
                    IndexTransmitter,
                atvVideoStExcIdx
                    IndexAB,
                atvVideoStWhiteAmplitudeOutput
                    Unsigned32,
                atvVideoStMemoryGain
                    Unsigned32,
                atvVideoStCurrentGainSource
                    INTEGER,
                atvVideoStLimiterActive
                    TruthValue,
                atvVideoStSyncAmplitudeOutput
                    Unsigned32
             }

        atvVideoStTxIdx OBJECT-TYPE
            SYNTAX IndexTransmitter
            MAX-ACCESS not-accessible
            STATUS current
            DESCRIPTION
                "The transmitter index."
            ::= { atvVideoStateEntry 1 }

        
        atvVideoStExcIdx OBJECT-TYPE
            SYNTAX IndexAB
            MAX-ACCESS not-accessible
            STATUS current
            DESCRIPTION
                "This index distinguishes the exiters.
                Necessary if you have dual drive transmitters."
            ::= { atvVideoStateEntry 2 }

        
        atvVideoStWhiteAmplitudeOutput OBJECT-TYPE
            SYNTAX Unsigned32
            UNITS "mV"
            MAX-ACCESS read-only
            STATUS current
            DESCRIPTION
                "Description."
            ::= { atvVideoStateEntry 3 }

        
        atvVideoStMemoryGain OBJECT-TYPE
            SYNTAX Unsigned32
            UNITS "per thousand"
            MAX-ACCESS read-only
            STATUS current
            DESCRIPTION
                "Description."
            ::= { atvVideoStateEntry 4 }

        
        atvVideoStCurrentGainSource OBJECT-TYPE
            SYNTAX INTEGER
                {
                manual(1),
                memory(2),
                automatic(3)
                }
            MAX-ACCESS read-only
            STATUS current
            DESCRIPTION
                "Description."
            ::= { atvVideoStateEntry 5 }

        
        atvVideoStLimiterActive OBJECT-TYPE
            SYNTAX TruthValue
            MAX-ACCESS read-only
            STATUS current
            DESCRIPTION
                "Description."
            ::= { atvVideoStateEntry 6 }

        
        atvVideoStSyncAmplitudeOutput OBJECT-TYPE
            SYNTAX Unsigned32
            UNITS "mV"
            MAX-ACCESS read-only
            STATUS current
            DESCRIPTION
                "Description."
            ::= { atvVideoStateEntry 7 }

        
        atvVideoConfigTable OBJECT-TYPE
            SYNTAX SEQUENCE OF AtvVideoConfigEntry
            MAX-ACCESS not-accessible
            STATUS current
            DESCRIPTION
                "Description."
            ::= { atvVideo 3 }

        
        atvVideoConfigEntry OBJECT-TYPE
            SYNTAX AtvVideoConfigEntry
            MAX-ACCESS not-accessible
            STATUS current
            DESCRIPTION
                "Description."
            AUGMENTS { atvVideoStateEntry }
            ::= { atvVideoConfigTable 1 }

        
        AtvVideoConfigEntry ::=
            SEQUENCE { 
                atvVideoCfgAutomatic
                    SwitchOnOff,
                atvVideoCfgGainSource
                    INTEGER,
                atvVideoCfgManualGain
                    Integer32,
                atvVideoCfgTestLine
                    Unsigned32,
                atvVideoCfgDataLine
                    Unsigned32,
                atvVideoCfgLimiter
                    SwitchOnOff,
                atvVideoCfgThreshold
                    Unsigned32,
                atvVideoCfgSyncImpulsRegeneration
                    SwitchOnOff,
                atvVideoCfgSyncAmplitude
                    Unsigned32,
                atvVideoCfgReceiverPreEqualization
                    SwitchOnOff,
                atvVideoCfgDiplexer
                    SwitchOnOff,
                atvVideoCfgDiplexerPeaking
                    Unsigned32
             }

        atvVideoCfgAutomatic OBJECT-TYPE
            SYNTAX SwitchOnOff
            MAX-ACCESS read-write
            STATUS current
            DESCRIPTION
                "Description."
            ::= { atvVideoConfigEntry 1 }

        
        atvVideoCfgGainSource OBJECT-TYPE
            SYNTAX INTEGER
                {
                manual(1),
                memory(2)
                }
            MAX-ACCESS read-write
            STATUS current
            DESCRIPTION
                "Description."
            ::= { atvVideoConfigEntry 2 }

        
        atvVideoCfgManualGain OBJECT-TYPE
            SYNTAX Integer32 (-100..100)
            UNITS "per thousand"
            MAX-ACCESS read-write
            STATUS current
            DESCRIPTION
                "Description."
            ::= { atvVideoConfigEntry 3 }

        
        atvVideoCfgTestLine OBJECT-TYPE
            SYNTAX Unsigned32 (16..22 | 329..335)
            MAX-ACCESS read-write
            STATUS current
            DESCRIPTION
                "Description."
            ::= { atvVideoConfigEntry 4 }

        
        atvVideoCfgDataLine OBJECT-TYPE
            SYNTAX Unsigned32 (10..22)
            MAX-ACCESS read-write
            STATUS current
            DESCRIPTION
                "Description."
            ::= { atvVideoConfigEntry 5 }

        
        atvVideoCfgLimiter OBJECT-TYPE
            SYNTAX SwitchOnOff
            MAX-ACCESS read-write
            STATUS current
            DESCRIPTION
                "Description."
            ::= { atvVideoConfigEntry 6 }

        
        atvVideoCfgThreshold OBJECT-TYPE
            SYNTAX Unsigned32 (900..1200)
            UNITS "per thousand"
            MAX-ACCESS read-write
            STATUS current
            DESCRIPTION
                "Description."
            ::= { atvVideoConfigEntry 7 }

        
        atvVideoCfgSyncImpulsRegeneration OBJECT-TYPE
            SYNTAX SwitchOnOff
            MAX-ACCESS read-write
            STATUS current
            DESCRIPTION
                "Description."
            ::= { atvVideoConfigEntry 8 }

        
        atvVideoCfgSyncAmplitude OBJECT-TYPE
            SYNTAX Unsigned32 (200..500)
            UNITS "mV"
            MAX-ACCESS read-write
            STATUS current
            DESCRIPTION
                "Description."
            ::= { atvVideoConfigEntry 9 }

        
        atvVideoCfgReceiverPreEqualization OBJECT-TYPE
            SYNTAX SwitchOnOff
            MAX-ACCESS read-write
            STATUS current
            DESCRIPTION
                "Indicates whether receiver pre-equalization is switched on. 
                Receiver pre-equalization can be switched on or off here.
                "
            ::= { atvVideoConfigEntry 10 }

        
        atvVideoCfgDiplexer OBJECT-TYPE
            SYNTAX SwitchOnOff
            MAX-ACCESS read-write
            STATUS current
            DESCRIPTION
                "Description."
            ::= { atvVideoConfigEntry 11 }

        
        atvVideoCfgDiplexerPeaking OBJECT-TYPE
            SYNTAX Unsigned32 (1..25)
            UNITS "centi Bel"
            MAX-ACCESS read-write
            STATUS current
            DESCRIPTION
                "Description."
            ::= { atvVideoConfigEntry 12 }

        
        atvAudio OBJECT IDENTIFIER ::= { rsXx9AtvObjects 4 }

        
        atvAudioStateTable OBJECT-TYPE
            SYNTAX SEQUENCE OF AtvAudioStateEntry
            MAX-ACCESS not-accessible
            STATUS current
            DESCRIPTION
                "Description."
            ::= { atvAudio 2 }

        
        atvAudioStateEntry OBJECT-TYPE
            SYNTAX AtvAudioStateEntry
            MAX-ACCESS not-accessible
            STATUS current
            DESCRIPTION
                "Description."
            INDEX { atvAudioStTxIdx, atvAudioStExcIdx }
            ::= { atvAudioStateTable 1 }

        
        AtvAudioStateEntry ::=
            SEQUENCE { 
                atvAudioStTxIdx
                    IndexTransmitter,
                atvAudioStExcIdx
                    IndexAB,
                atvAudioStCurrentDeviationCarrier1
                    Unsigned32,
                atvAudioStCurrentDeviationCarrier2
                    Unsigned32,
                atvAudioStCurrentPilotDeviation
                    Unsigned32,
                atvAudioStLimiterCarrier1
                    TruthValue,
                atvAudioStLimiterCarrier2
                    TruthValue
             }

        atvAudioStTxIdx OBJECT-TYPE
            SYNTAX IndexTransmitter
            MAX-ACCESS not-accessible
            STATUS current
            DESCRIPTION
                "The transmitter index."
            ::= { atvAudioStateEntry 1 }

        
        atvAudioStExcIdx OBJECT-TYPE
            SYNTAX IndexAB
            MAX-ACCESS not-accessible
            STATUS current
            DESCRIPTION
                "This index distinguishes the exiters.
                Necessary if you have dual drive transmitters."
            ::= { atvAudioStateEntry 2 }

        
        atvAudioStCurrentDeviationCarrier1 OBJECT-TYPE
            SYNTAX Unsigned32
            UNITS "Hz"
            MAX-ACCESS read-only
            STATUS current
            DESCRIPTION
                "Description."
            ::= { atvAudioStateEntry 3 }

        
        atvAudioStCurrentDeviationCarrier2 OBJECT-TYPE
            SYNTAX Unsigned32
            UNITS "Hz"
            MAX-ACCESS read-only
            STATUS current
            DESCRIPTION
                "Description."
            ::= { atvAudioStateEntry 4 }

        
        atvAudioStCurrentPilotDeviation OBJECT-TYPE
            SYNTAX Unsigned32
            UNITS "Hz"
            MAX-ACCESS read-only
            STATUS current
            DESCRIPTION
                "Description."
            ::= { atvAudioStateEntry 5 }

        
        atvAudioStLimiterCarrier1 OBJECT-TYPE
            SYNTAX TruthValue
            MAX-ACCESS read-only
            STATUS current
            DESCRIPTION
                "Description."
            ::= { atvAudioStateEntry 6 }

        
        atvAudioStLimiterCarrier2 OBJECT-TYPE
            SYNTAX TruthValue
            MAX-ACCESS read-only
            STATUS current
            DESCRIPTION
                "Description."
            ::= { atvAudioStateEntry 7 }

        
        atvAudioConfigTable OBJECT-TYPE
            SYNTAX SEQUENCE OF AtvAudioConfigEntry
            MAX-ACCESS not-accessible
            STATUS current
            DESCRIPTION
                "Description."
            ::= { atvAudio 3 }

        
        atvAudioConfigEntry OBJECT-TYPE
            SYNTAX AtvAudioConfigEntry
            MAX-ACCESS not-accessible
            STATUS current
            DESCRIPTION
                "Description."
            AUGMENTS { atvAudioStateEntry }
            ::= { atvAudioConfigTable 1 }

        
        AtvAudioConfigEntry ::=
            SEQUENCE { 
                atvAudioCfgIrtNicam
                    INTEGER,
                atvAudioCfgPreemphase
                    SwitchOnOff,
                atvAudioCfgNominalDeviationAF1
                    Unsigned32,
                atvAudioCfgNominalDeviationAF2
                    Unsigned32,
                atvAudioCfgPilotGain
                    Integer32,
                atvAudioCfgPilot
                    SwitchOnOff,
                atvAudioCfgSoundModeCarrier1
                    SoundMode,
                atvAudioCfgSoundModeCarrier2
                    SoundMode,
                atvAudioCfgLimiterThreshold
                    Unsigned32,
                atvAudioCfgDeviationLimiter
                    SwitchOnOff,
                atvAudioCfgWarningAbove
                    Unsigned32,
                atvAudioCfgPrecorrectionChannel1
                    SwitchOnOff,
                atvAudioCfgPrecorrectionChannel2
                    SwitchOnOff,
                atvAudioCfgInsetPoint1Channel1
                    Unsigned32,
                atvAudioCfgInsetPoint1Channel2
                    Unsigned32,
                atvAudioCfgSlope1Channel1
                    Integer32,
                atvAudioCfgSlope1Channel2
                    Integer32,
                atvAudioCfgInsetPoint2Channel1
                    Unsigned32,
                atvAudioCfgInsetPoint2Channel2
                    Unsigned32,
                atvAudioCfgSlope2Channel1
                    Integer32,
                atvAudioCfgSlope2Channel2
                    Integer32
             }

        atvAudioCfgIrtNicam OBJECT-TYPE
            SYNTAX INTEGER
                {
                irt(1),
                nicam(2)
                }
            MAX-ACCESS read-write
            STATUS current
            DESCRIPTION
                "Description."
            ::= { atvAudioConfigEntry 1 }

        
        atvAudioCfgPreemphase OBJECT-TYPE
            SYNTAX SwitchOnOff
            MAX-ACCESS read-write
            STATUS current
            DESCRIPTION
                "Description."
            ::= { atvAudioConfigEntry 2 }

        
        atvAudioCfgNominalDeviationAF1 OBJECT-TYPE
            SYNTAX Unsigned32 (20000..75000)
            UNITS "Hz"
            MAX-ACCESS read-write
            STATUS current
            DESCRIPTION
                "Description."
            ::= { atvAudioConfigEntry 3 }

        
        atvAudioCfgNominalDeviationAF2 OBJECT-TYPE
            SYNTAX Unsigned32 (20000..75000)
            UNITS "Hz"
            MAX-ACCESS read-write
            STATUS current
            DESCRIPTION
                "Description."
            ::= { atvAudioConfigEntry 4 }

        
        atvAudioCfgPilotGain OBJECT-TYPE
            SYNTAX Integer32 (-1900..-1200)
            UNITS "1/100 dBu"
            MAX-ACCESS read-write
            STATUS current
            DESCRIPTION
                "Description."
            ::= { atvAudioConfigEntry 5 }

        
        atvAudioCfgPilot OBJECT-TYPE
            SYNTAX SwitchOnOff
            MAX-ACCESS read-write
            STATUS current
            DESCRIPTION
                "Description."
            ::= { atvAudioConfigEntry 6 }

        
        atvAudioCfgSoundModeCarrier1 OBJECT-TYPE
            SYNTAX SoundMode
            MAX-ACCESS read-write
            STATUS current
            DESCRIPTION
                "Description."
            ::= { atvAudioConfigEntry 7 }

        
        atvAudioCfgSoundModeCarrier2 OBJECT-TYPE
            SYNTAX SoundMode
            MAX-ACCESS read-write
            STATUS current
            DESCRIPTION
                "Description."
            ::= { atvAudioConfigEntry 8 }

        
        atvAudioCfgLimiterThreshold OBJECT-TYPE
            SYNTAX Unsigned32 (50000..120000)
            UNITS "Hz"
            MAX-ACCESS read-write
            STATUS current
            DESCRIPTION
                "Description."
            ::= { atvAudioConfigEntry 9 }

        
        atvAudioCfgDeviationLimiter OBJECT-TYPE
            SYNTAX SwitchOnOff
            MAX-ACCESS read-write
            STATUS current
            DESCRIPTION
                "Description."
            ::= { atvAudioConfigEntry 10 }

        
        atvAudioCfgWarningAbove OBJECT-TYPE
            SYNTAX Unsigned32 (50000..250000)
            UNITS "Hz"
            MAX-ACCESS read-write
            STATUS current
            DESCRIPTION
                "Description."
            ::= { atvAudioConfigEntry 11 }

        
        atvAudioCfgPrecorrectionChannel1 OBJECT-TYPE
            SYNTAX SwitchOnOff
            MAX-ACCESS read-write
            STATUS current
            DESCRIPTION
                "Indicates whether the sound phase shifter for carrier 1 is switched on. 
                The setting can be changed here.
                "
            ::= { atvAudioConfigEntry 12 }

        
        atvAudioCfgPrecorrectionChannel2 OBJECT-TYPE
            SYNTAX SwitchOnOff
            MAX-ACCESS read-write
            STATUS current
            DESCRIPTION
                "Indicates whether the sound phase shifter for carrier 1 is switched on. 
                The setting can be changed here.
                "
            ::= { atvAudioConfigEntry 13 }

        
        atvAudioCfgInsetPoint1Channel1 OBJECT-TYPE
            SYNTAX Unsigned32 (0..1000)
            UNITS "per thousand"
            MAX-ACCESS read-write
            STATUS current
            DESCRIPTION
                "Indicates the first position defined for the respective onset point of the 
                phase shifter (referenced to modulation of the picture signal)
                "
            ::= { atvAudioConfigEntry 14 }

        
        atvAudioCfgInsetPoint1Channel2 OBJECT-TYPE
            SYNTAX Unsigned32 (0..1000)
            UNITS "per thousand"
            MAX-ACCESS read-write
            STATUS current
            DESCRIPTION
                "Indicates the first position defined for the respective onset point of the 
                phase shifter (referenced to modulation of the picture signal)
                "
            ::= { atvAudioConfigEntry 15 }

        
        atvAudioCfgSlope1Channel1 OBJECT-TYPE
            SYNTAX Integer32 (-500..500)
            UNITS "per thousand"
            MAX-ACCESS read-write
            STATUS current
            DESCRIPTION
                "Indicates the value that has been set for the slope at the respective 
                onset point of the phase shifter.
                "
            ::= { atvAudioConfigEntry 16 }

        
        atvAudioCfgSlope1Channel2 OBJECT-TYPE
            SYNTAX Integer32 (-500..500)
            UNITS "per thousand"
            MAX-ACCESS read-write
            STATUS current
            DESCRIPTION
                "Indicates the value that has been set for the slope at the respective 
                onset point of the phase shifter.
                "
            ::= { atvAudioConfigEntry 17 }

        
        atvAudioCfgInsetPoint2Channel1 OBJECT-TYPE
            SYNTAX Unsigned32 (0..1000)
            UNITS "per thousand"
            MAX-ACCESS read-write
            STATUS current
            DESCRIPTION
                "Indicates the second position defined for the respective onset 
                point of the phase shifter (referenced to modulation of the 
                picture signal)
                "
            ::= { atvAudioConfigEntry 18 }

        
        atvAudioCfgInsetPoint2Channel2 OBJECT-TYPE
            SYNTAX Unsigned32 (0..1000)
            UNITS "per thousand"
            MAX-ACCESS read-write
            STATUS current
            DESCRIPTION
                "Indicates the second position defined for the respective onset 
                point of the phase shifter (referenced to modulation of the 
                picture signal)
                "
            ::= { atvAudioConfigEntry 19 }

        
        atvAudioCfgSlope2Channel1 OBJECT-TYPE
            SYNTAX Integer32 (-500..500)
            UNITS "per thousand"
            MAX-ACCESS read-write
            STATUS current
            DESCRIPTION
                "Indicates the value that has been set for the slope at 
                the respective onset point of the phase shifter.
                "
            ::= { atvAudioConfigEntry 20 }

        
        atvAudioCfgSlope2Channel2 OBJECT-TYPE
            SYNTAX Integer32 (-500..500)
            UNITS "per thousand"
            MAX-ACCESS read-write
            STATUS current
            DESCRIPTION
                "Indicates the value that has been set for the slope at 
                the respective onset point of the phase shifter.
                "
            ::= { atvAudioConfigEntry 21 }

        
        atvNicam OBJECT IDENTIFIER ::= { rsXx9AtvObjects 5 }

        
        atvNicamConfigTable OBJECT-TYPE
            SYNTAX SEQUENCE OF AtvNicamConfigEntry
            MAX-ACCESS not-accessible
            STATUS current
            DESCRIPTION
                "Description."
            ::= { atvNicam 3 }

        
        atvNicamConfigEntry OBJECT-TYPE
            SYNTAX AtvNicamConfigEntry
            MAX-ACCESS not-accessible
            STATUS current
            DESCRIPTION
                "Description."
            INDEX { atvNicamCfgTxIdx, atvNicamCfgExcIdx }
            ::= { atvNicamConfigTable 1 }

        
        AtvNicamConfigEntry ::=
            SEQUENCE { 
                atvNicamCfgTxIdx
                    IndexTransmitter,
                atvNicamCfgExcIdx
                    IndexAB,
                atvNicamCfgAudioMode
                    INTEGER,
                atvNicamCfgPreemphasis
                    SwitchOnOff,
                atvNicamCfgReserveSound
                    SwitchOnOff,
                atvNicamCfgNicamMode
                    INTEGER,
                atvNicamCfgNicamRolloff
                    INTEGER,
                atvNicamCfgSoundMode
                    SoundMode
             }

        atvNicamCfgTxIdx OBJECT-TYPE
            SYNTAX IndexTransmitter
            MAX-ACCESS not-accessible
            STATUS current
            DESCRIPTION
                "The transmitter index."
            ::= { atvNicamConfigEntry 1 }

        
        atvNicamCfgExcIdx OBJECT-TYPE
            SYNTAX IndexAB
            MAX-ACCESS not-accessible
            STATUS current
            DESCRIPTION
                "This index distinguishes the exiters.
                Necessary if you have dual drive transmitters."
            ::= { atvNicamConfigEntry 2 }

        
        atvNicamCfgAudioMode OBJECT-TYPE
            SYNTAX INTEGER
                {
                equalFM(1),
                monoData(2),
                stereo(3),
                dual(4)
                }
            MAX-ACCESS read-write
            STATUS current
            DESCRIPTION
                "Description."
            ::= { atvNicamConfigEntry 3 }

        
        atvNicamCfgPreemphasis OBJECT-TYPE
            SYNTAX SwitchOnOff
            MAX-ACCESS read-write
            STATUS current
            DESCRIPTION
                "Description."
            ::= { atvNicamConfigEntry 4 }

        
        atvNicamCfgReserveSound OBJECT-TYPE
            SYNTAX SwitchOnOff
            MAX-ACCESS read-write
            STATUS current
            DESCRIPTION
                "Description."
            ::= { atvNicamConfigEntry 5 }

        
        atvNicamCfgNicamMode OBJECT-TYPE
            SYNTAX INTEGER
                {
                coder(1),
                modulator(2)
                }
            MAX-ACCESS read-write
            STATUS current
            DESCRIPTION
                "Description."
            ::= { atvNicamConfigEntry 6 }

        
        atvNicamCfgNicamRolloff OBJECT-TYPE
            SYNTAX INTEGER
                {
                auto(1),
                pct40(2),
                pct100(3)
                }
            MAX-ACCESS read-write
            STATUS current
            DESCRIPTION
                "Description."
            ::= { atvNicamConfigEntry 7 }

        
        atvNicamCfgSoundMode OBJECT-TYPE
            SYNTAX SoundMode
            MAX-ACCESS read-write
            STATUS current
            DESCRIPTION
                "Description."
            ::= { atvNicamConfigEntry 8 }

        
        rsXx9AtvConformance OBJECT IDENTIFIER ::= { rsXx9Atv 2 }

        
        rsXx9AtvCompliances OBJECT IDENTIFIER ::= { rsXx9AtvConformance 1 }

        
        atvBasicCompliance MODULE-COMPLIANCE
            STATUS current
            DESCRIPTION 
                "The compliance statement for XX9000 ATV encoding."
            MODULE -- this module
                MANDATORY-GROUPS { atvObjsCommon, atvObjsVideo, atvObjsAudio, atvObjsNicam, atvObjsInput
                     }
            ::= { rsXx9AtvCompliances 1 }

        
        rsXx9AtvGroups OBJECT IDENTIFIER ::= { rsXx9AtvConformance 2 }

        
        atvObjsInput OBJECT-GROUP
            OBJECTS { atvInpCmnDatalineInfo, atvInpCmnInputImpedance, atvInpVideoWhiteAmplitude, atvInpVideoWhitePulseMonitoring, atvInpVideoSyncAmplitude, 
                atvInpVideoSyncMonitoring, atvInpVideoNominalAmplitude, atvInpAudioCurrentLevel, atvInpAudioClipping, atvInpAudioNominalLevel, 
                atvInpNicamCurrentLevel, atvInpNicamClipping, atvInpVideoClipping, atvInputIrdetoMode, atvInpNicamGainAdjustment, 
                atvInpCmnAudioLowpass, atvInpCmnNicam728Datastream }
            STATUS current
            DESCRIPTION 
                "Input ATV objects group."
            ::= { rsXx9AtvGroups 1 }

        
        atvObjsCommon OBJECT-GROUP
            OBJECTS { atvCmnStCurrentAudioMode, atvCmnCfgTvStandard, atvCmnCfgSoundCarrierSelect, atvCmnCfgCoderMode, atvCmnCfgVisionSound1, 
                atvCmnCfgVisionSound2, atvCmnCfgResidual, atvCommonTestSignal }
            STATUS current
            DESCRIPTION 
                "Common ATV objects group."
            ::= { rsXx9AtvGroups 2 }

        
        atvObjsVideo OBJECT-GROUP
            OBJECTS { atvVideoStWhiteAmplitudeOutput, atvVideoStMemoryGain, atvVideoStCurrentGainSource, atvVideoStLimiterActive, atvVideoStSyncAmplitudeOutput, 
                atvVideoCfgAutomatic, atvVideoCfgGainSource, atvVideoCfgManualGain, atvVideoCfgTestLine, atvVideoCfgDataLine, 
                atvVideoCfgLimiter, atvVideoCfgThreshold, atvVideoCfgSyncImpulsRegeneration, atvVideoCfgSyncAmplitude, atvVideoCfgReceiverPreEqualization, 
                atvVideoCfgDiplexer, atvVideoCfgDiplexerPeaking }
            STATUS current
            DESCRIPTION 
                "Video ATV objects group."
            ::= { rsXx9AtvGroups 3 }

        
        atvObjsAudio OBJECT-GROUP
            OBJECTS { atvAudioStCurrentDeviationCarrier1, atvAudioStCurrentDeviationCarrier2, atvAudioStCurrentPilotDeviation, atvAudioStLimiterCarrier1, atvAudioStLimiterCarrier2, 
                atvAudioCfgIrtNicam, atvAudioCfgPreemphase, atvAudioCfgNominalDeviationAF1, atvAudioCfgNominalDeviationAF2, atvAudioCfgPilotGain, 
                atvAudioCfgPilot, atvAudioCfgSoundModeCarrier1, atvAudioCfgSoundModeCarrier2, atvAudioCfgLimiterThreshold, atvAudioCfgDeviationLimiter, 
                atvAudioCfgWarningAbove, atvAudioCfgPrecorrectionChannel1, atvAudioCfgPrecorrectionChannel2, atvAudioCfgInsetPoint1Channel1, atvAudioCfgInsetPoint1Channel2, 
                atvAudioCfgSlope1Channel1, atvAudioCfgSlope1Channel2, atvAudioCfgInsetPoint2Channel1, atvAudioCfgInsetPoint2Channel2, atvAudioCfgSlope2Channel1, 
                atvAudioCfgSlope2Channel2 }
            STATUS current
            DESCRIPTION 
                "Audio ATV objects group."
            ::= { rsXx9AtvGroups 4 }

        
        atvObjsNicam OBJECT-GROUP
            OBJECTS { atvNicamCfgAudioMode, atvNicamCfgPreemphasis, atvNicamCfgReserveSound, atvNicamCfgNicamMode, atvNicamCfgNicamRolloff, 
                atvNicamCfgSoundMode }
            STATUS current
            DESCRIPTION 
                "NICAM ATV objects group."
            ::= { rsXx9AtvGroups 5 }

        
        atvObjsInputObsolete OBJECT-GROUP
            OBJECTS { atvInpCmnInputIdx }
            STATUS obsolete
            DESCRIPTION 
                "Obsolete input ATV objects group."
            ::= { rsXx9AtvGroups 6 }

        
    
    END

--
-- RS-XX9-ATV-MIB.mi2
--
