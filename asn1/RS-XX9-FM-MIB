--
-- RS-XX9-FM-MIB.mi2
-- MIB generated by MG-SOFT Visual MIB Builder 2010 Version 8.0  Build 410
-- Tuesday, September 09, 2014 at 11:54:56
--

-- *****************************************************************************
-- *****************************************************************************
-- **
-- **  COPYRIGHT      (c) 2012 Rohde & Schwarz GmbH & Co. KG
-- **                          Muehldorfstrasse 15
-- **    R & S                 D-81671 Muenchen
-- **
-- *****************************************************************************
-- **
-- **  MODULE         RS-XX9-FM-MIB
-- **  
-- *****************************************************************************
-- *****************************************************************************

	RS-XX9-FM-MIB DEFINITIONS ::= BEGIN
 
		IMPORTS
			commonNotificationAlarmClass			
				FROM RS-XX9-COMMON-MIB			
			rsXx9Fm, rsXx9MibModule			
				FROM RS-XX9-SMI-MIB			
			IndexTransmitter, IndexAB, NotificationMask, NotificationPriority, NotificationState, 
			SwitchOnOff			
				FROM RS-XX9-TC-MIB			
			SnmpAdminString			
				FROM SNMP-FRAMEWORK-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI			
			TruthValue, TEXTUAL-CONVENTION			
				FROM SNMPv2-TC;
	
	
		-- 1.3.6.1.4.1.2566.149.1.216.11
		rsXx9FmMibModule MODULE-IDENTITY 
			LAST-UPDATED "201211200800Z"		-- November 20, 2012 at 08:00 GMT
			ORGANIZATION 
				"Rohde&Schwarz GmbH & Co. KG"
			CONTACT-INFO 
				"Rohde & Schwarz GmbH & Co. KG
				Broadcasting Division
				
				Muehldorfstrasse 15
				81671 Munich
				Germany
				
				customersupport@rohde-schwarz.com"
			DESCRIPTION 
				"This MIB defines FM specific objects
				of XX9000 transmitting systems from Rohde & Schwarz.
				
				The following MIBs are related to this:
				- RS-COMMON-MIB         - mandatory for this MIB
				- RS-XX9-SMI-MIB        - mandatory for this MIB
				- RS-XX9-TC-MIB         - mandatory for this MIB
				- RS-XX9-COMMON-MIB     - mandatory for this MIB"
			REVISION "201211200800Z"		-- November 20, 2012 at 08:00 GMT
			DESCRIPTION 
				"Preliminary revision"
			::= { rsXx9MibModule 11 }

		
	
--
-- Textual conventions
--
	
		FmPilotSyncSource ::= TEXTUAL-CONVENTION
			STATUS current
			DESCRIPTION 
				"Reference source for pilot synchronization."
			SYNTAX INTEGER
				{
				off(1),
				aesUserBits(2),
				aesStartFrame(3),
				aesSB(4),
				ext1PPS(5)
				}

		FmSoundMode ::= TEXTUAL-CONVENTION
			STATUS current
			DESCRIPTION 
				"The sound mode for AF and AES inputs."
			SYNTAX INTEGER
				{
				monoL(1),
				monoR(2),
				monoLpR(3),
				stereo(4)
				}

	
--
-- Node definitions
--
	
		-- 1.3.6.1.4.1.2566.127.1.2.216.11.0
		rsXx9FmNotifications OBJECT IDENTIFIER ::= { rsXx9Fm 0 }

		
		-- 1.3.6.1.4.1.2566.127.1.2.216.11.0.1
		fmAudioInputPrimary NOTIFICATION-TYPE
			OBJECTS { commonNotificationAlarmClass, fmInpStNotificationPriority, fmInpStNotificationState }
			STATUS current
			DESCRIPTION 
				"State of primary input.
				
				Possible values:
				ok(5) - if the selectet physical input(s)
				        (via fmInpGenSetupMainSource and fmInpGenSetupMainSoundMode)
				        is ok
				otherwise
				off(2) - if fmInpGenSetupInputMonitoring is off(1) or
				         activeIfRfOn(3) and the exciter is switched off
				         or if txInpAutoActiveInput is input2(3) and txInpAutoIfReseveFails is nothing(1)
				otherwise
				warning(4) - if txInpAutoActiveInput is input1(2) and txInpAutoForceExciterChangeover is off(2)
				             or if txInpAutoActiveInput is input2(3) and txInpAutoIfReseveFails is warn(2)
				otherwise
				fault(3)
				
				Notification class: fault"
			::= { rsXx9FmNotifications 1 }

		
		-- 1.3.6.1.4.1.2566.127.1.2.216.11.0.2
		fmAudioInputSecondary NOTIFICATION-TYPE
			OBJECTS { commonNotificationAlarmClass, fmInpStNotificationPriority, fmInpStNotificationState }
			STATUS current
			DESCRIPTION 
				"State of secondary input.
				
				Possible values:
				ok(5) - if fmInpGenSetupReserveSource is not none(1)
				        and the selectet physical input(s)
				        (via fmInpGenSetupReserveSource and fmInpGenSetupReserveSoundMode)
				        is ok
				otherwise
				off(2) - if fmInpGenSetupReserveSource is none(1) and txInpAutoActiveInput is input1(2)
				         or fmInpGenSetupInputMonitoring is off(1) or
				         activeIfRfOn(3) and the exciter is switched off
				         or if txInpAutoActiveInput is input1(2) and txInpAutoIfReseveFails is nothing(1)
				otherwise
				warning(4) - if txInpAutoActiveInput is input2(3) and txInpAutoForceExciterChangeover is off(2)
				             or if txInpAutoActiveInput is input1(2) and txInpAutoIfReseveFails is warn(2)
				otherwise
				fault(3)
				
				Notification class: fault"
			::= { rsXx9FmNotifications 2 }

		
		-- 1.3.6.1.4.1.2566.127.1.2.216.11.0.3
		fmAfLeft NOTIFICATION-TYPE
			OBJECTS { commonNotificationAlarmClass, fmInpStNotificationPriority, fmInpStNotificationState }
			STATUS current
			DESCRIPTION 
				"Left AF input state.
				
				Possible values:
				ok(5) - if fmAfStateLeftCurrentLevelPercent is bigger than fmAfSetupThresholdPercent
				otherwise
				fault(3)
				
				Notification class: fault"
			::= { rsXx9FmNotifications 3 }

		
		-- 1.3.6.1.4.1.2566.127.1.2.216.11.0.4
		fmAfRight NOTIFICATION-TYPE
			OBJECTS { commonNotificationAlarmClass, fmInpStNotificationPriority, fmInpStNotificationState }
			STATUS current
			DESCRIPTION 
				"Right AF input state.
				
				Possible values:
				ok(5) - if fmAfStateRightCurrentLevelPercent is bigger than fmAfSetupThresholdPercent
				otherwise
				fault(3)
				
				Notification class: fault"
			::= { rsXx9FmNotifications 4 }

		
		-- 1.3.6.1.4.1.2566.127.1.2.216.11.0.5
		fmMpx1 NOTIFICATION-TYPE
			OBJECTS { commonNotificationAlarmClass, fmInpStNotificationPriority, fmInpStNotificationState }
			STATUS current
			DESCRIPTION 
				"MPx 1 input state.
				
				Possible values:
				off(2) - if fmDataSetupOperationMode.1 is on(1)
				otherwise
				ok(5) - if fmMpxAux1StateCurrentLevelPercent is bigger than fmMpxSetupThresholdPercent.1
				otherwise
				fault(3)
				
				Notification class: fault"
			::= { rsXx9FmNotifications 5 }

		
		-- 1.3.6.1.4.1.2566.127.1.2.216.11.0.6
		fmMpx2 NOTIFICATION-TYPE
			OBJECTS { commonNotificationAlarmClass, fmInpStNotificationPriority, fmInpStNotificationState }
			STATUS current
			DESCRIPTION 
				"MPx 2 input state.
				
				Possible values:
				off(2) - if fmDataSetupOperationMode.2 is on(1)
				otherwise
				ok(5) - if fmMpxAux2StateCurrentLevelPercent is bigger than fmMpxSetupThresholdPercent.2
				otherwise
				fault(3)
				
				Notification class: fault"
			::= { rsXx9FmNotifications 6 }

		
		-- 1.3.6.1.4.1.2566.127.1.2.216.11.0.7
		fmAesLeft NOTIFICATION-TYPE
			OBJECTS { commonNotificationAlarmClass, fmInpStNotificationPriority, fmInpStNotificationState }
			STATUS current
			DESCRIPTION 
				"Left AES input state.
				
				Possible values:
				ok(5) - if fmAesStateLeftCurrentLevelPercent is bigger than fmAesSetupThresholdPercent
				        and fmAesStateAudio, fmAesStateParityBiphase, fmAesStateClock are true(1)
				        and fmAesStatePcm, fmAesStateChannel are ok(2)
				otherwise
				fault(3)
				
				Notification class: fault"
			::= { rsXx9FmNotifications 7 }

		
		-- 1.3.6.1.4.1.2566.127.1.2.216.11.0.8
		fmAesRight NOTIFICATION-TYPE
			OBJECTS { commonNotificationAlarmClass, fmInpStNotificationPriority, fmInpStNotificationState }
			STATUS current
			DESCRIPTION 
				"Right AES input state.
				
				Possible values:
				ok(5) - if fmAesStateRightCurrentLevelPercent is bigger than fmAesSetupThresholdPercent
				        and fmAesStateAudio, fmAesStateParityBiphase, fmAesStateClock are true(1)
				        and fmAesStatePcm, fmAesStateChannel are ok(2)
				otherwise
				fault(3)
				
				Notification class: fault"
			::= { rsXx9FmNotifications 8 }

		
		-- 1.3.6.1.4.1.2566.127.1.2.216.11.0.9
		fmAux1Input NOTIFICATION-TYPE
			OBJECTS { commonNotificationAlarmClass, fmInpStNotificationPriority, fmInpStNotificationState }
			STATUS current
			DESCRIPTION 
				"Aux 1 input state.
				
				Possible values:
				off(2) - if fmDataSetupOperationMode.1 is off(2)
				otherwise
				ok(5) - if fmMpxAux1StateCurrentLevelPercent is bigger than fmDataSetupThresholdPercent
				otherwise
				fault(3)
				
				Notification class: warning"
			::= { rsXx9FmNotifications 9 }

		
		-- 1.3.6.1.4.1.2566.127.1.2.216.11.0.10
		fmAux2Input NOTIFICATION-TYPE
			OBJECTS { commonNotificationAlarmClass, fmInpStNotificationPriority, fmInpStNotificationState }
			STATUS current
			DESCRIPTION 
				"Aux 2 input state.
				
				Possible values:
				off(2) - if fmDataSetupOperationMode.2 is off(2)
				otherwise
				ok(5) - if fmMpxAux2StateCurrentLevelPercent is bigger than fmDataSetupThresholdPercent
				otherwise
				fault(3)
				
				Notification class: warning"
			::= { rsXx9FmNotifications 10 }

		
		-- 1.3.6.1.4.1.2566.127.1.2.216.11.1
		rsXx9FmObjects OBJECT IDENTIFIER ::= { rsXx9Fm 1 }

		
		-- 1.3.6.1.4.1.2566.127.1.2.216.11.1.1
		fmInput OBJECT IDENTIFIER ::= { rsXx9FmObjects 1 }

		
		-- 1.3.6.1.4.1.2566.127.1.2.216.11.1.1.1
		fmInputStatus OBJECT IDENTIFIER ::= { fmInput 1 }

		
		-- 1.3.6.1.4.1.2566.127.1.2.216.11.1.1.1.1
		fmInpStNotificationTable OBJECT-TYPE
			SYNTAX SEQUENCE OF FmInpStNotificationEntry
			MAX-ACCESS not-accessible
			STATUS current
			DESCRIPTION
				"The context information/configuration for the
				FM input status notifications."
			::= { fmInputStatus 1 }

		
		-- 1.3.6.1.4.1.2566.127.1.2.216.11.1.1.1.1.1
		fmInpStNotificationEntry OBJECT-TYPE
			SYNTAX FmInpStNotificationEntry
			MAX-ACCESS not-accessible
			STATUS current
			DESCRIPTION
				"An entry in the fmInpStNotificationTable."
			INDEX { fmInpStNotificationTxIdx, fmInpStNotificationExcIdx, fmInpStNotificationIdx }
			::= { fmInpStNotificationTable 1 }

		
		FmInpStNotificationEntry ::=
			SEQUENCE { 
				fmInpStNotificationTxIdx
					IndexTransmitter,
				fmInpStNotificationExcIdx
					IndexAB,
				fmInpStNotificationIdx
					Unsigned32,
				fmInpStNotificationName
					INTEGER,
				fmInpStNotificationMask
					NotificationMask,
				fmInpStNotificationPriority
					NotificationPriority,
				fmInpStNotificationState
					NotificationState
			 }

		-- 1.3.6.1.4.1.2566.127.1.2.216.11.1.1.1.1.1.1
		fmInpStNotificationTxIdx OBJECT-TYPE
			SYNTAX IndexTransmitter
			MAX-ACCESS not-accessible
			STATUS current
			DESCRIPTION
				"The transmitter index."
			::= { fmInpStNotificationEntry 1 }

		
		-- 1.3.6.1.4.1.2566.127.1.2.216.11.1.1.1.1.1.2
		fmInpStNotificationExcIdx OBJECT-TYPE
			SYNTAX IndexAB
			MAX-ACCESS not-accessible
			STATUS current
			DESCRIPTION
				"This index distinguishes the exiters.
				Necessary if you have dual drive transmitters."
			::= { fmInpStNotificationEntry 2 }

		
		-- 1.3.6.1.4.1.2566.127.1.2.216.11.1.1.1.1.1.3
		fmInpStNotificationIdx OBJECT-TYPE
			SYNTAX Unsigned32 (1..10)
			MAX-ACCESS not-accessible
			STATUS current
			DESCRIPTION
				"The notification number as below rsXx9FmNotifications.
				This is a helper column and therefore not-accessible."
			::= { fmInpStNotificationEntry 3 }

		
		-- 1.3.6.1.4.1.2566.127.1.2.216.11.1.1.1.1.1.4
		fmInpStNotificationName OBJECT-TYPE
			SYNTAX INTEGER
				{
				fmAudioInputPrimary(1),
				fmAudioInputSecondary(2),
				fmAfLeft(3),
				fmAfRight(4),
				fmMpx1(5),
				fmMpx2(6),
				fmAesLeft(7),
				fmAesRight(8),
				fmAux1Input(9),
				fmAux2Input(10)
				}
			MAX-ACCESS read-write
			STATUS current
			DESCRIPTION
				"The notification number as an enumeration.
				The enumeration correlates with the notifications under rsXx9FmNotifications."
			::= { fmInpStNotificationEntry 4 }

		
		-- 1.3.6.1.4.1.2566.127.1.2.216.11.1.1.1.1.1.5
		fmInpStNotificationMask OBJECT-TYPE
			SYNTAX NotificationMask
			MAX-ACCESS read-write
			STATUS current
			DESCRIPTION
				"See textual convention for details."
			::= { fmInpStNotificationEntry 5 }

		
		-- 1.3.6.1.4.1.2566.127.1.2.216.11.1.1.1.1.1.6
		fmInpStNotificationPriority OBJECT-TYPE
			SYNTAX NotificationPriority
			MAX-ACCESS read-write
			STATUS current
			DESCRIPTION
				"See textual convention for details."
			::= { fmInpStNotificationEntry 6 }

		
		-- 1.3.6.1.4.1.2566.127.1.2.216.11.1.1.1.1.1.7
		fmInpStNotificationState OBJECT-TYPE
			SYNTAX NotificationState
			MAX-ACCESS read-only
			STATUS current
			DESCRIPTION
				"See textual convention for details."
			::= { fmInpStNotificationEntry 7 }

		
		-- 1.3.6.1.4.1.2566.127.1.2.216.11.1.1.1.2
		fmAfStateTable OBJECT-TYPE
			SYNTAX SEQUENCE OF FmAfStateEntry
			MAX-ACCESS not-accessible
			STATUS current
			DESCRIPTION
				"FM AF input state values."
			::= { fmInputStatus 2 }

		
		-- 1.3.6.1.4.1.2566.127.1.2.216.11.1.1.1.2.1
		fmAfStateEntry OBJECT-TYPE
			SYNTAX FmAfStateEntry
			MAX-ACCESS not-accessible
			STATUS current
			DESCRIPTION
				"An entry in the fmAfStateTable."
			INDEX { fmInpStNotificationTxIdx, fmInpStNotificationExcIdx }
			::= { fmAfStateTable 1 }

		
		FmAfStateEntry ::=
			SEQUENCE { 
				fmAfStateLeftCurrentLevel
					Integer32,
				fmAfStateLeftCurrentLevelPercent
					Unsigned32,
				fmAfStateRightCurrentLevel
					Integer32,
				fmAfStateRightCurrentLevelPercent
					Unsigned32
			 }

		-- 1.3.6.1.4.1.2566.127.1.2.216.11.1.1.1.2.1.1
		fmAfStateLeftCurrentLevel OBJECT-TYPE
			SYNTAX Integer32
			UNITS "1/10 dBu"
			MAX-ACCESS read-only
			STATUS current
			DESCRIPTION
				"Current level on left AF input in dBu."
			::= { fmAfStateEntry 1 }

		
		-- 1.3.6.1.4.1.2566.127.1.2.216.11.1.1.1.2.1.2
		fmAfStateLeftCurrentLevelPercent OBJECT-TYPE
			SYNTAX Unsigned32
			UNITS "per thousand"
			MAX-ACCESS read-only
			STATUS current
			DESCRIPTION
				"Current level on left AF input in o/oo relating to the
				nominal value."
			::= { fmAfStateEntry 2 }

		
		-- 1.3.6.1.4.1.2566.127.1.2.216.11.1.1.1.2.1.3
		fmAfStateRightCurrentLevel OBJECT-TYPE
			SYNTAX Integer32
			UNITS "1/10 dBu"
			MAX-ACCESS read-only
			STATUS current
			DESCRIPTION
				"Current level on right AF input in dBu."
			::= { fmAfStateEntry 3 }

		
		-- 1.3.6.1.4.1.2566.127.1.2.216.11.1.1.1.2.1.4
		fmAfStateRightCurrentLevelPercent OBJECT-TYPE
			SYNTAX Unsigned32
			UNITS "per thousand"
			MAX-ACCESS read-only
			STATUS current
			DESCRIPTION
				"Current level on right AF input in o/oo relating to the
				nominal value."
			::= { fmAfStateEntry 4 }

		
		-- 1.3.6.1.4.1.2566.127.1.2.216.11.1.1.1.3
		fmDigitalAudioStateTable OBJECT-TYPE
			SYNTAX SEQUENCE OF FmDigitalAudioStateEntry
			MAX-ACCESS not-accessible
			STATUS current
			DESCRIPTION
				"FM digital audio input state values."
			::= { fmInputStatus 3 }

		
		-- 1.3.6.1.4.1.2566.127.1.2.216.11.1.1.1.3.1
		fmDigitalAudioStateEntry OBJECT-TYPE
			SYNTAX FmDigitalAudioStateEntry
			MAX-ACCESS not-accessible
			STATUS current
			DESCRIPTION
				"An entry in the fmDigitalAudioStateTable."
			AUGMENTS { fmAfStateEntry }
			::= { fmDigitalAudioStateTable 1 }

		
		FmDigitalAudioStateEntry ::=
			SEQUENCE { 
				fmAesStateLeftCurrentLevel
					Integer32,
				fmAesStateLeftCurrentLevelPercent
					Unsigned32,
				fmAesStateRightCurrentLevel
					Integer32,
				fmAesStateRightCurrentLevelPercent
					Unsigned32,
				fmAesStateSampleRate
					Unsigned32,
				fmAesStatePreemphasis
					INTEGER,
				fmAesStateAudio
					TruthValue,
				fmAesStatePcm
					INTEGER,
				fmAesStateChannel
					INTEGER,
				fmAesStateParityBiphase
					TruthValue,
				fmAesStateClock
					TruthValue
			 }

		-- 1.3.6.1.4.1.2566.127.1.2.216.11.1.1.1.3.1.1
		fmAesStateLeftCurrentLevel OBJECT-TYPE
			SYNTAX Integer32
			UNITS "1/10 dBFs"
			MAX-ACCESS read-only
			STATUS current
			DESCRIPTION
				"Current level on left AES input in dBFs."
			::= { fmDigitalAudioStateEntry 1 }

		
		-- 1.3.6.1.4.1.2566.127.1.2.216.11.1.1.1.3.1.2
		fmAesStateLeftCurrentLevelPercent OBJECT-TYPE
			SYNTAX Unsigned32
			UNITS "per thousand"
			MAX-ACCESS read-only
			STATUS current
			DESCRIPTION
				"Current level on left AES input in o/oo."
			::= { fmDigitalAudioStateEntry 2 }

		
		-- 1.3.6.1.4.1.2566.127.1.2.216.11.1.1.1.3.1.3
		fmAesStateRightCurrentLevel OBJECT-TYPE
			SYNTAX Integer32
			UNITS "1/10 dBFs"
			MAX-ACCESS read-only
			STATUS current
			DESCRIPTION
				"Current level on right AES input in dBFs."
			::= { fmDigitalAudioStateEntry 3 }

		
		-- 1.3.6.1.4.1.2566.127.1.2.216.11.1.1.1.3.1.4
		fmAesStateRightCurrentLevelPercent OBJECT-TYPE
			SYNTAX Unsigned32
			UNITS "per thousand"
			MAX-ACCESS read-only
			STATUS current
			DESCRIPTION
				"Current level on right AES input in o/oo."
			::= { fmDigitalAudioStateEntry 4 }

		
		-- 1.3.6.1.4.1.2566.127.1.2.216.11.1.1.1.3.1.5
		fmAesStateSampleRate OBJECT-TYPE
			SYNTAX Unsigned32
			UNITS "1/10 kHz"
			MAX-ACCESS read-only
			STATUS current
			DESCRIPTION
				"Current sample rate on AES input."
			::= { fmDigitalAudioStateEntry 5 }

		
		-- 1.3.6.1.4.1.2566.127.1.2.216.11.1.1.1.3.1.6
		fmAesStatePreemphasis OBJECT-TYPE
			SYNTAX INTEGER
				{
				unknown(1),
				on(2),
				off(3)
				}
			MAX-ACCESS read-only
			STATUS current
			DESCRIPTION
				"Detection of preemphasis on AES input.
				
				unknown(1) - fmAesStateChannel is not ok(2)"
			::= { fmDigitalAudioStateEntry 6 }

		
		-- 1.3.6.1.4.1.2566.127.1.2.216.11.1.1.1.3.1.7
		fmAesStateAudio OBJECT-TYPE
			SYNTAX TruthValue
			MAX-ACCESS read-only
			STATUS current
			DESCRIPTION
				"Detection of audio content on AES input."
			::= { fmDigitalAudioStateEntry 7 }

		
		-- 1.3.6.1.4.1.2566.127.1.2.216.11.1.1.1.3.1.8
		fmAesStatePcm OBJECT-TYPE
			SYNTAX INTEGER
				{
				unknown(1),
				ok(2),
				warning(3)
				}
			MAX-ACCESS read-only
			STATUS current
			DESCRIPTION
				"Detection of invalid audio samples on AES input.
				
				unknown(1) - fmAesStateChannel is not ok(2)
				ok(2)      - PCM audio samples are valid
				warning(3) - there are invalid PCM audio samples"
			::= { fmDigitalAudioStateEntry 8 }

		
		-- 1.3.6.1.4.1.2566.127.1.2.216.11.1.1.1.3.1.9
		fmAesStateChannel OBJECT-TYPE
			SYNTAX INTEGER
				{
				unknown(1),
				ok(2),
				warning(3)
				}
			MAX-ACCESS read-only
			STATUS current
			DESCRIPTION
				"Validity of channel on AES input.
				
				unknown(1) - fmAesStateAudio is false(2)
				warning(3) - channel CRC is invalid"
			::= { fmDigitalAudioStateEntry 9 }

		
		-- 1.3.6.1.4.1.2566.127.1.2.216.11.1.1.1.3.1.11
		fmAesStateParityBiphase OBJECT-TYPE
			SYNTAX TruthValue
			MAX-ACCESS read-only
			STATUS current
			DESCRIPTION
				"Validity of AES/EBU frame on AES input."
			::= { fmDigitalAudioStateEntry 11 }

		
		-- 1.3.6.1.4.1.2566.127.1.2.216.11.1.1.1.3.1.12
		fmAesStateClock OBJECT-TYPE
			SYNTAX TruthValue
			MAX-ACCESS read-only
			STATUS current
			DESCRIPTION
				"Detection of valid clock on AES input."
			::= { fmDigitalAudioStateEntry 12 }

		
		-- 1.3.6.1.4.1.2566.127.1.2.216.11.1.1.1.4
		fmMpxAuxStateTable OBJECT-TYPE
			SYNTAX SEQUENCE OF FmMpxAuxStateEntry
			MAX-ACCESS not-accessible
			STATUS current
			DESCRIPTION
				"FM MPx input state values."
			::= { fmInputStatus 4 }

		
		-- 1.3.6.1.4.1.2566.127.1.2.216.11.1.1.1.4.1
		fmMpxAuxStateEntry OBJECT-TYPE
			SYNTAX FmMpxAuxStateEntry
			MAX-ACCESS not-accessible
			STATUS current
			DESCRIPTION
				"An entry in the fmMpxAuxStateTable."
			AUGMENTS { fmAfStateEntry }
			::= { fmMpxAuxStateTable 1 }

		
		FmMpxAuxStateEntry ::=
			SEQUENCE { 
				fmMpxAux1StateCurrentLevel
					Integer32,
				fmMpxAux1StateCurrentLevelPercent
					Unsigned32,
				fmMpxAux2StateCurrentLevel
					Integer32,
				fmMpxAux2StateCurrentLevelPercent
					Unsigned32
			 }

		-- 1.3.6.1.4.1.2566.127.1.2.216.11.1.1.1.4.1.1
		fmMpxAux1StateCurrentLevel OBJECT-TYPE
			SYNTAX Integer32
			UNITS "1/10 dBu"
			MAX-ACCESS read-only
			STATUS current
			DESCRIPTION
				"Current level on MPx/Aux 1 input in dBu."
			::= { fmMpxAuxStateEntry 1 }

		
		-- 1.3.6.1.4.1.2566.127.1.2.216.11.1.1.1.4.1.2
		fmMpxAux1StateCurrentLevelPercent OBJECT-TYPE
			SYNTAX Unsigned32
			UNITS "per thousand"
			MAX-ACCESS read-only
			STATUS current
			DESCRIPTION
				"Current level on MPx/Aux 1 input in o/oo relating to the
				nominal value."
			::= { fmMpxAuxStateEntry 2 }

		
		-- 1.3.6.1.4.1.2566.127.1.2.216.11.1.1.1.4.1.3
		fmMpxAux2StateCurrentLevel OBJECT-TYPE
			SYNTAX Integer32
			UNITS "1/10 dBu"
			MAX-ACCESS read-only
			STATUS current
			DESCRIPTION
				"Current level on MPx/Aux 2 input in dBu."
			::= { fmMpxAuxStateEntry 3 }

		
		-- 1.3.6.1.4.1.2566.127.1.2.216.11.1.1.1.4.1.4
		fmMpxAux2StateCurrentLevelPercent OBJECT-TYPE
			SYNTAX Unsigned32
			UNITS "per thousand"
			MAX-ACCESS read-only
			STATUS current
			DESCRIPTION
				"Current level on MPx/Aux 2 input in o/oo relating to the
				nominal value."
			::= { fmMpxAuxStateEntry 4 }

		
		-- 1.3.6.1.4.1.2566.127.1.2.216.11.1.1.2
		fmInputSetup OBJECT IDENTIFIER ::= { fmInput 2 }

		
		-- 1.3.6.1.4.1.2566.127.1.2.216.11.1.1.2.1
		fmInputGeneralSetupTable OBJECT-TYPE
			SYNTAX SEQUENCE OF FmInputGeneralSetupEntry
			MAX-ACCESS not-accessible
			STATUS current
			DESCRIPTION
				"Setup of logical inputs."
			::= { fmInputSetup 1 }

		
		-- 1.3.6.1.4.1.2566.127.1.2.216.11.1.1.2.1.1
		fmInputGeneralSetupEntry OBJECT-TYPE
			SYNTAX FmInputGeneralSetupEntry
			MAX-ACCESS not-accessible
			STATUS current
			DESCRIPTION
				"An entry in the fmInputGeneralSetupTable."
			INDEX { fmInpGenSetupTxIdx, fmInpGenSetupExcIdx }
			::= { fmInputGeneralSetupTable 1 }

		
		FmInputGeneralSetupEntry ::=
			SEQUENCE { 
				fmInpGenSetupTxIdx
					IndexTransmitter,
				fmInpGenSetupExcIdx
					IndexAB,
				fmInpGenSetupMainSource
					INTEGER,
				fmInpGenSetupMainSoundMode
					FmSoundMode,
				fmInpGenSetupReserveSource
					INTEGER,
				fmInpGenSetupReserveSoundMode
					FmSoundMode,
				fmInpGenSetupInputMonitoring
					INTEGER,
				fmInpGenSetupMpxMode
					INTEGER
			 }

		-- 1.3.6.1.4.1.2566.127.1.2.216.11.1.1.2.1.1.1
		fmInpGenSetupTxIdx OBJECT-TYPE
			SYNTAX IndexTransmitter
			MAX-ACCESS not-accessible
			STATUS current
			DESCRIPTION
				"The transmitter index."
			::= { fmInputGeneralSetupEntry 1 }

		
		-- 1.3.6.1.4.1.2566.127.1.2.216.11.1.1.2.1.1.2
		fmInpGenSetupExcIdx OBJECT-TYPE
			SYNTAX IndexAB
			MAX-ACCESS not-accessible
			STATUS current
			DESCRIPTION
				"This index distinguishes the exiters.
				Necessary if you have dual drive transmitters."
			::= { fmInputGeneralSetupEntry 2 }

		
		-- 1.3.6.1.4.1.2566.127.1.2.216.11.1.1.2.1.1.3
		fmInpGenSetupMainSource OBJECT-TYPE
			SYNTAX INTEGER
				{
				af(2),
				aes(3),
				mpx1(4),
				mpx2(5)
				}
			MAX-ACCESS read-write
			STATUS current
			DESCRIPTION
				"Assignment of physical input to main input."
			::= { fmInputGeneralSetupEntry 3 }

		
		-- 1.3.6.1.4.1.2566.127.1.2.216.11.1.1.2.1.1.4
		fmInpGenSetupMainSoundMode OBJECT-TYPE
			SYNTAX FmSoundMode
			MAX-ACCESS read-write
			STATUS current
			DESCRIPTION
				"Configuration of mono/stereo-mode
				if fmInpGenSetupMainSource is af(2) or aes(3)."
			::= { fmInputGeneralSetupEntry 4 }

		
		-- 1.3.6.1.4.1.2566.127.1.2.216.11.1.1.2.1.1.5
		fmInpGenSetupReserveSource OBJECT-TYPE
			SYNTAX INTEGER
				{
				none(1),
				af(2),
				aes(3),
				mpx1(4),
				mpx2(5)
				}
			MAX-ACCESS read-write
			STATUS current
			DESCRIPTION
				"Assignment of physical input to reserve input."
			::= { fmInputGeneralSetupEntry 5 }

		
		-- 1.3.6.1.4.1.2566.127.1.2.216.11.1.1.2.1.1.6
		fmInpGenSetupReserveSoundMode OBJECT-TYPE
			SYNTAX FmSoundMode
			MAX-ACCESS read-write
			STATUS current
			DESCRIPTION
				"Configuration of mono/stereo-mode
				if fmInpGenSetupReserveSource is af(2) or aes(3)."
			::= { fmInputGeneralSetupEntry 6 }

		
		-- 1.3.6.1.4.1.2566.127.1.2.216.11.1.1.2.1.1.7
		fmInpGenSetupInputMonitoring OBJECT-TYPE
			SYNTAX INTEGER
				{
				off(1),
				alwaysOn(2),
				activeIfRfOn(3)
				}
			MAX-ACCESS read-write
			STATUS current
			DESCRIPTION
				"Enabling / disabling of monitoring of the audio input state:
				off(1)          - no monitoring
				alwaysOn(2)     - always monitoring
				activeIfRfOn(3) - monitoring if the transmitter is on"
			::= { fmInputGeneralSetupEntry 7 }

		
		-- 1.3.6.1.4.1.2566.127.1.2.216.11.1.1.2.1.1.8
		fmInpGenSetupMpxMode OBJECT-TYPE
			SYNTAX INTEGER
				{
				unbalanced(1),
				balanced(2)
				}
			MAX-ACCESS read-write
			STATUS current
			DESCRIPTION
				"Select unbalanced(1) or balanced(2) MPx input.
				This selection affects both MPx1 and MPx2.
				
				The selection balanced(2) is possible only
				if the coder board revision is at least 04.00."
			::= { fmInputGeneralSetupEntry 8 }

		
		-- 1.3.6.1.4.1.2566.127.1.2.216.11.1.1.2.2
		fmAfSetupTable OBJECT-TYPE
			SYNTAX SEQUENCE OF FmAfSetupEntry
			MAX-ACCESS not-accessible
			STATUS current
			DESCRIPTION
				"FM AF input setup parameters."
			::= { fmInputSetup 2 }

		
		-- 1.3.6.1.4.1.2566.127.1.2.216.11.1.1.2.2.1
		fmAfSetupEntry OBJECT-TYPE
			SYNTAX FmAfSetupEntry
			MAX-ACCESS not-accessible
			STATUS current
			DESCRIPTION
				"An entry in the fmAfSetupTable."
			AUGMENTS { fmInputGeneralSetupEntry }
			::= { fmAfSetupTable 1 }

		
		FmAfSetupEntry ::=
			SEQUENCE { 
				fmAfSetupImpedance
					INTEGER,
				fmAfSetupNominalLevel
					Integer32,
				fmAfSetupThresholdPercent
					Unsigned32,
				fmAfSetupOnTime
					Unsigned32,
				fmAfSetupOffTime
					Unsigned32,
				fmAfSetupThreshold
					Integer32
			 }

		-- 1.3.6.1.4.1.2566.127.1.2.216.11.1.1.2.2.1.1
		fmAfSetupImpedance OBJECT-TYPE
			SYNTAX INTEGER
				{
				gt2kOhm(1),
				sixhundredOhm(2)
				}
			MAX-ACCESS read-write
			STATUS current
			DESCRIPTION
				"Setting of impedance on both AF inputs."
			::= { fmAfSetupEntry 1 }

		
		-- 1.3.6.1.4.1.2566.127.1.2.216.11.1.1.2.2.1.2
		fmAfSetupNominalLevel OBJECT-TYPE
			SYNTAX Integer32 (-60..120)
			UNITS "1/10 dBu"
			MAX-ACCESS read-write
			STATUS current
			DESCRIPTION
				"Nominal level for both AF inputs."
			::= { fmAfSetupEntry 2 }

		
		-- 1.3.6.1.4.1.2566.127.1.2.216.11.1.1.2.2.1.3
		fmAfSetupThresholdPercent OBJECT-TYPE
			SYNTAX Unsigned32 (1..1000)
			UNITS "per thousand"
			MAX-ACCESS read-write
			STATUS current
			DESCRIPTION
				"Setting of fault threshold for both AF inputs in o/oo
				relating to the nominal level."
			::= { fmAfSetupEntry 3 }

		
		-- 1.3.6.1.4.1.2566.127.1.2.216.11.1.1.2.2.1.4
		fmAfSetupOnTime OBJECT-TYPE
			SYNTAX Unsigned32 (0..600)
			UNITS "second"
			MAX-ACCESS read-write
			STATUS current
			DESCRIPTION
				"Guard time for detecting 'input ok' for both AF inputs."
			::= { fmAfSetupEntry 4 }

		
		-- 1.3.6.1.4.1.2566.127.1.2.216.11.1.1.2.2.1.5
		fmAfSetupOffTime OBJECT-TYPE
			SYNTAX Unsigned32 (0..600)
			UNITS "second"
			MAX-ACCESS read-write
			STATUS current
			DESCRIPTION
				"Guard time for detecting 'input fault' for both AF inputs."
			::= { fmAfSetupEntry 5 }

		
		-- 1.3.6.1.4.1.2566.127.1.2.216.11.1.1.2.2.1.6
		fmAfSetupThreshold OBJECT-TYPE
			SYNTAX Integer32
			UNITS "1/10 dBu"
			MAX-ACCESS read-only
			STATUS current
			DESCRIPTION
				"The fault threshold for both AF inputs in dBu."
			::= { fmAfSetupEntry 6 }

		
		-- 1.3.6.1.4.1.2566.127.1.2.216.11.1.1.2.3
		fmDigitalAudioSetupTable OBJECT-TYPE
			SYNTAX SEQUENCE OF FmDigitalAudioSetupEntry
			MAX-ACCESS not-accessible
			STATUS current
			DESCRIPTION
				"FM digital audio input setup parameters."
			::= { fmInputSetup 3 }

		
		-- 1.3.6.1.4.1.2566.127.1.2.216.11.1.1.2.3.1
		fmDigitalAudioSetupEntry OBJECT-TYPE
			SYNTAX FmDigitalAudioSetupEntry
			MAX-ACCESS not-accessible
			STATUS current
			DESCRIPTION
				"An entry in the fmDigitalAudioSetupTable."
			AUGMENTS { fmInputGeneralSetupEntry }
			::= { fmDigitalAudioSetupTable 1 }

		
		FmDigitalAudioSetupEntry ::=
			SEQUENCE { 
				fmAesSetupNominalLevel
					Integer32,
				fmAesSetupThresholdPercent
					Unsigned32,
				fmAesSetupOnTime
					Unsigned32,
				fmAesSetupOffTime
					Unsigned32,
				fmAesSetupThreshold
					Integer32
			 }

		-- 1.3.6.1.4.1.2566.127.1.2.216.11.1.1.2.3.1.1
		fmAesSetupNominalLevel OBJECT-TYPE
			SYNTAX Integer32 (-120..0)
			UNITS "1/10 dB FS"
			MAX-ACCESS read-write
			STATUS current
			DESCRIPTION
				"Nominal level for AES input."
			::= { fmDigitalAudioSetupEntry 1 }

		
		-- 1.3.6.1.4.1.2566.127.1.2.216.11.1.1.2.3.1.2
		fmAesSetupThresholdPercent OBJECT-TYPE
			SYNTAX Unsigned32 (1..1000)
			UNITS "per thousand"
			MAX-ACCESS read-write
			STATUS current
			DESCRIPTION
				"Setting of fault threshold for AES input in o/oo
				relating to the nominal level."
			::= { fmDigitalAudioSetupEntry 2 }

		
		-- 1.3.6.1.4.1.2566.127.1.2.216.11.1.1.2.3.1.3
		fmAesSetupOnTime OBJECT-TYPE
			SYNTAX Unsigned32 (0..600)
			UNITS "second"
			MAX-ACCESS read-write
			STATUS current
			DESCRIPTION
				"Guard time for detecting 'input ok' for AES input."
			::= { fmDigitalAudioSetupEntry 3 }

		
		-- 1.3.6.1.4.1.2566.127.1.2.216.11.1.1.2.3.1.4
		fmAesSetupOffTime OBJECT-TYPE
			SYNTAX Unsigned32 (0..600)
			UNITS "second"
			MAX-ACCESS read-write
			STATUS current
			DESCRIPTION
				"Guard time for detecting 'input fault' for AES input."
			::= { fmDigitalAudioSetupEntry 4 }

		
		-- 1.3.6.1.4.1.2566.127.1.2.216.11.1.1.2.3.1.5
		fmAesSetupThreshold OBJECT-TYPE
			SYNTAX Integer32
			UNITS "1/10 dB FS"
			MAX-ACCESS read-only
			STATUS current
			DESCRIPTION
				"The fault threshold for AES input in dB FS."
			::= { fmDigitalAudioSetupEntry 5 }

		
		-- 1.3.6.1.4.1.2566.127.1.2.216.11.1.1.2.4
		fmMpxSetupTable OBJECT-TYPE
			SYNTAX SEQUENCE OF FmMpxSetupEntry
			MAX-ACCESS not-accessible
			STATUS current
			DESCRIPTION
				"FM MPx input setup parameters."
			::= { fmInputSetup 4 }

		
		-- 1.3.6.1.4.1.2566.127.1.2.216.11.1.1.2.4.1
		fmMpxSetupEntry OBJECT-TYPE
			SYNTAX FmMpxSetupEntry
			MAX-ACCESS not-accessible
			STATUS current
			DESCRIPTION
				"An entry in the fmMpxSetupTable."
			INDEX { fmInpGenSetupTxIdx, fmInpGenSetupExcIdx, fmMpxSetupInpIdx }
			::= { fmMpxSetupTable 1 }

		
		FmMpxSetupEntry ::=
			SEQUENCE { 
				fmMpxSetupInpIdx
					INTEGER,
				fmMpxSetupNominalLevel
					Integer32,
				fmMpxSetupThresholdPercent
					Unsigned32,
				fmMpxSetupOnTime
					Unsigned32,
				fmMpxSetupOffTime
					Unsigned32,
				fmMpxSetupThreshold
					Integer32
			 }

		-- 1.3.6.1.4.1.2566.127.1.2.216.11.1.1.2.4.1.1
		fmMpxSetupInpIdx OBJECT-TYPE
			SYNTAX INTEGER
				{
				mpx1(1),
				mpx2(2)
				}
			MAX-ACCESS not-accessible
			STATUS current
			DESCRIPTION
				"Selection of input MPX1 or MPX2."
			::= { fmMpxSetupEntry 1 }

		
		-- 1.3.6.1.4.1.2566.127.1.2.216.11.1.1.2.4.1.2
		fmMpxSetupNominalLevel OBJECT-TYPE
			SYNTAX Integer32 (-10..160)
			UNITS "1/10 dBu"
			MAX-ACCESS read-write
			STATUS current
			DESCRIPTION
				"Nominal level for both MPx inputs."
			::= { fmMpxSetupEntry 2 }

		
		-- 1.3.6.1.4.1.2566.127.1.2.216.11.1.1.2.4.1.3
		fmMpxSetupThresholdPercent OBJECT-TYPE
			SYNTAX Unsigned32 (1..1000)
			UNITS "per thousand"
			MAX-ACCESS read-write
			STATUS current
			DESCRIPTION
				"Setting of fault threshold for both MPx inputs in o/oo
				relating to the nominal level."
			::= { fmMpxSetupEntry 3 }

		
		-- 1.3.6.1.4.1.2566.127.1.2.216.11.1.1.2.4.1.4
		fmMpxSetupOnTime OBJECT-TYPE
			SYNTAX Unsigned32 (0..600)
			UNITS "second"
			MAX-ACCESS read-write
			STATUS current
			DESCRIPTION
				"Guard time for detecting 'input ok' for both MPx inputs."
			::= { fmMpxSetupEntry 4 }

		
		-- 1.3.6.1.4.1.2566.127.1.2.216.11.1.1.2.4.1.5
		fmMpxSetupOffTime OBJECT-TYPE
			SYNTAX Unsigned32 (0..600)
			UNITS "second"
			MAX-ACCESS read-write
			STATUS current
			DESCRIPTION
				"Guard time for detecting 'input fault' for both MPx inputs."
			::= { fmMpxSetupEntry 5 }

		
		-- 1.3.6.1.4.1.2566.127.1.2.216.11.1.1.2.4.1.6
		fmMpxSetupThreshold OBJECT-TYPE
			SYNTAX Integer32
			UNITS "1/10 dBu"
			MAX-ACCESS read-only
			STATUS current
			DESCRIPTION
				"The fault threshold for both MPx inputs in dBu."
			::= { fmMpxSetupEntry 6 }

		
		-- 1.3.6.1.4.1.2566.127.1.2.216.11.1.1.2.5
		fmDataInputSetupTable OBJECT-TYPE
			SYNTAX SEQUENCE OF FmDataInputSetupEntry
			MAX-ACCESS not-accessible
			STATUS current
			DESCRIPTION
				"FM data input setup parameters."
			::= { fmInputSetup 5 }

		
		-- 1.3.6.1.4.1.2566.127.1.2.216.11.1.1.2.5.1
		fmDataInputSetupEntry OBJECT-TYPE
			SYNTAX FmDataInputSetupEntry
			MAX-ACCESS not-accessible
			STATUS current
			DESCRIPTION
				"An entry in the fmDataInputSetupTable."
			INDEX { fmInpGenSetupTxIdx, fmInpGenSetupExcIdx, fmDataSetupInpIdx }
			::= { fmDataInputSetupTable 1 }

		
		FmDataInputSetupEntry ::=
			SEQUENCE { 
				fmDataSetupInpIdx
					INTEGER,
				fmDataSetupOperationMode
					SwitchOnOff,
				fmDataSetupNominalLevel
					Integer32,
				fmDataSetupNominalDeviation
					Unsigned32,
				fmDataSetupThresholdPercent
					Unsigned32,
				fmDataSetupOnTime
					Unsigned32,
				fmDataSetupOffTime
					Unsigned32,
				fmDataSetupLabel
					SnmpAdminString,
				fmDataSetupThreshold
					Integer32
			 }

		-- 1.3.6.1.4.1.2566.127.1.2.216.11.1.1.2.5.1.1
		fmDataSetupInpIdx OBJECT-TYPE
			SYNTAX INTEGER
				{
				aux1(1),
				aux2(2)
				}
			MAX-ACCESS not-accessible
			STATUS current
			DESCRIPTION
				"Distinction between AUX1 and AUX2."
			::= { fmDataInputSetupEntry 1 }

		
		-- 1.3.6.1.4.1.2566.127.1.2.216.11.1.1.2.5.1.2
		fmDataSetupOperationMode OBJECT-TYPE
			SYNTAX SwitchOnOff
			MAX-ACCESS read-write
			STATUS current
			DESCRIPTION
				"Switches data input on or off."
			::= { fmDataInputSetupEntry 2 }

		
		-- 1.3.6.1.4.1.2566.127.1.2.216.11.1.1.2.5.1.3
		fmDataSetupNominalLevel OBJECT-TYPE
			SYNTAX Integer32 (-180..-70)
			UNITS "1/10 dBu"
			MAX-ACCESS read-write
			STATUS current
			DESCRIPTION
				"Nominal level for data input."
			::= { fmDataInputSetupEntry 3 }

		
		-- 1.3.6.1.4.1.2566.127.1.2.216.11.1.1.2.5.1.4
		fmDataSetupNominalDeviation OBJECT-TYPE
			SYNTAX Unsigned32 (20..100)
			UNITS "1/10 kHz"
			MAX-ACCESS read-write
			STATUS current
			DESCRIPTION
				"Nominal deviation of data input."
			::= { fmDataInputSetupEntry 4 }

		
		-- 1.3.6.1.4.1.2566.127.1.2.216.11.1.1.2.5.1.5
		fmDataSetupThresholdPercent OBJECT-TYPE
			SYNTAX Unsigned32 (1..1000)
			UNITS "per thousand"
			MAX-ACCESS read-write
			STATUS current
			DESCRIPTION
				"Setting of fault threshold for data input in o/oo
				relating to the nominal level."
			::= { fmDataInputSetupEntry 5 }

		
		-- 1.3.6.1.4.1.2566.127.1.2.216.11.1.1.2.5.1.6
		fmDataSetupOnTime OBJECT-TYPE
			SYNTAX Unsigned32 (0..600)
			UNITS "second"
			MAX-ACCESS read-write
			STATUS current
			DESCRIPTION
				"Guard time for detecting 'input ok' for data input."
			::= { fmDataInputSetupEntry 6 }

		
		-- 1.3.6.1.4.1.2566.127.1.2.216.11.1.1.2.5.1.7
		fmDataSetupOffTime OBJECT-TYPE
			SYNTAX Unsigned32 (0..600)
			UNITS "second"
			MAX-ACCESS read-write
			STATUS current
			DESCRIPTION
				"Guard time for detecting 'input fault' for data input."
			::= { fmDataInputSetupEntry 7 }

		
		-- 1.3.6.1.4.1.2566.127.1.2.216.11.1.1.2.5.1.8
		fmDataSetupLabel OBJECT-TYPE
			SYNTAX SnmpAdminString
			MAX-ACCESS read-write
			STATUS current
			DESCRIPTION
				"Labeling for the deployment of input.
				(For example: RDS or SCA.)"
			::= { fmDataInputSetupEntry 8 }

		
		-- 1.3.6.1.4.1.2566.127.1.2.216.11.1.1.2.5.1.9
		fmDataSetupThreshold OBJECT-TYPE
			SYNTAX Integer32
			UNITS "1/10 dBu"
			MAX-ACCESS read-only
			STATUS current
			DESCRIPTION
				"The fault threshold for data input in dBu."
			::= { fmDataInputSetupEntry 9 }

		
		-- 1.3.6.1.4.1.2566.127.1.2.216.11.1.2
		fmPilotTable OBJECT-TYPE
			SYNTAX SEQUENCE OF FmPilotEntry
			MAX-ACCESS not-accessible
			STATUS current
			DESCRIPTION
				"Pilot parameters."
			::= { rsXx9FmObjects 2 }

		
		-- 1.3.6.1.4.1.2566.127.1.2.216.11.1.2.1
		fmPilotEntry OBJECT-TYPE
			SYNTAX FmPilotEntry
			MAX-ACCESS not-accessible
			STATUS current
			DESCRIPTION
				"An entry in the fmPilotTable."
			INDEX { fmPilotTxIdx, fmPilotExcIdx }
			::= { fmPilotTable 1 }

		
		FmPilotEntry ::=
			SEQUENCE { 
				fmPilotTxIdx
					IndexTransmitter,
				fmPilotExcIdx
					IndexAB,
				fmPilotOperationMode
					SwitchOnOff,
				fmPilotDeviation
					Unsigned32
			 }

		-- 1.3.6.1.4.1.2566.127.1.2.216.11.1.2.1.1
		fmPilotTxIdx OBJECT-TYPE
			SYNTAX IndexTransmitter
			MAX-ACCESS not-accessible
			STATUS current
			DESCRIPTION
				"The transmitter index."
			::= { fmPilotEntry 1 }

		
		-- 1.3.6.1.4.1.2566.127.1.2.216.11.1.2.1.2
		fmPilotExcIdx OBJECT-TYPE
			SYNTAX IndexAB
			MAX-ACCESS not-accessible
			STATUS current
			DESCRIPTION
				"This index distinguishes the exiters.
				Necessary if you have dual drive transmitters."
			::= { fmPilotEntry 2 }

		
		-- 1.3.6.1.4.1.2566.127.1.2.216.11.1.2.1.3
		fmPilotOperationMode OBJECT-TYPE
			SYNTAX SwitchOnOff
			MAX-ACCESS read-write
			STATUS current
			DESCRIPTION
				"Switches pilot of internal stereo coder on or off."
			::= { fmPilotEntry 3 }

		
		-- 1.3.6.1.4.1.2566.127.1.2.216.11.1.2.1.4
		fmPilotDeviation OBJECT-TYPE
			SYNTAX Unsigned32 (200..1000)
			UNITS "1/100 kHz"
			MAX-ACCESS read-write
			STATUS current
			DESCRIPTION
				"Deviation of pilot for internal stereo coder."
			::= { fmPilotEntry 4 }

		
		-- 1.3.6.1.4.1.2566.127.1.2.216.11.1.3
		fmPreemphasisTable OBJECT-TYPE
			SYNTAX SEQUENCE OF FmPreemphasisEntry
			MAX-ACCESS not-accessible
			STATUS current
			DESCRIPTION
				"Preemphasis parameters."
			::= { rsXx9FmObjects 3 }

		
		-- 1.3.6.1.4.1.2566.127.1.2.216.11.1.3.1
		fmPreemphasisEntry OBJECT-TYPE
			SYNTAX FmPreemphasisEntry
			MAX-ACCESS not-accessible
			STATUS current
			DESCRIPTION
				"An entry in the fmPreemphasisTable."
			AUGMENTS { fmPilotEntry }
			::= { fmPreemphasisTable 1 }

		
		FmPreemphasisEntry ::=
			SEQUENCE { 
				fmPreemphasisOperationMode
					SwitchOnOff,
				fmPreemphasisValue
					INTEGER
			 }

		-- 1.3.6.1.4.1.2566.127.1.2.216.11.1.3.1.1
		fmPreemphasisOperationMode OBJECT-TYPE
			SYNTAX SwitchOnOff
			MAX-ACCESS read-write
			STATUS current
			DESCRIPTION
				"Switches preemphasis on or off."
			::= { fmPreemphasisEntry 1 }

		
		-- 1.3.6.1.4.1.2566.127.1.2.216.11.1.3.1.2
		fmPreemphasisValue OBJECT-TYPE
			SYNTAX INTEGER
				{
				microSec50(1),
				microSec75(2)
				}
			MAX-ACCESS read-write
			STATUS current
			DESCRIPTION
				"Selection of time constant for preemphasis:
				microSec50(1) - 50 micro seconds
				microSec75(2) - 75 micro seconds"
			::= { fmPreemphasisEntry 2 }

		
		-- 1.3.6.1.4.1.2566.127.1.2.216.11.1.4
		fmDeviationTable OBJECT-TYPE
			SYNTAX SEQUENCE OF FmDeviationEntry
			MAX-ACCESS not-accessible
			STATUS current
			DESCRIPTION
				"Deviation parameters."
			::= { rsXx9FmObjects 4 }

		
		-- 1.3.6.1.4.1.2566.127.1.2.216.11.1.4.1
		fmDeviationEntry OBJECT-TYPE
			SYNTAX FmDeviationEntry
			MAX-ACCESS not-accessible
			STATUS current
			DESCRIPTION
				"An entry in the fmDeviationTable."
			AUGMENTS { fmPilotEntry }
			::= { fmDeviationTable 1 }

		
		FmDeviationEntry ::=
			SEQUENCE { 
				fmDeviationNominal
					Unsigned32,
				fmDeviationCurrent
					Unsigned32,
				fmLimiterOperationMode
					INTEGER,
				fmLimiterThreshold
					Unsigned32,
				fmLimiterActivity
					Integer32,
				fmDeviationClipped
					Unsigned32,
				fmMPxPowerControlOperationMode
					SwitchOnOff,
				fmMPxPowerThreshold
					Integer32,
				fmMPxPowerCurrent
					Integer32
			 }

		-- 1.3.6.1.4.1.2566.127.1.2.216.11.1.4.1.1
		fmDeviationNominal OBJECT-TYPE
			SYNTAX Unsigned32 (400..1500)
			UNITS "1/10 kHz"
			MAX-ACCESS read-write
			STATUS current
			DESCRIPTION
				"Deviation without pilot, RDS, SCA."
			::= { fmDeviationEntry 1 }

		
		-- 1.3.6.1.4.1.2566.127.1.2.216.11.1.4.1.2
		fmDeviationCurrent OBJECT-TYPE
			SYNTAX Unsigned32
			UNITS "1/10 kHz"
			MAX-ACCESS read-only
			STATUS current
			DESCRIPTION
				"Current summary deviation."
			::= { fmDeviationEntry 2 }

		
		-- 1.3.6.1.4.1.2566.127.1.2.216.11.1.4.1.3
		fmLimiterOperationMode OBJECT-TYPE
			SYNTAX INTEGER
				{
				off(1),
				on(2),
				clipperOnly(3)
				}
			MAX-ACCESS read-write
			STATUS current
			DESCRIPTION
				"Switches limiter on or off."
			::= { fmDeviationEntry 3 }

		
		-- 1.3.6.1.4.1.2566.127.1.2.216.11.1.4.1.4
		fmLimiterThreshold OBJECT-TYPE
			SYNTAX Unsigned32 (400..1500)
			UNITS "1/10 kHz"
			MAX-ACCESS read-write
			STATUS current
			DESCRIPTION
				"Threshold for limiter."
			::= { fmDeviationEntry 4 }

		
		-- 1.3.6.1.4.1.2566.127.1.2.216.11.1.4.1.5
		fmLimiterActivity OBJECT-TYPE
			SYNTAX Integer32
			UNITS "percent"
			MAX-ACCESS read-only
			STATUS current
			DESCRIPTION
				"Activity of limiter in percent."
			::= { fmDeviationEntry 5 }

		
		-- 1.3.6.1.4.1.2566.127.1.2.216.11.1.4.1.6
		fmDeviationClipped OBJECT-TYPE
			SYNTAX Unsigned32
			UNITS "1/10 kHz"
			MAX-ACCESS read-only
			STATUS current
			DESCRIPTION
				"Activity of limiter in Hz."
			::= { fmDeviationEntry 6 }

		
		-- 1.3.6.1.4.1.2566.127.1.2.216.11.1.4.1.7
		fmMPxPowerControlOperationMode OBJECT-TYPE
			SYNTAX SwitchOnOff
			MAX-ACCESS read-write
			STATUS current
			DESCRIPTION
				"Switches MPx power control on or off."
			::= { fmDeviationEntry 7 }

		
		-- 1.3.6.1.4.1.2566.127.1.2.216.11.1.4.1.8
		fmMPxPowerThreshold OBJECT-TYPE
			SYNTAX Integer32 (-50..50)
			UNITS "1/10 dBr"
			MAX-ACCESS read-write
			STATUS current
			DESCRIPTION
				"Threshold for MPx power."
			::= { fmDeviationEntry 8 }

		
		-- 1.3.6.1.4.1.2566.127.1.2.216.11.1.4.1.9
		fmMPxPowerCurrent OBJECT-TYPE
			SYNTAX Integer32
			UNITS "1/10 dBr"
			MAX-ACCESS read-only
			STATUS current
			DESCRIPTION
				"Current MPx power."
			::= { fmDeviationEntry 9 }

		
		-- 1.3.6.1.4.1.2566.127.1.2.216.11.1.6
		fmSyncTable OBJECT-TYPE
			SYNTAX SEQUENCE OF FmSyncEntry
			MAX-ACCESS not-accessible
			STATUS current
			DESCRIPTION
				"Synchron FM parameters."
			::= { rsXx9FmObjects 6 }

		
		-- 1.3.6.1.4.1.2566.127.1.2.216.11.1.6.1
		fmSyncEntry OBJECT-TYPE
			SYNTAX FmSyncEntry
			MAX-ACCESS not-accessible
			STATUS current
			DESCRIPTION
				"An entry in the fmSyncTable."
			AUGMENTS { fmPilotEntry }
			::= { fmSyncTable 1 }

		
		FmSyncEntry ::=
			SEQUENCE { 
				fmSyncPilotSyncSource
					FmPilotSyncSource,
				fmSyncPilotSyncSourceCurrent
					FmPilotSyncSource,
				fmSyncStaticDelay
					Unsigned32,
				fmSyncPilotPhase
					Unsigned32
			 }

		-- 1.3.6.1.4.1.2566.127.1.2.216.11.1.6.1.1
		fmSyncPilotSyncSource OBJECT-TYPE
			SYNTAX FmPilotSyncSource
			MAX-ACCESS read-write
			STATUS current
			DESCRIPTION
				"Selection of reference for pilot synchronization."
			::= { fmSyncEntry 1 }

		
		-- 1.3.6.1.4.1.2566.127.1.2.216.11.1.6.1.2
		fmSyncPilotSyncSourceCurrent OBJECT-TYPE
			SYNTAX FmPilotSyncSource
			MAX-ACCESS read-only
			STATUS current
			DESCRIPTION
				"Current reference for pilot synchronization."
			::= { fmSyncEntry 2 }

		
		-- 1.3.6.1.4.1.2566.127.1.2.216.11.1.6.1.3
		fmSyncStaticDelay OBJECT-TYPE
			SYNTAX Unsigned32 (0..999999999)
			UNITS "nano second"
			MAX-ACCESS read-write
			STATUS current
			DESCRIPTION
				"MPx delay."
			::= { fmSyncEntry 3 }

		
		-- 1.3.6.1.4.1.2566.127.1.2.216.11.1.6.1.4
		fmSyncPilotPhase OBJECT-TYPE
			SYNTAX Unsigned32 (0..10000)
			UNITS "1/100 percent"
			MAX-ACCESS read-write
			STATUS current
			DESCRIPTION
				"Correction of pilot phase."
			::= { fmSyncEntry 4 }

		
		-- 1.3.6.1.4.1.2566.127.1.2.216.11.2
		rsXx9FmConformance OBJECT IDENTIFIER ::= { rsXx9Fm 2 }

		
		-- 1.3.6.1.4.1.2566.127.1.2.216.11.2.1
		rsXx9FmCompliances OBJECT IDENTIFIER ::= { rsXx9FmConformance 1 }

		
		-- 1.3.6.1.4.1.2566.127.1.2.216.11.2.1.1
		fmBasicCompliance MODULE-COMPLIANCE
			STATUS current
			DESCRIPTION 
				"The compliance statement for XX9000 FM encoding."
			MODULE -- this module
				MANDATORY-GROUPS { fmObjBasic, fmObjInput, fmNotifyInput }
			::= { rsXx9FmCompliances 1 }

		
		-- 1.3.6.1.4.1.2566.127.1.2.216.11.2.2
		rsXx9FmGroups OBJECT IDENTIFIER ::= { rsXx9FmConformance 2 }

		
		-- 1.3.6.1.4.1.2566.127.1.2.216.11.2.2.1
		fmObjBasic OBJECT-GROUP
			OBJECTS { fmPilotOperationMode, fmPilotDeviation, fmPreemphasisOperationMode, fmPreemphasisValue, fmDeviationNominal, 
				fmDeviationCurrent, fmLimiterOperationMode, fmLimiterThreshold, fmLimiterActivity, fmDeviationClipped, 
				fmMPxPowerControlOperationMode, fmMPxPowerThreshold, fmMPxPowerCurrent, fmSyncPilotSyncSource, fmSyncStaticDelay, 
				fmSyncPilotPhase, fmSyncPilotSyncSourceCurrent }
			STATUS current
			DESCRIPTION 
				"General FM objects."
			::= { rsXx9FmGroups 1 }

		
		-- 1.3.6.1.4.1.2566.127.1.2.216.11.2.2.2
		fmObjInput OBJECT-GROUP
			OBJECTS { fmInpStNotificationName, fmInpStNotificationMask, fmInpStNotificationPriority, fmInpStNotificationState, fmAesStateLeftCurrentLevel, 
				fmAesStateLeftCurrentLevelPercent, fmAesStateRightCurrentLevel, fmAesStateRightCurrentLevelPercent, fmAesStateSampleRate, fmAesStatePreemphasis, 
				fmAesStateAudio, fmAesStateClock, fmAfSetupImpedance, fmAfSetupNominalLevel, fmAfSetupThreshold, 
				fmAfSetupOnTime, fmAfSetupOffTime, fmAesSetupNominalLevel, fmAesSetupThreshold, fmAesSetupOnTime, 
				fmAesSetupOffTime, fmMpxSetupNominalLevel, fmMpxSetupThreshold, fmMpxSetupOnTime, fmMpxSetupOffTime, 
				fmDataSetupOperationMode, fmDataSetupNominalLevel, fmDataSetupNominalDeviation, fmDataSetupThreshold, fmDataSetupOnTime, 
				fmInpGenSetupMainSource, fmInpGenSetupMainSoundMode, fmInpGenSetupReserveSource, fmInpGenSetupReserveSoundMode, fmDataSetupLabel, 
				fmDataSetupOffTime, fmAesStateParityBiphase, fmAesStatePcm, fmDataSetupThresholdPercent, fmMpxSetupThresholdPercent, 
				fmAesSetupThresholdPercent, fmAfSetupThresholdPercent, fmInpGenSetupInputMonitoring, fmInpGenSetupMpxMode, fmAesStateChannel, 
				fmAfStateLeftCurrentLevel, fmAfStateLeftCurrentLevelPercent, fmAfStateRightCurrentLevel, fmAfStateRightCurrentLevelPercent, fmMpxAux1StateCurrentLevel, 
				fmMpxAux1StateCurrentLevelPercent, fmMpxAux2StateCurrentLevel, fmMpxAux2StateCurrentLevelPercent }
			STATUS current
			DESCRIPTION 
				"FM input objects."
			::= { rsXx9FmGroups 2 }

		
		-- 1.3.6.1.4.1.2566.127.1.2.216.11.2.2.3
		fmNotifyInput NOTIFICATION-GROUP
			NOTIFICATIONS { fmAudioInputPrimary, fmAudioInputSecondary, fmMpx1, fmMpx2, fmAesLeft, 
				fmAesRight, fmAfLeft, fmAfRight, fmAux1Input, fmAux2Input
				 }
			STATUS current
			DESCRIPTION 
				"FM input notifications."
			::= { rsXx9FmGroups 3 }

		
	
	END

--
-- RS-XX9-FM-MIB.mi2
--
