--
-- RS-XX9-AIR-COOLING-MIB.mi2
-- MIB generated by MG-SOFT Visual MIB Builder 2010 Version 8.0  Build 403
-- Monday, March 09, 2015 at 14:18:26
--

    RS-XX9-AIR-COOLING-MIB DEFINITIONS ::= BEGIN
 
        IMPORTS
            commonNotificationAlarmClass            
                FROM RS-XX9-COMMON-MIB            
            rsXx9AirCooling, rsXx9MibModule            
                FROM RS-XX9-SMI-MIB            
            NotificationMask, NotificationPriority, NotificationState            
                FROM RS-XX9-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI;
    
    
        rsXx9AirCoolingMibModule MODULE-IDENTITY 
            LAST-UPDATED "201502271500Z"		-- February 27, 2015 at 15:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines air cooling specific objects
                of XX9000 transmitting systems from Rohde & Schwarz.
                
                The following MIBs are related to this:
                - RS-COMMON-MIB         - mandatory for this MIB.
                - RS-XX9-SMI-MIB        - mandatory for this MIB.
                - RS-XX9-TC-MIB         - mandatory for this MIB.
                - RS-XX9-COMMON-MIB     - mandatory for this MIB."
            REVISION "201502271500Z"		-- February 27, 2015 at 15:00 GMT
            DESCRIPTION 
                "updated description texts"
            REVISION "201401281200Z"		-- January 28, 2014 at 12:00 GMT
            DESCRIPTION 
                "Cleanup of descriptions."
            REVISION "201208010800Z"		-- August 01, 2012 at 08:00 GMT
            DESCRIPTION 
                "Preliminary revision"
            ::= { rsXx9MibModule 101 }

        
    
    
--
-- Node definitions
--
    
        rsXx9AirCoolingNotifications OBJECT IDENTIFIER ::= { rsXx9AirCooling 0 }

        
        airCoolingSummary NOTIFICATION-TYPE
            OBJECTS { commonNotificationAlarmClass, airCoolingNotificationPriority, airCoolingNotificationState }
            STATUS current
            DESCRIPTION 
                "Air cooling summary state.
                
                Possible values:
                off(2)       -
                fault(3)     - 
                warning(4)   - 
                ok(5)        - 
                
                Notification class: fault"
            ::= { rsXx9AirCoolingNotifications 1 }

        
        airCoolingSensorsSummary NOTIFICATION-TYPE
            OBJECTS { commonNotificationAlarmClass, airCoolingNotificationPriority, airCoolingNotificationState }
            STATUS current
            DESCRIPTION 
                "Air cooling sensors
                (inlet temperature, outlet temperature, pressure)
                summary state.
                
                Possible values:
                off(2)       -
                fault(3)     - failure of both pressure sensors
                warning(4)   - failure of one pressure sensor or of temperature sensors
                ok(5)        - "
            ::= { rsXx9AirCoolingNotifications 2 }

        
        rsXx9AirCoolingObjects OBJECT IDENTIFIER ::= { rsXx9AirCooling 1 }

        
        airCoolingStatus OBJECT IDENTIFIER ::= { rsXx9AirCoolingObjects 1 }

        
        airCoolingNotificationTable OBJECT-TYPE
            SYNTAX SEQUENCE OF AirCoolingNotificationEntry
            MAX-ACCESS not-accessible
            STATUS current
            DESCRIPTION
                "The context information/configuration for the
                air cooling status notifications."
            ::= { airCoolingStatus 1 }

        
        airCoolingNotificationEntry OBJECT-TYPE
            SYNTAX AirCoolingNotificationEntry
            MAX-ACCESS not-accessible
            STATUS current
            DESCRIPTION
                "An entry in the airCoolingNotificationTable."
            INDEX { airCoolingNotificationCycleIdx, airCoolingNotificationIdx }
            ::= { airCoolingNotificationTable 1 }

        
        AirCoolingNotificationEntry ::=
            SEQUENCE { 
                airCoolingNotificationCycleIdx
                    Unsigned32,
                airCoolingNotificationIdx
                    Unsigned32,
                airCoolingNotificationName
                    INTEGER,
                airCoolingNotificationMask
                    NotificationMask,
                airCoolingNotificationPriority
                    NotificationPriority,
                airCoolingNotificationState
                    NotificationState
             }

        airCoolingNotificationCycleIdx OBJECT-TYPE
            SYNTAX Unsigned32 (1..2)
            MAX-ACCESS not-accessible
            STATUS current
            DESCRIPTION
                "Air cooling cycle index."
            ::= { airCoolingNotificationEntry 1 }

        
        airCoolingNotificationIdx OBJECT-TYPE
            SYNTAX Unsigned32 (1..2)
            MAX-ACCESS not-accessible
            STATUS current
            DESCRIPTION
                "The notification number as below rsXx9AirCoolingNotifications.
                This is a helper column and therefore not-accessible."
            ::= { airCoolingNotificationEntry 2 }

        
        airCoolingNotificationName OBJECT-TYPE
            SYNTAX INTEGER
                {
                airCoolingSummary(1),
                airCoolingSensorsSummary(2)
                }
            MAX-ACCESS read-only
            STATUS current
            DESCRIPTION
                "The notification number as an enumeration.
                The enumeration correlates with the notifications
                under rsXx9AirCoolingNotifications."
            ::= { airCoolingNotificationEntry 3 }

        
        airCoolingNotificationMask OBJECT-TYPE
            SYNTAX NotificationMask
            MAX-ACCESS read-write
            STATUS current
            DESCRIPTION
                "See textual convention for details."
            ::= { airCoolingNotificationEntry 4 }

        
        airCoolingNotificationPriority OBJECT-TYPE
            SYNTAX NotificationPriority
            MAX-ACCESS read-write
            STATUS current
            DESCRIPTION
                "See textual convention for details."
            ::= { airCoolingNotificationEntry 5 }

        
        airCoolingNotificationState OBJECT-TYPE
            SYNTAX NotificationState
            MAX-ACCESS read-only
            STATUS current
            DESCRIPTION
                "See textual convention for details."
            ::= { airCoolingNotificationEntry 6 }

        
        airCoolingStateTable OBJECT-TYPE
            SYNTAX SEQUENCE OF AirCoolingStateEntry
            MAX-ACCESS not-accessible
            STATUS current
            DESCRIPTION
                "Air cooling state information."
            ::= { airCoolingStatus 2 }

        
        airCoolingStateEntry OBJECT-TYPE
            SYNTAX AirCoolingStateEntry
            MAX-ACCESS not-accessible
            STATUS current
            DESCRIPTION
                "An entry in the airCoolingStateTable."
            INDEX { airCoolingNotificationCycleIdx }
            ::= { airCoolingStateTable 1 }

        
        AirCoolingStateEntry ::=
            SEQUENCE { 
                airCoolingOutletTemperature
                    Integer32,
                airCoolingOutletTemperatureSensor
                    NotificationState,
                airCoolingInletTemperature
                    Integer32,
                airCoolingInletTemperatureSensor
                    NotificationState
             }

        airCoolingOutletTemperature OBJECT-TYPE
            SYNTAX Integer32
            UNITS "1/10 degree Celsius"
            MAX-ACCESS read-write
            STATUS current
            DESCRIPTION
                "Indicates the temperature of the coolant flowing out of the 
                transmitter rack toward the heat exchanger. The temperature 
                must not exceed a maximum value of 65 degree C.
                "
            ::= { airCoolingStateEntry 2 }

        
        airCoolingOutletTemperatureSensor OBJECT-TYPE
            SYNTAX NotificationState
            MAX-ACCESS read-write
            STATUS current
            DESCRIPTION
                "Outlet temperature sensor state.
                
                Possible values:
                fault(3)
                ok(5)"
            ::= { airCoolingStateEntry 3 }

        
        airCoolingInletTemperature OBJECT-TYPE
            SYNTAX Integer32
            UNITS "1/10 degree Celsius"
            MAX-ACCESS read-write
            STATUS current
            DESCRIPTION
                "Indicates the temperature of the coolant flowing into the transmitter rack.
                
                Value only relevant if airCoolingCfgType is conductedInletOutletAir(2)."
            ::= { airCoolingStateEntry 4 }

        
        airCoolingInletTemperatureSensor OBJECT-TYPE
            SYNTAX NotificationState
            MAX-ACCESS read-write
            STATUS current
            DESCRIPTION
                "Indicates the status of the temperature sensor at the inlet of the 
                rack. If a fault is indicated, first check the connecting cable 
                between the sensor and the cooling interface card (CIF) in the 
                R&S TCE900 system control unit.
                
                Possible values:
                fault(3)
                ok(5)
                
                Value only relevant if airCoolingCfgType is conductedInletOutletAir(2)."
            ::= { airCoolingStateEntry 5 }

        
        airCoolingPressureTable OBJECT-TYPE
            SYNTAX SEQUENCE OF AirCoolingPressureEntry
            MAX-ACCESS not-accessible
            STATUS current
            DESCRIPTION
                "pressure information"
            ::= { airCoolingStatus 3 }

        
        airCoolingPressureEntry OBJECT-TYPE
            SYNTAX AirCoolingPressureEntry
            MAX-ACCESS not-accessible
            STATUS current
            DESCRIPTION
                "An entry in the airCoolingPressureTable."
            INDEX { airCoolingNotificationCycleIdx, airCoolingPressureSensorIdx }
            ::= { airCoolingPressureTable 1 }

        
        AirCoolingPressureEntry ::=
            SEQUENCE { 
                airCoolingPressureSensorIdx
                    Unsigned32,
                airCoolingPressureValue
                    Integer32,
                airCoolingPressureSensor
                    NotificationState
             }

        airCoolingPressureSensorIdx OBJECT-TYPE
            SYNTAX Unsigned32 (1..3)
            MAX-ACCESS not-accessible
            STATUS current
            DESCRIPTION
                "1 - pressure sensor 1
                2 - pressure sensor 2
                3 - virtual sum pressure sensor"
            ::= { airCoolingPressureEntry 2 }

        
        airCoolingPressureValue OBJECT-TYPE
            SYNTAX Integer32
            UNITS "deci Pascal"
            MAX-ACCESS read-only
            STATUS current
            DESCRIPTION
                "Indicates the pressure in the rack. Two differential pressure 
                sensors (Sensor 1 and Sensor 2) measure the differential air 
                pressure inside and outside the rack. If a sensor fails, the 
                remaining sensor continues to indicate the pressure inside the 
                rack. 
                "
            ::= { airCoolingPressureEntry 3 }

        
        airCoolingPressureSensor OBJECT-TYPE
            SYNTAX NotificationState
            MAX-ACCESS read-only
            STATUS current
            DESCRIPTION
                "Indicates the status of pressure sensor. If a fault is indicated, 
                first check the connecting cable between the sensor and the air 
                cooling interface card in the R&S TCE900 system control unit.
                "
            ::= { airCoolingPressureEntry 4 }

        
        airCoolingFanTable OBJECT-TYPE
            SYNTAX SEQUENCE OF AirCoolingFanEntry
            MAX-ACCESS not-accessible
            STATUS current
            DESCRIPTION
                "Description."
            ::= { airCoolingStatus 4 }

        
        airCoolingFanEntry OBJECT-TYPE
            SYNTAX AirCoolingFanEntry
            MAX-ACCESS not-accessible
            STATUS current
            DESCRIPTION
                "An entry in the airCoolingFanTable."
            INDEX { airCoolingNotificationCycleIdx, airCoolingFanIdx }
            ::= { airCoolingFanTable 1 }

        
        AirCoolingFanEntry ::=
            SEQUENCE { 
                airCoolingFanIdx
                    Unsigned32,
                airCoolingFanSummary
                    NotificationState,
                airCoolingFanCommunication
                    NotificationState,
                airCoolingFanCurrentSpeed
                    Unsigned32
             }

        airCoolingFanIdx OBJECT-TYPE
            SYNTAX Unsigned32 (1..2)
            MAX-ACCESS not-accessible
            STATUS current
            DESCRIPTION
                "fan index"
            ::= { airCoolingFanEntry 2 }

        
        airCoolingFanSummary OBJECT-TYPE
            SYNTAX NotificationState
            MAX-ACCESS read-only
            STATUS current
            DESCRIPTION
                "Indicates the condition of the fan."
            ::= { airCoolingFanEntry 3 }

        
        airCoolingFanCommunication OBJECT-TYPE
            SYNTAX NotificationState
            MAX-ACCESS read-only
            STATUS current
            DESCRIPTION
                "Indicates whether the fan is connected to the ACIF board."
            ::= { airCoolingFanEntry 4 }

        
        airCoolingFanCurrentSpeed OBJECT-TYPE
            SYNTAX Unsigned32
            UNITS "percent"
            MAX-ACCESS read-only
            STATUS current
            DESCRIPTION
                "Indicates the current speed of the fan."
            ::= { airCoolingFanEntry 5 }

        
        airCoolingConfiguration OBJECT IDENTIFIER ::= { rsXx9AirCoolingObjects 2 }

        
        airCoolingConfigTable OBJECT-TYPE
            SYNTAX SEQUENCE OF AirCoolingConfigEntry
            MAX-ACCESS not-accessible
            STATUS current
            DESCRIPTION
                "Liquid cooling configuration."
            ::= { airCoolingConfiguration 1 }

        
        airCoolingConfigEntry OBJECT-TYPE
            SYNTAX AirCoolingConfigEntry
            MAX-ACCESS not-accessible
            STATUS current
            DESCRIPTION
                "An entry in the airCoolingConfigTable."
            INDEX { airCoolingCfgCycleIdx }
            ::= { airCoolingConfigTable 1 }

        
        AirCoolingConfigEntry ::=
            SEQUENCE { 
                airCoolingCfgCycleIdx
                    Unsigned32,
                airCoolingCfgType
                    INTEGER
             }

        airCoolingCfgCycleIdx OBJECT-TYPE
            SYNTAX Unsigned32 (1..2)
            MAX-ACCESS not-accessible
            STATUS current
            DESCRIPTION
                "Air cooling cycle index."
            ::= { airCoolingConfigEntry 1 }

        
        airCoolingCfgType OBJECT-TYPE
            SYNTAX INTEGER
                {
                conductedOutletAir(1),
                conductedInletOutletAir(2)
                }
            MAX-ACCESS read-write
            STATUS current
            DESCRIPTION
                "Used to set the specific Air Cooling Type. 
                Choose ConductedOutletAir(1) or ConductedInletOutletAir(2). 
                In case of ConductedInletOutletAir(2) there is an additional temperature sensor for incoming air."
            ::= { airCoolingConfigEntry 2 }

        
        rsXx9AirCoolingConformance OBJECT IDENTIFIER ::= { rsXx9AirCooling 2 }

        
        rsXx9AirCoolingCompliances OBJECT IDENTIFIER ::= { rsXx9AirCoolingConformance 1 }

        
        rsXx9AirCoolingBasicCompliance MODULE-COMPLIANCE
            STATUS current
            DESCRIPTION 
                "The compliance statement for the XX9000 air cooling system."
            MODULE -- this module
                MANDATORY-GROUPS { rsXx9AirCoolingObj, rsXx9AirCoolingNotify, rsXx9AirCoolingConductedObj }
            ::= { rsXx9AirCoolingCompliances 1 }

        
        rsXx9AirCoolingGroups OBJECT IDENTIFIER ::= { rsXx9AirCoolingConformance 2 }

        
        rsXx9AirCoolingObj OBJECT-GROUP
            OBJECTS { airCoolingNotificationName, airCoolingNotificationMask, airCoolingNotificationPriority, airCoolingNotificationState, airCoolingCfgType, 
                airCoolingOutletTemperature, airCoolingOutletTemperatureSensor, airCoolingPressureValue, airCoolingPressureSensor, airCoolingFanSummary, 
                airCoolingFanCommunication, airCoolingFanCurrentSpeed }
            STATUS current
            DESCRIPTION 
                "air cooling objects"
            ::= { rsXx9AirCoolingGroups 1 }

        
        rsXx9AirCoolingConductedObj OBJECT-GROUP
            OBJECTS { airCoolingInletTemperature, airCoolingInletTemperatureSensor }
            STATUS current
            DESCRIPTION 
                "Objects relevant only if airCoolingCfgType is conductedInletOutletAir(2)."
            ::= { rsXx9AirCoolingGroups 2 }

        
        rsXx9AirCoolingNotify NOTIFICATION-GROUP
            NOTIFICATIONS { airCoolingSummary, airCoolingSensorsSummary }
            STATUS current
            DESCRIPTION 
                "air cooling notifications"
            ::= { rsXx9AirCoolingGroups 3 }

        
    
    END

--
-- RS-XX9-AIR-COOLING-MIB.mi2
--
