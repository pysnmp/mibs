ACOS-VRRPA-COMMON-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		vrrpACommonModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "vrrpACommonModule OID for ACOS"
				::=  {  acosSchema 6 }

common		 OBJECT IDENTIFIER ::= { vrrpACommonModule 1}

commonStatsTable OBJECT-TYPE
	 SYNTAX SEQUENCE OF CommonStatsEntry
	 MAX-ACCESS not-accessible
	 STATUS current
	 DESCRIPTION
	 "HA VRRP-A Global Commands from object 'vrrp-a.common'"
	::= {common 1}

commonStatsEntry OBJECT-TYPE
	SYNTAX CommonStatsEntry
	MAX-ACCESS not-accessible
	STATUS current
	DESCRIPTION
		"The commonStats stats entry"
	INDEX {
		commonStatsSlotId
	}
	::= { commonStatsTable 1 }

CommonStatsEntry ::=
	SEQUENCE {
		commonStatsSlotId Integer32,
		commonStatsVrrpCommonDummy	 CounterBasedGauge64
	}

commonStatsSlotId OBJECT-TYPE
	 SYNTAX Integer32
	 MAX-ACCESS read-only
	 STATUS current
	 DESCRIPTION
		 ""
	::= { commonStatsEntry 1 }

commonStatsVrrpCommonDummy OBJECT-TYPE
	 SYNTAX Integer32
	 MAX-ACCESS read-only
	 STATUS current
	 DESCRIPTION
		 "vrrp_common_dummy"
	::= { commonStatsEntry 2 }

END
