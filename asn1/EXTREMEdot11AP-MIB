-- 
--  $RCSfile: extreme.mib,v $ - ExtremeWare enterprise MIB
-- 
--  Copyright (c) 1997 - 2002 by Extreme Networks Inc.
--  
-- 	  Extreme Networks
--       http://www.extremenetworks.com
-- 
-- 
-- This file contains multiple ASN.1 Module definitions
--


-- ********************************************************************* 
--  EXTREME 802.11 Access Point Management Information Base, based
--  on IEEE 802.11 AP MIB.
-- ********************************************************************* 
EXTREMEdot11AP-MIB DEFINITIONS ::= BEGIN 
	
	
	IMPORTS 
	MODULE-IDENTITY 	FROM SNMPv2-SMI
	OBJECT-TYPE 		FROM SNMPv2-SMI
	TruthValue 		FROM SNMPv2-TC 
	extremeAP		FROM EXTREME-BASE-MIB
	ifIndex 		FROM RFC1213-MIB
	Unsigned32		FROM SNMPv2-SMI;

-- ********************************************************************* 
--  MODULE IDENTITY 
-- ********************************************************************* 

	extremeDot11ap MODULE-IDENTITY
	LAST-UPDATED "0211140000Z" 
	ORGANIZATION "Extreme Networks"
	CONTACT-INFO " " 

	DESCRIPTION 
	"This MIB module provides managemetn of a set of APs.  It is based
	 on the IEEE AP MIB with additions for better indexing."
    ::= { extremeAP 21 }

-- ********************************************************************* 
--  Major sections 
-- ********************************************************************* 

-- ********************************************************************* 
--  End of EXTREME AP MIB
-- ********************************************************************* 
END
