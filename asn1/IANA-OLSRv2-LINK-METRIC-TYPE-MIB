IANA-OLSRv2-LINK-METRIC-TYPE-MIB DEFINITIONS ::= BEGIN

   IMPORTS
       MODULE-IDENTITY, mib-2
                 FROM SNMPv2-SMI
       TEXTUAL-CONVENTION
                 FROM SNMPv2-TC;

   ianaolsrv2LinkMetricType MODULE-IDENTITY
       LAST-UPDATED "201404090000Z"  -- 09 April 2014
       ORGANIZATION "IANA"
       CONTACT-INFO "Internet Assigned Numbers Authority

                     Postal: ICANN
                             12025 Waterfront Drive, Suite 300
                             Los Angeles, CA 90094-2536

                     Tel:    +1 310 301 5800
                     E-Mail: iana@iana.org"
       DESCRIPTION  "This MIB module defines the
                     IANAolsrv2LinkMetricType Textual
                     Convention, and thus the enumerated values of
                     the olsrv2LinkMetricType object defined in
                     the OLSRv2-MIB."
       REVISION      "201404090000Z"  -- 09 April 2014
       DESCRIPTION   "Initial version of this MIB as published in
                      RFC 7184."

       ::= { mib-2 221 }

   IANAolsrv2LinkMetricTypeTC ::= TEXTUAL-CONVENTION
      STATUS      current
      DESCRIPTION
         "This data type is used as the syntax of the
          olsrv2LinkMetricType object in the definition
          of the OLSRv2-MIB module.

          The olsrv2LinkMetricType corresponds to
          LINK_METRIC_TYPE of OLSRv2 (RFC 7181).
          OLSRv2 uses bidirectional additive link metrics
          to determine shortest distance routes (i.e.,
          routes with smallest total of link metric values).

          OLSRv2 has established a registry for the LINK_METRIC_TYPEs
          (denoted 'LINK_METRIC Address Block TLV Type Extensions'):
                 http://www.iana.org/assignments/manet-parameters/

          This is done in Section 24.5 in OLSRv2 (RFC 7181).
          The LINK_METRIC_TYPE (which has as corresponding
          object in the MIB module olsrv2LinkMetricType)
          corresponds to the type extension of
          the LINK_METRIC TLV that is set up in the
          'LINK_METRIC Address Block TLV Type Extensions' registry.
          Whenever new link metric types are added to that registry,
          IANA MUST update this textual convention accordingly.

          The definition of this textual convention with the
          addition of newly assigned values is published
          periodically by the IANA, in either the Assigned
          Numbers RFC, or some derivative of it specific to
          Internet Network Management number assignments.  (The
          latest arrangements can be obtained by contacting the
          IANA.)

          Requests for new values should be made to IANA via
          email (iana@iana.org)."
      SYNTAX  INTEGER {
                 unknown(0)     -- Link metric meaning assigned
                                --       by administrative action
                                -- 1-223 Unassigned
                                -- 224-255 Reserved for
                                --       Experimental Use
      }

      END
