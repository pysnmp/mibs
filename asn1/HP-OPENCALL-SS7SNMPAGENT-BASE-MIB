--
-- Hewlett Packard Company
-- MIB Definition for the OC traps (from logs)
-- 
HP-OPENCALL-SS7SNMPAGENT-BASE-MIB DEFINITIONS ::= BEGIN

   IMPORTS
 	MODULE-IDENTITY, OBJECT-TYPE, NOTIFICATION-TYPE,
        enterprises
                FROM SNMPv2-SMI

        DisplayString
                FROM SNMPv2-TC ;


-- deplacement de MODULE-IDENTITY en debut de module
-- ajout de CONTACT-INFO dans le MODULE-IDENTITY
   openCall MODULE-IDENTITY
       LAST-UPDATED "200409090000Z"
       ORGANIZATION "Hewlett Packard Company,
		     OpenCall Business Unit"

       CONTACT-INFO "Raymond Mercier"
	   DESCRIPTION
               "This is the MIB module that describes an HP private mib
		for the management of OpenCall traps. "
    REVISION    "200409090000Z"
    DESCRIPTION "text"
    REVISION    "200309090000Z"
    DESCRIPTION "text"

       ::= { enterprises hp(11) nm(2) inNetElem(29) 2 }

--   hp                OBJECT IDENTIFIER ::= { enterprises 11 }
--   nm                OBJECT IDENTIFIER ::= { hp 2 }
--   inNetElem         OBJECT IDENTIFIER ::= { nm 29 }


-- Hereunder, in order to freeze the ObjectID in the mib tree, only object 
-- Traps has been defined

-- First level tree -----------------------------------------
   openCallTraps     OBJECT IDENTIFIER ::= { openCall 0 }  


-- Traps variables -----------------------------------------
-- Trap: (sourceName, sourceOID, eventType, probableCause, severity, additionalText)

--   sourcePlatformEntity       OBJECT IDENTIFIER ::= { openCallTraps 1 }  
--   sourceObjectID	        	OBJECT IDENTIFIER ::= { openCallTraps 2 }
--   perceveidSeverity          OBJECT IDENTIFIER ::= { openCallTraps 3 }  
--   alarmText                  OBJECT IDENTIFIER ::= { openCallTraps 4 }  
--   probableCause              OBJECT IDENTIFIER ::= { openCallTraps 5 }  
--   correctiveAction           OBJECT IDENTIFIER ::= { openCallTraps 6 }  
--   timeStamp                  OBJECT IDENTIFIER ::= { openCallTraps 7 }  

-- remplacer not-accessible par read-only
   sourcePlatformEntity OBJECT-TYPE
       SYNTAX     DisplayString 
       MAX-ACCESS read-only
       STATUS     current
       DESCRIPTION
               " This is the source entity that sends the trap, typically this
			   is a combination of platform and machine name. (ex: oc_platform, nta2225.india.hp.com"
       ::= { openCallTraps 1 }

   sourceObjectID OBJECT-TYPE
       SYNTAX     DisplayString 
       MAX-ACCESS read-only
       STATUS     current
       DESCRIPTION
               " This identifies the objectID of the instance that sends the trap. (ex: Process Name)"
       ::= { openCallTraps 2 }

   perceveidSeverity OBJECT-TYPE
       SYNTAX     DisplayString 
       MAX-ACCESS read-only
       STATUS     current
       DESCRIPTION
               " This identifies the severity of the trap. Possible severity are
			   1. Major
			   2. Minor
			   3. Warning
			   4. Informative
			   5. Critical"
       ::= { openCallTraps 3 }

   alarmText OBJECT-TYPE
       SYNTAX     DisplayString 
       MAX-ACCESS read-only
       STATUS     current
       DESCRIPTION
               " This describes the alarm generating the trap."
       ::= { openCallTraps 4 }

   probableCause OBJECT-TYPE
       SYNTAX     DisplayString 
       MAX-ACCESS read-only
       STATUS     current
       DESCRIPTION
               " This identifies the probable cause of the trap."
       ::= { openCallTraps 5 }

   correctiveAction OBJECT-TYPE
       SYNTAX     DisplayString 
       MAX-ACCESS read-only
       STATUS     current
       DESCRIPTION
               " This describes the actions to apply for correcting the
               problem that generated this alarm."
       ::= { openCallTraps 6 }

-- renommer timeStamp en htimeStamp
   htimeStamp OBJECT-TYPE
       SYNTAX     DisplayString 
       MAX-ACCESS read-only
       STATUS     current
       DESCRIPTION
               " Time-Stamp recorded in the log generated by this alarm."
       ::= { openCallTraps 7 }


-- trap definitions

-- nécessaire de remplacer remplacer HPOC- par hHPOC-
   hHPOC-3100155  NOTIFICATION-TYPE
        OBJECTS {  	sourcePlatformEntity, 
			sourceObjectID,
			perceveidSeverity,
			alarmText,
			probableCause,
			correctiveAction,
			htimeStamp }
        STATUS  current
        DESCRIPTION
                "ISUP application <number> : Continuity test failed."
        ::= { openCallTraps 3100155 }


hHPOC-8400042 NOTIFICATION-TYPE
        OBJECTS {  	sourcePlatformEntity, 
			sourceObjectID,
			perceveidSeverity,
			alarmText,
			probableCause,
			correctiveAction,
			htimeStamp }
        STATUS  current
        DESCRIPTION
                "FTC: Peer FTC connection failure."
        ::= { openCallTraps 8400042 }


hHPOC-8400084  NOTIFICATION-TYPE
        OBJECTS {  	sourcePlatformEntity, 
			sourceObjectID,
			perceveidSeverity,
			alarmText,
			probableCause,
			correctiveAction,
			htimeStamp }
        STATUS  current
        DESCRIPTION
                "FTC: system switch-over occurred."
        ::= { openCallTraps 8400084 }


hHPOC-8400085  NOTIFICATION-TYPE
        OBJECTS {  	sourcePlatformEntity, 
			sourceObjectID,
			perceveidSeverity,
			alarmText,
			probableCause,
			correctiveAction,
			htimeStamp }
        STATUS  current
        DESCRIPTION
                "FTC: Active process is down."
        ::= { openCallTraps 8400085 }


hHPOC-8400086  NOTIFICATION-TYPE
        OBJECTS {  	sourcePlatformEntity, 
			sourceObjectID,
			perceveidSeverity,
			alarmText,
			probableCause,
			correctiveAction,
			htimeStamp }
        STATUS  current
        DESCRIPTION
                "FTC: Standby process is down."
        ::= { openCallTraps 8400086 }


hHPOC-8400087  NOTIFICATION-TYPE
        OBJECTS {  	sourcePlatformEntity, 
			sourceObjectID,
			perceveidSeverity,
			alarmText,
			probableCause,
			correctiveAction,
			htimeStamp }
        STATUS  current
        DESCRIPTION
                "FTC: Process is active."
        ::= { openCallTraps 8400087 }


hHPOC-8400088  NOTIFICATION-TYPE
        OBJECTS {  	sourcePlatformEntity, 
			sourceObjectID,
			perceveidSeverity,
			alarmText,
			probableCause,
			correctiveAction,
			htimeStamp }
        STATUS  current
        DESCRIPTION
                "FTC: Process is hotstandby."
        ::= { openCallTraps 8400088 }


hHPOC-9000332  NOTIFICATION-TYPE
        OBJECTS {  	sourcePlatformEntity, 
			sourceObjectID,
			perceveidSeverity,
			alarmText,
			probableCause,
			correctiveAction,
			htimeStamp }
        STATUS  current
        DESCRIPTION
                "ss7Stack-mtp: MTPL3 SYNCHRO ABORTED."
        ::= { openCallTraps 9000332 }


hHPOC-9000334  NOTIFICATION-TYPE
        OBJECTS {  	sourcePlatformEntity, 
			sourceObjectID,
			perceveidSeverity,
			alarmText,
			probableCause,
			correctiveAction,
			htimeStamp }
        STATUS  current
        DESCRIPTION
                "ss7Stack-mtp: MTPL3 SYNCHRO ABORTED."
        ::= { openCallTraps 9000334 }


hHPOC-9000336  NOTIFICATION-TYPE
        OBJECTS {  	sourcePlatformEntity, 
			sourceObjectID,
			perceveidSeverity,
			alarmText,
			probableCause,
			correctiveAction,
			htimeStamp }
        STATUS  current
        DESCRIPTION
                "ss7Stack-mtp: MTPL3 SYNCHRO ABORTED."
        ::= { openCallTraps 9000336 }


hHPOC-9000341  NOTIFICATION-TYPE
        OBJECTS {  	sourcePlatformEntity, 
			sourceObjectID,
			perceveidSeverity,
			alarmText,
			probableCause,
			correctiveAction,
			htimeStamp }
        STATUS  current
        DESCRIPTION
                "ss7Stack-mtp: Link out of service."
        ::= { openCallTraps 9000341 }


hHPOC-9000342  NOTIFICATION-TYPE
        OBJECTS {  	sourcePlatformEntity, 
			sourceObjectID,
			perceveidSeverity,
			alarmText,
			probableCause,
			correctiveAction,
			htimeStamp }
        STATUS  current
        DESCRIPTION
                "ss7Stack-mtp: Link inactive."
        ::= { openCallTraps 9000342 }


hHPOC-9000343  NOTIFICATION-TYPE
        OBJECTS {  	sourcePlatformEntity, 
			sourceObjectID,
			perceveidSeverity,
			alarmText,
			probableCause,
			correctiveAction,
			htimeStamp }
        STATUS  current
        DESCRIPTION
                "ss7Stack-mtp: Link active."
        ::= { openCallTraps 9000343 }


hHPOC-9000344  NOTIFICATION-TYPE
        OBJECTS {  	sourcePlatformEntity, 
			sourceObjectID,
			perceveidSeverity,
			alarmText,
			probableCause,
			correctiveAction,
			htimeStamp }
        STATUS  current
        DESCRIPTION
                "ss7Stack-mtp: Linkset out of service."
        ::= { openCallTraps 9000344 }


hHPOC-9000345  NOTIFICATION-TYPE
        OBJECTS {  	sourcePlatformEntity, 
			sourceObjectID,
			perceveidSeverity,
			alarmText,
			probableCause,
			correctiveAction,
			htimeStamp }
        STATUS  current
        DESCRIPTION
                "ss7Stack-mtp: Linkset inactive."
        ::= { openCallTraps 9000345 }


hHPOC-9000346  NOTIFICATION-TYPE
        OBJECTS {  	sourcePlatformEntity, 
			sourceObjectID,
			perceveidSeverity,
			alarmText,
			probableCause,
			correctiveAction,
			htimeStamp }
        STATUS  current
        DESCRIPTION
                "ss7Stack-mtp: Linkset active."
        ::= { openCallTraps 9000346 }


hHPOC-9000347  NOTIFICATION-TYPE
        OBJECTS {  	sourcePlatformEntity, 
			sourceObjectID,
			perceveidSeverity,
			alarmText,
			probableCause,
			correctiveAction,
			htimeStamp }
        STATUS  current
        DESCRIPTION
                "ss7Stack-mtp: MTP out of service."
        ::= { openCallTraps 9000347 }

hHPOC-9000348  NOTIFICATION-TYPE
        OBJECTS {  	sourcePlatformEntity, 
			sourceObjectID,
			perceveidSeverity,
			alarmText,
			probableCause,
			correctiveAction,
			htimeStamp }
        STATUS  current
        DESCRIPTION
                "ss7Stack-mtp: MTP active."
        ::= { openCallTraps 9000348 }

hHPOC-9000349  NOTIFICATION-TYPE
        OBJECTS {  	sourcePlatformEntity, 
			sourceObjectID,
			perceveidSeverity,
			alarmText,
			probableCause,
			correctiveAction,
			htimeStamp }
        STATUS  current
        DESCRIPTION
                "ss7Stack-mtp: MTP inactive."
        ::= { openCallTraps 9000349 }

hHPOC-9000350  NOTIFICATION-TYPE
        OBJECTS {  	sourcePlatformEntity, 
			sourceObjectID,
			perceveidSeverity,
			alarmText,
			probableCause,
			correctiveAction,
			htimeStamp }
        STATUS  current
        DESCRIPTION
                "ss7Stack-mtp: MTP restarting."
        ::= { openCallTraps 9000350 }

hHPOC-9000354  NOTIFICATION-TYPE
        OBJECTS {  	sourcePlatformEntity, 
			sourceObjectID,
			perceveidSeverity,
			alarmText,
			probableCause,
			correctiveAction,
			htimeStamp }
        STATUS  current
        DESCRIPTION
                "ss7Stack-mtp: <string> user MTP3 connection closed."
        ::= { openCallTraps 9000354 }

hHPOC-9000355  NOTIFICATION-TYPE
        OBJECTS {  	sourcePlatformEntity, 
			sourceObjectID,
			perceveidSeverity,
			alarmText,
			probableCause,
			correctiveAction,
			htimeStamp }
        STATUS  current
        DESCRIPTION
                "ss7Stack-mtp: <string> user MTP3 connection open."
        ::= { openCallTraps 9000355 }

hHPOC-9000356  NOTIFICATION-TYPE
        OBJECTS {  	sourcePlatformEntity, 
			sourceObjectID,
			perceveidSeverity,
			alarmText,
			probableCause,
			correctiveAction,
			htimeStamp }
        STATUS  current
        DESCRIPTION
                "ss7Stack-mtp: Link outbound congestion."
        ::= { openCallTraps 9000356 }

hHPOC-9000357  NOTIFICATION-TYPE
        OBJECTS {  	sourcePlatformEntity, 
			sourceObjectID,
			perceveidSeverity,
			alarmText,
			probableCause,
			correctiveAction,
			htimeStamp }
        STATUS  current
        DESCRIPTION
                "ss7Stack-mtp: Deletion not allowed, VPC <number> in use"
        ::= { openCallTraps 9000357 }

hHPOC-9000635  NOTIFICATION-TYPE
        OBJECTS {  	sourcePlatformEntity, 
			sourceObjectID,
			perceveidSeverity,
			alarmText,
			probableCause,
			correctiveAction,
			htimeStamp }
        STATUS  current
        DESCRIPTION
                "ss7Stack-sccp: SCCP is now deactivated and disconnected of MTP"
        ::= { openCallTraps 9000635 }

hHPOC-9000636  NOTIFICATION-TYPE
        OBJECTS {  	sourcePlatformEntity, 
			sourceObjectID,
			perceveidSeverity,
			alarmText,
			probableCause,
			correctiveAction,
			htimeStamp }
        STATUS  current
        DESCRIPTION
                "ss7Stack-sccp: SCCP is now reactivated and connected to MTP"
        ::= { openCallTraps 9000636 }

hHPOC-9000681  NOTIFICATION-TYPE
        OBJECTS {  	sourcePlatformEntity, 
			sourceObjectID,
			perceveidSeverity,
			alarmText,
			probableCause,
			correctiveAction,
			htimeStamp }
        STATUS  current
        DESCRIPTION
                "ss7Stack-sccp: Local SCCP user out of service."
        ::= { openCallTraps 9000681 }

hHPOC-9000682  NOTIFICATION-TYPE
        OBJECTS {  	sourcePlatformEntity, 
			sourceObjectID,
			perceveidSeverity,
			alarmText,
			probableCause,
			correctiveAction,
			htimeStamp }
        STATUS  current
        DESCRIPTION
                "ss7Stack-sccp: Local SCCP user in service."
        ::= { openCallTraps 9000682 }

hHPOC-9001260  NOTIFICATION-TYPE
        OBJECTS {  	sourcePlatformEntity, 
			sourceObjectID,
			perceveidSeverity,
			alarmText,
			probableCause,
			correctiveAction,
			htimeStamp }
        STATUS  current
        DESCRIPTION
                "ss7Stack-level2: <string>: double fan failure"
        ::= { openCallTraps 9001260 }

hHPOC-9001262  NOTIFICATION-TYPE
        OBJECTS {  	sourcePlatformEntity, 
			sourceObjectID,
			perceveidSeverity,
			alarmText,
			probableCause,
			correctiveAction,
			htimeStamp }
        STATUS  current
        DESCRIPTION
                "<string>: SIU reachable from standby."
        ::= { openCallTraps 9001262 }

hHPOC-9001268  NOTIFICATION-TYPE
        OBJECTS {  	sourcePlatformEntity, 
			sourceObjectID,
			perceveidSeverity,
			alarmText,
			probableCause,
			correctiveAction,
			htimeStamp }
        STATUS  current
        DESCRIPTION
                "<string>: SIU out of service."
        ::= { openCallTraps 9001268 }

hHPOC-9001269  NOTIFICATION-TYPE
        OBJECTS {  	sourcePlatformEntity, 
			sourceObjectID,
			perceveidSeverity,
			alarmText,
			probableCause,
			correctiveAction,
			htimeStamp }
        STATUS  current
        DESCRIPTION
                "<string>: SIU in service."
        ::= { openCallTraps 9001269 }

hHPOC-9001270  NOTIFICATION-TYPE
        OBJECTS {  	sourcePlatformEntity, 
			sourceObjectID,
			perceveidSeverity,
			alarmText,
			probableCause,
			correctiveAction,
			htimeStamp }
        STATUS  current
        DESCRIPTION
                "<string>: TSU unreachable from standby."
        ::= { openCallTraps 9001270 }

hHPOC-9001271  NOTIFICATION-TYPE
        OBJECTS {  	sourcePlatformEntity, 
			sourceObjectID,
			perceveidSeverity,
			alarmText,
			probableCause,
			correctiveAction,
			htimeStamp }
        STATUS  current
        DESCRIPTION
                "<string>: TSU reachable from standby."
        ::= { openCallTraps 9001271 }

hHPOC-9001272 NOTIFICATION-TYPE
        OBJECTS {  	sourcePlatformEntity, 
			sourceObjectID,
			perceveidSeverity,
			alarmText,
			probableCause,
			correctiveAction,
			htimeStamp }
        STATUS  current
        DESCRIPTION
                "<string>: TSU out of service."
        ::= { openCallTraps 9001272 }

hHPOC-9001273  NOTIFICATION-TYPE
        OBJECTS {  	sourcePlatformEntity, 
			sourceObjectID,
			perceveidSeverity,
			alarmText,
			probableCause,
			correctiveAction,
			htimeStamp }
        STATUS  current
        DESCRIPTION
                "<string>: TSU in service."
        ::= { openCallTraps 9001273 }

hHPOC-9001274  NOTIFICATION-TYPE
        OBJECTS {  	sourcePlatformEntity, 
			sourceObjectID,
			perceveidSeverity,
			alarmText,
			probableCause,
			correctiveAction,
			htimeStamp }
        STATUS  current
        DESCRIPTION
                "<string>: TSC out of service."
        ::= { openCallTraps 9001274 }

hHPOC-9001275  NOTIFICATION-TYPE
        OBJECTS {  	sourcePlatformEntity, 
			sourceObjectID,
			perceveidSeverity,
			alarmText,
			probableCause,
			correctiveAction,
			htimeStamp }
        STATUS  current
        DESCRIPTION
                "<string>: TSC in service."
        ::= { openCallTraps 9001275 }

hHPOC-9001276  NOTIFICATION-TYPE
        OBJECTS {  	sourcePlatformEntity, 
			sourceObjectID,
			perceveidSeverity,
			alarmText,
			probableCause,
			correctiveAction,
			htimeStamp }
        STATUS  current
        DESCRIPTION
                "<string>: TSU fan <number> has failed"
        ::= { openCallTraps 9001276 }

hHPOC-9001277  NOTIFICATION-TYPE
        OBJECTS {  	sourcePlatformEntity, 
			sourceObjectID,
			perceveidSeverity,
			alarmText,
			probableCause,
			correctiveAction,
			htimeStamp }
        STATUS  current
        DESCRIPTION
                "<string>: TSU -48VDC input <number> has failed"
        ::= { openCallTraps 9001277 }

hHPOC-9001278  NOTIFICATION-TYPE
        OBJECTS {  	sourcePlatformEntity, 
			sourceObjectID,
			perceveidSeverity,
			alarmText,
			probableCause,
			correctiveAction,
			htimeStamp }
        STATUS  current
        DESCRIPTION
                "<string>: TSU fan <number> has recovered operation."
        ::= { openCallTraps 9001278 }

hHPOC-9001279  NOTIFICATION-TYPE
        OBJECTS {  	sourcePlatformEntity, 
			sourceObjectID,
			perceveidSeverity,
			alarmText,
			probableCause,
			correctiveAction,
			htimeStamp }
        STATUS  current
        DESCRIPTION
                "<string>: TSU -48VDC input <number> has recovered operation"
        ::= { openCallTraps 9001279 }

hHPOC-9001280  NOTIFICATION-TYPE
        OBJECTS {  	sourcePlatformEntity, 
			sourceObjectID,
			perceveidSeverity,
			alarmText,
			probableCause,
			correctiveAction,
			htimeStamp }
        STATUS  current
        DESCRIPTION
                "<string>: SIU unreachable from standby."
        ::= { openCallTraps 9001280 }

hHPOC-8400089  NOTIFICATION-TYPE
        OBJECTS {       sourcePlatformEntity,
                        sourceObjectID,
                        perceveidSeverity,
                        alarmText,
                        probableCause,
                        correctiveAction,
                        htimeStamp }
        STATUS  current
        DESCRIPTION
                "FTC: Peer FTC connected"
        ::= { openCallTraps 8400089 }

hHPOC-40400001  NOTIFICATION-TYPE
        OBJECTS {  	sourcePlatformEntity, 
			sourceObjectID,
			perceveidSeverity,
			alarmText,
			probableCause,
			correctiveAction,
			htimeStamp }
        STATUS  current
        DESCRIPTION
                "The maximum licensed traffic capacity of <string> is exceeded."
        ::= { openCallTraps 40400001 }

hHPOC-40400002  NOTIFICATION-TYPE
        OBJECTS {  	sourcePlatformEntity, 
			sourceObjectID,
			perceveidSeverity,
			alarmText,
			probableCause,
			correctiveAction,
			htimeStamp }
        STATUS  current
        DESCRIPTION
                "The traffic of <string> is about to reach the maximum licensed traffic capacity of <string>."
        ::= { openCallTraps 40400002 }

hHPOC-40400003  NOTIFICATION-TYPE
        OBJECTS {  	sourcePlatformEntity, 
			sourceObjectID,
			perceveidSeverity,
			alarmText,
			probableCause,
			correctiveAction,
			htimeStamp }
        STATUS  current
        DESCRIPTION
                "The Traffic of <string> is now back below the maximum licensed traffic capacity."
        ::= { openCallTraps 40400003 }

hHPOC-40100001  NOTIFICATION-TYPE
        OBJECTS {  	sourcePlatformEntity, 
			sourceObjectID,
			perceveidSeverity,
			alarmText,
			probableCause,
			correctiveAction,
			htimeStamp }
        STATUS  current
        DESCRIPTION
                "M3UA EP <number>: Connected to IPSP/SGP <number>."
        ::= { openCallTraps 40100001 }

hHPOC-40100011  NOTIFICATION-TYPE
        OBJECTS {  	sourcePlatformEntity, 
			sourceObjectID,
			perceveidSeverity,
			alarmText,
			probableCause,
			correctiveAction,
			htimeStamp }
        STATUS  current
        DESCRIPTION
                "M3UA EP <number>: Association with IPSP/SGP <number> has been lost."
        ::= { openCallTraps 40100011 }

hHPOC-40100040  NOTIFICATION-TYPE
        OBJECTS {  	sourcePlatformEntity, 
			sourceObjectID,
			perceveidSeverity,
			alarmText,
			probableCause,
			correctiveAction,
			htimeStamp }
        STATUS  current
        DESCRIPTION
                "M3UA EP <number>: SCTP listening FAILURE. Stop the M3UA stack."
        ::= { openCallTraps 40100040 }

hHPOC-40100501  NOTIFICATION-TYPE
        OBJECTS {  	sourcePlatformEntity, 
			sourceObjectID,
			perceveidSeverity,
			alarmText,
			probableCause,
			correctiveAction,
			htimeStamp }
        STATUS  current
        DESCRIPTION
                "Failed M3UA General Configuration request for reason <number>."
        ::= { openCallTraps 40100501 }

hHPOC-40100502  NOTIFICATION-TYPE
        OBJECTS {  	sourcePlatformEntity, 
			sourceObjectID,
			perceveidSeverity,
			alarmText,
			probableCause,
			correctiveAction,
			htimeStamp }
        STATUS  current
        DESCRIPTION
                "Stack initialization failure."
        ::= { openCallTraps 40100502 }

hHPOC-40100601  NOTIFICATION-TYPE
        OBJECTS {  	sourcePlatformEntity, 
			sourceObjectID,
			perceveidSeverity,
			alarmText,
			probableCause,
			correctiveAction,
			htimeStamp }
        STATUS  current
        DESCRIPTION
                "M3UA EP <number>: RepMgr Service lost by the Ha Component. Graceful shutdown requested"
        ::= { openCallTraps 40100601 }

hHPOC-40100607  NOTIFICATION-TYPE
        OBJECTS {  	sourcePlatformEntity, 
			sourceObjectID,
			perceveidSeverity,
			alarmText,
			probableCause,
			correctiveAction,
			htimeStamp }
        STATUS  current
        DESCRIPTION
                "M3UA EP <number> enters flowcontrol"
        ::= { openCallTraps 40100607 }

hHPOC-40100608  NOTIFICATION-TYPE
        OBJECTS {  	sourcePlatformEntity, 
			sourceObjectID,
			perceveidSeverity,
			alarmText,
			probableCause,
			correctiveAction,
			htimeStamp }
        STATUS  current
        DESCRIPTION
                "M3UA EP <number> exits flowcontrol"
        ::= { openCallTraps 40100608 }

hHPOC-40100801  NOTIFICATION-TYPE
        OBJECTS {  	sourcePlatformEntity, 
			sourceObjectID,
			perceveidSeverity,
			alarmText,
			probableCause,
			correctiveAction,
			htimeStamp }
        STATUS  current
        DESCRIPTION
                "M3UA: Remote DPC <number> is available"
        ::= { openCallTraps 40100801 }

hHPOC-40100802  NOTIFICATION-TYPE
        OBJECTS {  	sourcePlatformEntity, 
			sourceObjectID,
			perceveidSeverity,
			alarmText,
			probableCause,
			correctiveAction,
			htimeStamp }
        STATUS  current
        DESCRIPTION
                "M3UA: Remote DPC <number> is unavailable"
        ::= { openCallTraps 40100802 }

hHPOC-40100803  NOTIFICATION-TYPE
        OBJECTS {  	sourcePlatformEntity, 
			sourceObjectID,
			perceveidSeverity,
			alarmText,
			probableCause,
			correctiveAction,
			htimeStamp }
        STATUS  current
        DESCRIPTION
                "M3UA: Remote DPC <number> is congested"
        ::= { openCallTraps 40100803 }

hHPOC-40100804  NOTIFICATION-TYPE
        OBJECTS {  	sourcePlatformEntity, 
			sourceObjectID,
			perceveidSeverity,
			alarmText,
			probableCause,
			correctiveAction,
			htimeStamp }
        STATUS  current
        DESCRIPTION
                "M3UA: Remote DPC <number> is congested at level <number>"
        ::= { openCallTraps 40100804 }

hHPOC-40100806  NOTIFICATION-TYPE
        OBJECTS {  	sourcePlatformEntity, 
			sourceObjectID,
			perceveidSeverity,
			alarmText,
			probableCause,
			correctiveAction,
			htimeStamp }
        STATUS  current
        DESCRIPTION
                "M3UA: Remote AS (DPC <number> SI <number>) is active"
        ::= { openCallTraps 40100806 }

hHPOC-40100807  NOTIFICATION-TYPE
        OBJECTS {  	sourcePlatformEntity, 
			sourceObjectID,
			perceveidSeverity,
			alarmText,
			probableCause,
			correctiveAction,
			htimeStamp }
        STATUS  current
        DESCRIPTION
                "M3UA: Remote AS (DPC <number> SI <number>) is inactive"
        ::= { openCallTraps 40100807 }

hHPOC-40100809  NOTIFICATION-TYPE
        OBJECTS {  	sourcePlatformEntity, 
			sourceObjectID,
			perceveidSeverity,
			alarmText,
			probableCause,
			correctiveAction,
			htimeStamp }
        STATUS  current
        DESCRIPTION
                "Switch transport to MTP for DPC <number>"
        ::= { openCallTraps 40100809 }

hHPOC-40100810  NOTIFICATION-TYPE
        OBJECTS {  	sourcePlatformEntity, 
			sourceObjectID,
			perceveidSeverity,
			alarmText,
			probableCause,
			correctiveAction,
			htimeStamp }
        STATUS  current
        DESCRIPTION
                "Switch transport to M3UA for DPC <number>"
        ::= { openCallTraps 40100810 }

hHPOC-40300002  NOTIFICATION-TYPE
        OBJECTS {       sourcePlatformEntity,
                        sourceObjectID,
                        perceveidSeverity,
                        alarmText,
                        probableCause,
                        correctiveAction,
                        htimeStamp }
        STATUS  current
        DESCRIPTION
                "Failed <string> request for <string> Id=<number>, error code <number>"
        ::= { openCallTraps 40300002 }

hHPOC-40300003  NOTIFICATION-TYPE
        OBJECTS {       sourcePlatformEntity,
                        sourceObjectID,
                        perceveidSeverity,
                        alarmText,
                        probableCause,
                        correctiveAction,
                        htimeStamp }
        STATUS  current
        DESCRIPTION
                "Timeout from stack on <string> request for <string> Id=<number>, error code <number>"
        ::= { openCallTraps 40300003 }

hHPOC-40300006  NOTIFICATION-TYPE
        OBJECTS {       sourcePlatformEntity,
                        sourceObjectID,
                        perceveidSeverity,
                        alarmText,
                        probableCause,
                        correctiveAction,
                        htimeStamp }
        STATUS  current
        DESCRIPTION
                "Required <string> Id=<number> not found in network configuration"
        ::= { openCallTraps 40300006 }

hHPOC-40300011  NOTIFICATION-TYPE
        OBJECTS {       sourcePlatformEntity,
                        sourceObjectID,
                        perceveidSeverity,
                        alarmText,
                        probableCause,
                        correctiveAction,
                        htimeStamp }
        STATUS  current
        DESCRIPTION
                "Error while accessing configuration file"
        ::= { openCallTraps 403000011 }

hHPOC-40300015  NOTIFICATION-TYPE
        OBJECTS {       sourcePlatformEntity,
                        sourceObjectID,
                        perceveidSeverity,
                        alarmText,
                        probableCause,
                        correctiveAction,
                        htimeStamp }
        STATUS  current
        DESCRIPTION
                "Missing or invalid Primary address in Static Configuration file"
        ::= { openCallTraps 403000015 }

hHPOC-40300016  NOTIFICATION-TYPE
        OBJECTS {       sourcePlatformEntity,
                        sourceObjectID,
                        perceveidSeverity,
                        alarmText,
                        probableCause,
                        correctiveAction,
                        htimeStamp }
        STATUS  current
        DESCRIPTION
                "Failed to retrieve statistics from M3UA stack"
        ::= { openCallTraps 403000016 }

hHPOC-40300017  NOTIFICATION-TYPE
        OBJECTS {       sourcePlatformEntity,
                        sourceObjectID,
                        perceveidSeverity,
                        alarmText,
                        probableCause,
                        correctiveAction,
                        htimeStamp }
        STATUS  current
        DESCRIPTION
                "Automatic loadconf failed on M3UA instance <number>, SHUTTING DOWN"
        ::= { openCallTraps 403000017 }


END
