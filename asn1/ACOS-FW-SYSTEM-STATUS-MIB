ACOS-FW-SYSTEM-STATUS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwSystemStatusModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwSystemStatusModule OID for ACOS"
				::=  {  acosSchema 486 }

systemStatus		 OBJECT IDENTIFIER ::= { fwSystemStatusModule 1}

systemStatusOperTable OBJECT-TYPE
	 SYNTAX SEQUENCE OF SystemStatusOperEntry
	 MAX-ACCESS not-accessible
	 STATUS current
	 DESCRIPTION
		 "Firewall system status from object 'fw.system-status'"
	::= {systemStatus 2}

systemStatusOperEntry OBJECT-TYPE
	SYNTAX SystemStatusOperEntry
	MAX-ACCESS not-accessible
	STATUS current
	DESCRIPTION
		"The systemStatusOper entry"
	INDEX {
		systemStatusOperSlotId
	}
	::= { systemStatusOperTable 1 }

SystemStatusOperEntry ::=
	SEQUENCE {
		systemStatusOperSlotId Integer32,
		systemStatusOperDataSessionsUsed	 Integer32,
		systemStatusOperDataSessionsFree	 Integer32,
		systemStatusOperSmpSessionsUsed	 Integer32,
		systemStatusOperSmpSessionsFree	 Integer32,
		systemStatusOperRadiusEntriesUsed	 Integer32,
		systemStatusOperRadiusEntriesFree	 Integer32
	}

systemStatusOperSlotId OBJECT-TYPE
	 SYNTAX Integer32
	 MAX-ACCESS read-only
	 STATUS current
	 DESCRIPTION
		 ""
	::= { systemStatusOperEntry 1 }

systemStatusOperDataSessionsUsed OBJECT-TYPE
	 SYNTAX Integer32
	 MAX-ACCESS read-only
	 STATUS current
	 DESCRIPTION
		 "data-sessions-used"
	::= { systemStatusOperEntry 2 }

systemStatusOperDataSessionsFree OBJECT-TYPE
	 SYNTAX Integer32
	 MAX-ACCESS read-only
	 STATUS current
	 DESCRIPTION
		 "data-sessions-free"
	::= { systemStatusOperEntry 3 }

systemStatusOperSmpSessionsUsed OBJECT-TYPE
	 SYNTAX Integer32
	 MAX-ACCESS read-only
	 STATUS current
	 DESCRIPTION
		 "smp-sessions-used"
	::= { systemStatusOperEntry 4 }

systemStatusOperSmpSessionsFree OBJECT-TYPE
	 SYNTAX Integer32
	 MAX-ACCESS read-only
	 STATUS current
	 DESCRIPTION
		 "smp-sessions-free"
	::= { systemStatusOperEntry 5 }

systemStatusOperRadiusEntriesUsed OBJECT-TYPE
	 SYNTAX Integer32
	 MAX-ACCESS read-only
	 STATUS current
	 DESCRIPTION
		 "radius-entries-used"
	::= { systemStatusOperEntry 6 }

systemStatusOperRadiusEntriesFree OBJECT-TYPE
	 SYNTAX Integer32
	 MAX-ACCESS read-only
	 STATUS current
	 DESCRIPTION
		 "radius-entries-free"
	::= { systemStatusOperEntry 7 }

END
