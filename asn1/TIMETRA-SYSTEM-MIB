TIMETRA-SYSTEM-MIB DEFINITIONS ::= BEGIN

IMPORTS
    smLaunchEntry, smLaunchError,
    smLaunchName, smLaunchOwner,
    smLaunchScriptName, smLaunchScriptOwner,
    smRunEntry, smRunIndex
                                                         FROM DISMAN-SCRIPT-MIB
    CounterBasedGauge64
                                                         FROM HCNUM-TC
    InetAddress, InetAddressIPv6,
    InetAddressPrefixLength,
    InetAddressType, InetPortNumber
                                                         FROM INET-ADDRESS-MIB
    snmpCommunityEntry
                                                         FROM SNMP-COMMUNITY-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DateAndTime, DisplayString, MacAddress,
    RowPointer, RowStatus,
    TEXTUAL-CONVENTION, TimeStamp,
    TruthValue
                                                         FROM SNMPv2-TC
    TmnxSlotNum, tmnxChassisBaseMacAddress,
    tmnxChassisIndex,
    tmnxChassisNotifyHwIndex,
    tmnxCpmCardNum, tmnxCpmCardSlotNum,
    tmnxHwClass, tmnxHwID
                                                         FROM TIMETRA-CHASSIS-MIB
    timetraSRMIBModules, tmnxSRConfs,
    tmnxSRNotifyPrefix, tmnxSRObjs
                                                         FROM TIMETRA-GLOBAL-MIB
    tmnxEhsHEntryMinDelay,
    tmnxEhsHEntryMinDelayInterval,
    tmnxEhsHEntryScriptPlcyName,
    tmnxEhsHEntryScriptPlcyOwner,
    tmnxEhsHandlerDescription,
    tmnxLogExecRollbackOpIndex,
    tmnxLogExecRollbackOpType
                                                         FROM TIMETRA-LOG-MIB
    IpAddressPrefixLength, TDSCPNameOrEmpty,
    TItemDescription, TLDisplayString,
    TLNamedItem, TLNamedItemOrEmpty,
    TNamedItem, TNamedItemOrEmpty,
    TTcpUdpPort, TmnxActionType,
    TmnxAdminState,
    TmnxAdminStateTruthValue, TmnxCliEngine,
    TmnxDisplayStringURL,
    TmnxEnabledDisabled,
    TmnxLongDisplayString, TmnxOperState,
    TmnxScriptAuthType, TmnxServId,
    TmnxUuid, TmnxVRtrID, TmnxVRtrIDOrZero
                                                         FROM TIMETRA-TC-MIB
    ;

timetraSysMIBModule              MODULE-IDENTITY
    LAST-UPDATED "201701010000Z"
    ORGANIZATION "Nokia"
    CONTACT-INFO
        "Nokia SROS Support
         Web: http://www.nokia.com"
    DESCRIPTION
        "This document is the System SNMP MIB module for the Nokia
         SROS device.  The System MIB module defines SNMP objects to
         manage and provision system features.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied `as is', and Nokia makes no warranty,
         either express or implied, as to the use, operation, condition, or
         performance of the Specification."

    REVISION    "201701010000Z"
    DESCRIPTION
        "Rev 15.0               1 Jan 2017 00:00
         15.0 release of the TIMETRA-SYSTEM-MIB."

    REVISION    "201601010000Z"
    DESCRIPTION
        "Rev 14.0               1 Jan 2016 00:00
         14.0 release of the TIMETRA-SYSTEM-MIB."

    REVISION    "201406010000Z"
    DESCRIPTION
        "Rev 13.0               01 Jun 2014 00:00
         13.0 release of the TIMETRA-SYSTEM-MIB."

    REVISION    "201401010000Z"
    DESCRIPTION
        "Rev 12.0               01 Jan 2014 00:00
         12.0 release of the TIMETRA-SYSTEM-MIB."

    REVISION    "201102010000Z"
    DESCRIPTION
        "Rev 9.0                01 Feb 2011 00:00
         9.0 release of the TIMETRA-SYSTEM-MIB."

    REVISION    "201001010000Z"
    DESCRIPTION
        "Rev 8.0                01 Jan 2010 00:00
         8.0 release of the TIMETRA-SYSTEM-MIB."

    REVISION    "200902280000Z"
    DESCRIPTION
        "Rev 7.0                28 Feb 2009 00:00
         7.0 release of the TIMETRA-SYSTEM-MIB."

    REVISION    "200801010000Z"
    DESCRIPTION
        "Rev 6.0                01 Jan 2008 00:00
         6.0 release of the TIMETRA-SYSTEM-MIB."

    REVISION    "200701010000Z"
    DESCRIPTION
        "Rev 5.0                01 Jan 2007 00:00
         5.0 release of the TIMETRA-SYSTEM-MIB."

    REVISION    "200603150000Z"
    DESCRIPTION
        "Rev 4.0                15 Mar 2006 00:00
         4.0 release of the TIMETRA-SYSTEM-MIB."

    REVISION    "200508310000Z"
    DESCRIPTION
        "Rev 3.0                31 Aug 2005 00:00
         3.0 release of the TIMETRA-SYSTEM-MIB."

    REVISION    "200501240000Z"
    DESCRIPTION
        "Rev 2.1                24 Jan 2005 00:00
         2.1 release of the TIMETRA-SYSTEM-MIB."

    REVISION    "200401150000Z"
    DESCRIPTION
        "Rev 2.0                15 Jan 2004 00:00
         2.0 release of the TIMETRA-SYSTEM-MIB."

    REVISION    "200308150000Z"
    DESCRIPTION
        "Rev 1.2                15 Aug 2003 00:00
         1.2 release of the TIMETRA-SYSTEM-MIB."

    REVISION    "200301200000Z"
    DESCRIPTION
        "Rev 1.0                20 Jan 2003 00:00
         1.0 Release of the TIMETRA-SYSTEM-MIB."

    REVISION    "200008140000Z"
    DESCRIPTION
        "Rev 0.1                14 Aug 2000 00:00
         First version of the TIMETRA-SYSTEM-MIB."

    ::= { timetraSRMIBModules 1 }

TmnxSsiSyncMode                  ::= TEXTUAL-CONVENTION
    STATUS      current
    DESCRIPTION
        "The value of TmnxSsiSyncMode specifies the type of synchronization
         operation to perform between the primary and secondary CPMs after a
         change has been made to the configuration files or the boot
         environment information contained in the boot options file (bof)."
    SYNTAX      INTEGER {
        none    (1),
        config  (2),
        bootEnv (3)
    }

TmnxSsiSyncRollbackMode          ::= TEXTUAL-CONVENTION
    STATUS      current
    DESCRIPTION
        "The value of TmnxSsiSyncRollbackMode specifies the type of
         synchronization operation to perform between the primary and secondary
         CPMs after a change has been made to the rollback files."
    SYNTAX      INTEGER {
        none           (1),
        rollbackSingle (2),
        rollbackAll    (3)
    }

TmnxSysLicenseApplication        ::= TEXTUAL-CONVENTION
    STATUS      current
    DESCRIPTION
        "The textual convention TmnxSysLicenseApplication represents an
         application in a virtual machine implementation that is subject to
         licensing.

         NAT - Network Address Translation
         WLAN-GW - Wireless Local Area Network Gateway
         LNS - L2TP Network Server
         Subscriber Management
         AA  - Application Assurance"
    SYNTAX      INTEGER {
        none    (0),
        nat     (1),
        wlanGw  (2),
        lns     (3),
        subMgmt (4),
        aa      (5),
        ipsec   (6)
    }

TmnxSysLicenseAppStatsType       ::= TEXTUAL-CONVENTION
    STATUS      current
    DESCRIPTION
        "The textual convention TmnxSysLicenseAppStatsType represents the type
         of statistics collected about an application in a virtual machine
         implementation subject to licensing."
    SYNTAX      INTEGER {
        none                (0),
        lsnSubscribers      (1),
        lsnBandwidth        (2),
        wlanGwUserEquipment (1000),
        wlanGwGtpBearers    (1001),
        lnsTunnels          (2000),
        lnsSessions         (2001),
        subscriberHosts     (3000),
        aaSubscribers       (4000),
        aaBandwidth         (4001),
        ipsecTunnels        (5000),
        ipsecTnlBandwidth   (5001),
        ipTunnels           (5002),
        ipTnlBandwidth      (5003)
    }

TmnxSysLicensingGroup            ::= TEXTUAL-CONVENTION
    STATUS      current
    DESCRIPTION
        "The textual convention TmnxSysLicensingGroup represents a grouping of
         licensed applications.

         system   - System Level Licenses
         services - Service Type Licenses
         nsp      - Network Management Licenses
         isa      - Integrated Services Licenses
         iom      - IOM Card Licenses
         mda      - MDA Licenses"
    SYNTAX      INTEGER {
        system   (0),
        services (1),
        nsp      (2),
        isa      (3),
        iom      (4),
        mda      (5)
    }

TmnxSysMonSampleTime             ::= TEXTUAL-CONVENTION
    STATUS      current
    DESCRIPTION
        "The value of TmnxSysMonSampleTime specifies the monitoring sample time
         (in terms of seconds) for a system object."
    SYNTAX      Unsigned32 (1 | 60 | 300)

TmnxSysMonUtilization            ::= TEXTUAL-CONVENTION
    STATUS      current
    DESCRIPTION
        "The value of TmnxSysMonUtilization specifies the utilization/idle
         percentage (in terms 100ths of a percent) for a given sample-time."
    SYNTAX      Gauge32 (0..10000)

TmnxSysMgmtIfDstoreLockState     ::= TEXTUAL-CONVENTION
    STATUS      current
    DESCRIPTION
        "The value of TmnxSysMgmtIfDstoreLockState specifies the datastore lock
         state."
    SYNTAX      INTEGER {
        locked   (1),
        unlocked (2)
    }

TmnxSysNeid                      ::= TEXTUAL-CONVENTION
    DISPLAY-HINT "1x:"
    STATUS      current
    DESCRIPTION
        "The textual convention TmnxSysNeid represents the  Network Element
         Identifier.

         The first 8 high-order bits indicate the subnet ID and the 16
         low-order bits indicate the basic ID."
    SYNTAX      OCTET STRING (SIZE (0|3))

TmnxConfigFileFormatType         ::= TEXTUAL-CONVENTION
    STATUS      current
    DESCRIPTION
        "The value of TmnxConfigFileFormatType specifies format of the
         configuration file."
    SYNTAX      INTEGER {
        classicCli (1),
        mdCli      (2)
    }

tmnxSysObjs                      OBJECT IDENTIFIER ::= { tmnxSRObjs 1 }

sysGenInfo                       OBJECT IDENTIFIER ::= { tmnxSysObjs 1 }

sgiCpuUsage                      OBJECT-TYPE
    SYNTAX      Unsigned32 (0..100)
    UNITS       "percent"
    MAX-ACCESS  read-only
    STATUS      current
    DESCRIPTION
        "The value of sgiCpuUsage indicates the current CPU utilization for the
         system."
    ::= { sysGenInfo 1 }

sgiMemoryUsed                    OBJECT-TYPE
    SYNTAX      Unsigned32
    UNITS       "bytes"
    MAX-ACCESS  read-only
    STATUS      current
    DESCRIPTION
        "The value of sgiMemoryUsed indicates the total pre-allocated pool
         memory currently in use on the system.

         If the value is greater than the maximum value reportable by this
         object then this object reports its maximum value (4,294,967,295) and
         sgiKbMemoryUsed must be used to determine the total pre-allocated pool
         memory."
    ::= { sysGenInfo 2 }

sgiMemoryAvailable               OBJECT-TYPE
    SYNTAX      Unsigned32
    UNITS       "bytes"
    MAX-ACCESS  read-only
    STATUS      current
    DESCRIPTION
        "The value of sgiMemoryAvailable indicates the amount of free memory in
         the overall system that is not allocated to memory pools, but is
         available in case a memory pool needs to grow.

         If the value is greater than the maximum value reportable by this
         object then this object reports its maximum value (4,294,967,295) and
         sgiKbMemoryAvailable must be used to determine the total free memory."
    ::= { sysGenInfo 3 }

sgiMemoryPoolAllocated           OBJECT-TYPE
    SYNTAX      Unsigned32
    UNITS       "bytes"
    MAX-ACCESS  read-only
    STATUS      current
    DESCRIPTION
        "The value of sgiMemoryPoolAllocated indicates the total memory
         currently allocated in memory-pools on the system.

         This memory may or may not be currently in use, but is pre-allocated
         should the software need to use it.

         If the value is greater than the maximum value reportable by this
         object then this object reports its maximum value (4,294,967,295) and
         sgiKbMemoryPoolAllocated must be used to determine the total memory
         allocated in memory-pools."
    ::= { sysGenInfo 4 }

sgiSwMajorVersion                OBJECT-TYPE
    SYNTAX      Unsigned32
    MAX-ACCESS  read-only
    STATUS      current
    DESCRIPTION
        "The value of sgiSwMajorVersion indicates the major version number of
         the software running on the active CPM card."
    ::= { sysGenInfo 5 }

sgiSwMinorVersion                OBJECT-TYPE
    SYNTAX      Unsigned32
    MAX-ACCESS  read-only
    STATUS      current
    DESCRIPTION
        "The value of sgiSwMinorVersion indicates the minor version number of
         the software running on the active CPM card."
    ::= { sysGenInfo 6 }

sgiSwVersionModifier             OBJECT-TYPE
    SYNTAX      OCTET STRING (SIZE (0..255))
    MAX-ACCESS  read-only
    STATUS      current
    DESCRIPTION
        "The value of sgiSwVersionModifier indicates additional information
         about the version of software running on the active CPM card."
    ::= { sysGenInfo 7 }

sgiSnmpInGetBulks                OBJECT-TYPE
    SYNTAX      Counter32
    MAX-ACCESS  read-only
    STATUS      current
    DESCRIPTION
        "The value of sgiSnmpInGetBulks indicates the total number of SNMP
         Get-Next PDUs which have been accepted and processed by the SNMP
         protocol entity."
    ::= { sysGenInfo 8 }

sgiKbMemoryUsed                  OBJECT-TYPE
    SYNTAX      Unsigned32
    UNITS       "kilobytes"
    MAX-ACCESS  read-only
    STATUS      current
    DESCRIPTION
        "The value of sgiKbMemoryUsed indicates the total pre-allocated pool
         memory, in kilobytes, currently in use on the system."
    ::= { sysGenInfo 9 }

sgiKbMemoryAvailable             OBJECT-TYPE
    SYNTAX      Unsigned32
    UNITS       "kilobytes"
    MAX-ACCESS  read-only
    STATUS      current
    DESCRIPTION
        "The value of sgiKbMemoryAvailable indicates the amount of free memory,
         in kilobytes, in the overall system that is not allocated to memory
         pools, but is available in case a memory pool needs to grow."
    ::= { sysGenInfo 10 }

sgiKbMemoryPoolAllocated         OBJECT-TYPE
    SYNTAX      Unsigned32
    UNITS       "kilobytes"
    MAX-ACCESS  read-only
    STATUS      current
    DESCRIPTION
        "The value of sgiKbMemoryPoolAllocated indicates the total memory, in
         kilobytes, currently allocated in memory-pools on the system.

         This memory may or may not be currently in use, but is pre-allocated
         should the software need to use it."
    ::= { sysGenInfo 11 }

tmnxSysCpuMonTable               OBJECT-TYPE
    SYNTAX      SEQUENCE OF TmnxSysCpuMonEntry
    MAX-ACCESS  not-accessible
    STATUS      current
    DESCRIPTION
        "tmnxSysCpuMonTable consists of the system level CPU monitoring
         statistics."
    ::= { sysGenInfo 12 }

tmnxSysCpuMonEntry               OBJECT-TYPE
    SYNTAX      TmnxSysCpuMonEntry
    MAX-ACCESS  not-accessible
    STATUS      current
    DESCRIPTION
        "tmnxSysCpuMonEntry contains the system level CPU monitoring statistics
         over a specified sample-time."
    INDEX       { tmnxSysCpuMonSampleTime }
    ::= { tmnxSysCpuMonTable 1 }

TmnxSysCpuMonEntry               ::= SEQUENCE
{
    tmnxSysCpuMonSampleTime          TmnxSysMonSampleTime,
    tmnxSysCpuMonCpuIdle             TmnxSysMonUtilization,
    tmnxSysCpuMonBusyCoreUtil        TmnxSysMonUtilization,
    tmnxSysCpuMonBusyGroupName       OCTET STRING,
    tmnxSysCpuMonBusyGroupUtil       TmnxSysMonUtilization
}

tmnxSysCpuMonSampleTime          OBJECT-TYPE
    SYNTAX      TmnxSysMonSampleTime
    MAX-ACCESS  not-accessible
    STATUS      current
    DESCRIPTION
        "The value of tmnxSysCpuMonSampleTime specifies the sample-time used to
         calculate the utilization results for the row."
    ::= { tmnxSysCpuMonEntry 1 }

tmnxSysCpuMonCpuIdle             OBJECT-TYPE
    SYNTAX      TmnxSysMonUtilization
    MAX-ACCESS  read-only
    STATUS      current
    DESCRIPTION
        "The value of tmnxSysCpuMonCpuIdle indicates the overall percentage of
         CPU idleness over the specified sample-time."
    ::= { tmnxSysCpuMonEntry 2 }

tmnxSysCpuMonBusyCoreUtil        OBJECT-TYPE
    SYNTAX      TmnxSysMonUtilization
    MAX-ACCESS  read-only
    STATUS      current
    DESCRIPTION
        "The value of tmnxSysCpuMonBusyCoreUtil indicates the utilization
         percentage of the busiest processor core over the specified
         sample-time. On single core CPUs, this is the overall system
         utilization percentage over the specified sample-time."
    ::= { tmnxSysCpuMonEntry 3 }

tmnxSysCpuMonBusyGroupName       OBJECT-TYPE
    SYNTAX      OCTET STRING (SIZE (0..64))
    MAX-ACCESS  read-only
    STATUS      current
    DESCRIPTION
        "The value of tmnxSysCpuMonBusyGroupName indicates the name of the
         group that is running at the highest capacity utilization.

         Capacity utilization is the CPU utilization relative to the maximum CPU
         resources available to that group.  A group is a set of related
         applications, services, tasks or protocol handlers that consumes some
         part of the system CPU resources.

         The capacity utilization of the busiest group is indicated by
         tmnxSysCpuMonBusyGroupUtil."
    ::= { tmnxSysCpuMonEntry 4 }

tmnxSysCpuMonBusyGroupUtil       OBJECT-TYPE
    SYNTAX      TmnxSysMonUtilization
    MAX-ACCESS  read-only
    STATUS      current
    DESCRIPTION
        "The value of tmnxSysCpuMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxSysCpuMonBusyGroupName."
    ::= { tmnxSysCpuMonEntry 5 }

sgiGroupingIDs                   OBJECT IDENTIFIER ::= { sysGenInfo 13 }

sgiSystemGroupID                 OBJECT-TYPE
    SYNTAX      Unsigned32
    MAX-ACCESS  read-write
    STATUS      current
    DESCRIPTION
        "The value of sgiSystemGroupID specifies a group this
         system belongs to.  It is used by NMS applications to identify
         a set of systems for which the NMS wants to perform common
         tasks such as correlating alarms."
    DEFVAL      { 0 }
    ::= { sgiGroupingIDs 1 }

sgiSystemSubGroupID              OBJECT-TYPE
    SYNTAX      Unsigned32
    MAX-ACCESS  read-write
    STATUS      current
    DESCRIPTION
        "The value of sgiSystemSubGroupID specifies a sub-group within the
         sgiSystemGroupID group that this system belongs to. It is used by NMS
         applications to identify a subset of systems in the sgiSystemGroupID
         for which the NMS wants to perform common tasks such as correlating
         alarms."
    DEFVAL      { 0 }
    ::= { sgiGroupingIDs 2 }

sgiSnmpFailedSets                OBJECT-TYPE
    SYNTAX      Counter32
    MAX-ACCESS  read-only
    STATUS      current
    DESCRIPTION
        "The value of sgiSnmpFailedSets indicates the total number of SNMP set
         requests which have failed which failed due to another management
         interface (such as NETCONF) exclusively reserving the system
         resources."
    ::= { sysGenInfo 14 }

sysTimeInfo                      OBJECT IDENTIFIER ::= { tmnxSysObjs 2 }

stiDateAndTime                   OBJECT-TYPE
    SYNTAX      DateAndTime (SIZE (11))
    MAX-ACCESS  read-write
    STATUS      current
    DESCRIPTION
        "The current date and time (in UTC) maintained in this managed system."
    ::= { sysTimeInfo 1 }

stiActiveZone                    OBJECT-TYPE
    SYNTAX      DisplayString (SIZE (0..5))
    MAX-ACCESS  read-write
    STATUS      current
    DESCRIPTION
        "The time zone that is active in this managed system."
    DEFVAL      { "UTC" }
    ::= { sysTimeInfo 2 }

stiHoursOffset                   OBJECT-TYPE
    SYNTAX      Integer32 (-11..12)
    UNITS       "hours"
    MAX-ACCESS  read-write
    STATUS      current
    DESCRIPTION
        "The number of hours by which the time zone represented by
         stiActiveZone offsets from UTC (Coordinated Universal Time)."
    DEFVAL      { 0 }
    ::= { sysTimeInfo 3 }

stiMinutesOffset                 OBJECT-TYPE
    SYNTAX      Integer32 (0..59)
    UNITS       "minutes"
    MAX-ACCESS  read-write
    STATUS      current
    DESCRIPTION
        "The number of minutes (in addition to the hours offset defined by
         stiHoursOffset) by which the time zone represented by stiActiveZone
         offsets from UTC (Coordinated Universal Time). This value is used when
         the time zone does not have an offset that is an integral number of
         hours.

         If the hour offset is defined as '12', the minute offset cannot be
         anything other than zero."
    DEFVAL      { 0 }
    ::= { sysTimeInfo 4 }

stiZoneType                      OBJECT-TYPE
    SYNTAX      INTEGER {
        system (1),
        user   (2)
    }
    MAX-ACCESS  read-only
    STATUS      current
    DESCRIPTION
        "stiZoneType will be 'system' if the zone defined by stiActiveZone is a
         system-defined zone. It will be 'user' if the zone has been defined by
         the user."
    ::= { sysTimeInfo 5 }

stiSummerZoneTable               OBJECT-TYPE
    SYNTAX      SEQUENCE OF StiSummerZoneEntry
    MAX-ACCESS  not-accessible
    STATUS      current
    DESCRIPTION
        "The stiSummerZoneTable has an entry for each summer time zone
         information."
    ::= { sysTimeInfo 6 }

stiSummerZoneEntry               OBJECT-TYPE
    SYNTAX      StiSummerZoneEntry
    MAX-ACCESS  not-accessible
    STATUS      current
    DESCRIPTION
        "Each row entry contains information about a summer time zone. This
         information can be used to either override the default summer (or
         daylight savings) time information for a system-defined time zone or
         define the summer time information for a user-defined time zone."
    INDEX       { IMPLIED stiSummerZoneName }
    ::= { stiSummerZoneTable 1 }

StiSummerZoneEntry               ::= SEQUENCE
{
    stiSummerZoneName                OCTET STRING,
    stiSummerZoneRowStatus           RowStatus,
    stiSummerZoneStartDate           DateAndTime,
    stiSummerZoneEndDate             DateAndTime,
    stiSummerZoneOffset              Unsigned32,
    stiSummerZoneStartDay            INTEGER,
    stiSummerZoneStartWeek           INTEGER,
    stiSummerZoneStartMonth          INTEGER,
    stiSummerZoneStartHour           Unsigned32,
    stiSummerZoneStartMinute         Unsigned32,
    stiSummerZoneEndDay              INTEGER,
    stiSummerZoneEndWeek             INTEGER,
    stiSummerZoneEndMonth            INTEGER,
    stiSummerZoneEndHour             Unsigned32,
    stiSummerZoneEndMinute           Unsigned32
}

stiSummerZoneName                OBJECT-TYPE
    SYNTAX      OCTET STRING (SIZE (1..5))
    MAX-ACCESS  not-accessible
    STATUS      current
    DESCRIPTION
        "The name for a summer time zone. This name must be unique amongst the
         table entries. The summer time zone name should comprise only of
         uppercase letters A-Z and digits 0-9."
    ::= { stiSummerZoneEntry 1 }

stiSummerZoneRowStatus           OBJECT-TYPE
    SYNTAX      RowStatus
    MAX-ACCESS  read-create
    STATUS      current
    DESCRIPTION
        "The row status used to create and delete rows in this table."
    ::= { stiSummerZoneEntry 2 }

stiSummerZoneStartDate           OBJECT-TYPE
    SYNTAX      DateAndTime (SIZE (8))
    MAX-ACCESS  read-create
    STATUS      obsolete
    DESCRIPTION
        "The starting date and time when the summer time will take effect.

         This object was made obsolete in the 4.0 release."
    ::= { stiSummerZoneEntry 3 }

stiSummerZoneEndDate             OBJECT-TYPE
    SYNTAX      DateAndTime (SIZE (8))
    MAX-ACCESS  read-create
    STATUS      obsolete
    DESCRIPTION
        "The date and time when summer time will end.

         This object was made obsolete in the 4.0 release."
    ::= { stiSummerZoneEntry 4 }

stiSummerZoneOffset              OBJECT-TYPE
    SYNTAX      Unsigned32 (0..60)
    UNITS       "minutes"
    MAX-ACCESS  read-create
    STATUS      current
    DESCRIPTION
        "The number of minutes that will be added to the time when summer time
         takes effect. The same number of minutes will be subtracted from the
         time when the summer time ends."
    DEFVAL      { 60 }
    ::= { stiSummerZoneEntry 5 }

stiSummerZoneStartDay            OBJECT-TYPE
    SYNTAX      INTEGER {
        sunday    (0),
        monday    (1),
        tuesday   (2),
        wednesday (3),
        thursday  (4),
        friday    (5),
        saturday  (6)
    }
    MAX-ACCESS  read-create
    STATUS      current
    DESCRIPTION
        "The starting day of the week when the summer time will take effect."
    DEFVAL      { sunday }
    ::= { stiSummerZoneEntry 6 }

stiSummerZoneStartWeek           OBJECT-TYPE
    SYNTAX      INTEGER {
        first  (0),
        second (1),
        third  (2),
        fourth (3),
        last   (4)
    }
    MAX-ACCESS  read-create
    STATUS      current
    DESCRIPTION
        "The starting week of the month when the summer time will take effect."
    DEFVAL      { first }
    ::= { stiSummerZoneEntry 7 }

stiSummerZoneStartMonth          OBJECT-TYPE
    SYNTAX      INTEGER {
        january   (0),
        february  (1),
        march     (2),
        april     (3),
        may       (4),
        june      (5),
        july      (6),
        august    (7),
        september (8),
        october   (9),
        november  (10),
        december  (11)
    }
    MAX-ACCESS  read-create
    STATUS      current
    DESCRIPTION
        "The starting month of the year when the summer time will take effect."
    DEFVAL      { january }
    ::= { stiSummerZoneEntry 8 }

stiSummerZoneStartHour           OBJECT-TYPE
    SYNTAX      Unsigned32 (0..23)
    UNITS       "hours"
    MAX-ACCESS  read-create
    STATUS      current
    DESCRIPTION
        "The hour at which the summer time will take effect."
    DEFVAL      { 0 }
    ::= { stiSummerZoneEntry 9 }

stiSummerZoneStartMinute         OBJECT-TYPE
    SYNTAX      Unsigned32 (0..59)
    UNITS       "minutes"
    MAX-ACCESS  read-create
    STATUS      current
    DESCRIPTION
        "The number of minutes after the hours defined by
         stiSummerZoneStartHour when the summer time will take effect."
    DEFVAL      { 0 }
    ::= { stiSummerZoneEntry 10 }

stiSummerZoneEndDay              OBJECT-TYPE
    SYNTAX      INTEGER {
        sunday    (0),
        monday    (1),
        tuesday   (2),
        wednesday (3),
        thursday  (4),
        friday    (5),
        saturday  (6)
    }
    MAX-ACCESS  read-create
    STATUS      current
    DESCRIPTION
        "The day of the week when the summer time setting will end."
    DEFVAL      { sunday }
    ::= { stiSummerZoneEntry 11 }

stiSummerZoneEndWeek             OBJECT-TYPE
    SYNTAX      INTEGER {
        first  (0),
        second (1),
        third  (2),
        fourth (3),
        last   (4)
    }
    MAX-ACCESS  read-create
    STATUS      current
    DESCRIPTION
        "The week of the month when the summer time setting will end."
    DEFVAL      { first }
    ::= { stiSummerZoneEntry 12 }

stiSummerZoneEndMonth            OBJECT-TYPE
    SYNTAX      INTEGER {
        january   (0),
        february  (1),
        march     (2),
        april     (3),
        may       (4),
        june      (5),
        july      (6),
        august    (7),
        september (8),
        october   (9),
        november  (10),
        december  (11)
    }
    MAX-ACCESS  read-create
    STATUS      current
    DESCRIPTION
        "The month of the year when the summer time setting will end."
    DEFVAL      { january }
    ::= { stiSummerZoneEntry 13 }

stiSummerZoneEndHour             OBJECT-TYPE
    SYNTAX      Unsigned32 (0..23)
    UNITS       "hours"
    MAX-ACCESS  read-create
    STATUS      current
    DESCRIPTION
        "The hour at which the summer time will stop taking effect."
    DEFVAL      { 0 }
    ::= { stiSummerZoneEntry 14 }

stiSummerZoneEndMinute           OBJECT-TYPE
    SYNTAX      Unsigned32 (0..59)
    UNITS       "minutes"
    MAX-ACCESS  read-create
    STATUS      current
    DESCRIPTION
        "The number of minutes after the hours defined by stiSummerZoneEndHour
         when the summer time will stop taking effect."
    DEFVAL      { 0 }
    ::= { stiSummerZoneEntry 15 }

stiPreferLocalTime               OBJECT-TYPE
    SYNTAX      TruthValue
    MAX-ACCESS  read-write
    STATUS      current
    DESCRIPTION
        "The value of stiPreferLocalTime specifies the preference for the use
         of local or UTC time in the system for objects such as log file names,
         created/completed times reported in log files, rollback times
         displayed in show routines etc. Note that the time format for
         timestamps on log events themselves is controlled on a per log basis
         and not via prefer-local-time.

         A value of false(2) means use UTC time; true(1) means use the local
         system time, configured through 'configure system time' command"
    DEFVAL      { false }
    ::= { sysTimeInfo 7 }

sysSntpInfo                      OBJECT IDENTIFIER ::= { tmnxSysObjs 3 }

sntpState                        OBJECT-TYPE
    SYNTAX      INTEGER {
        unicast   (1),
        broadcast (2)
    }
    MAX-ACCESS  read-write
    STATUS      current
    DESCRIPTION
        "The mode for Simple Network Time Protocol (SNTP). 'Unicast' indicates
         that broadcast client is disabled. A value of 'broadcast' indicates
         that SNTP is listening to SNTP/NTP broadcast messages on interfaces
         with broadcast client enabled."
    DEFVAL      { unicast }
    ::= { sysSntpInfo 1 }

sntpServerTable                  OBJECT-TYPE
    SYNTAX      SEQUENCE OF SntpServerEntry
    MAX-ACCESS  not-accessible
    STATUS      current
    DESCRIPTION
        "The sntpServerEntry has an entry for each SNTP server for SNTP unicast
         client mode. SNTP can only receive the time from one of these SNTP
         servers. The table can have up to a maximum of 3 entries."
    ::= { sysSntpInfo 2 }

sntpServerEntry                  OBJECT-TYPE
    SYNTAX      SntpServerEntry
    MAX-ACCESS  not-accessible
    STATUS      current
    DESCRIPTION
        "Each row entry contains information about an SNTP server."
    INDEX       { sntpServerAddress }
    ::= { sntpServerTable 1 }

SntpServerEntry                  ::= SEQUENCE
{
    sntpServerAddress                IpAddress,
    sntpServerRowStatus              RowStatus,
    sntpServerVersion                Integer32,
    sntpServerPreference             INTEGER,
    sntpServerInterval               Unsigned32
}

sntpServerAddress                OBJECT-TYPE
    SYNTAX      IpAddress
    MAX-ACCESS  not-accessible
    STATUS      current
    DESCRIPTION
        "The IP address of the SNTP server."
    ::= { sntpServerEntry 1 }

sntpServerRowStatus              OBJECT-TYPE
    SYNTAX      RowStatus
    MAX-ACCESS  read-create
    STATUS      current
    DESCRIPTION
        "The row status used to create and delete rows in this table."
    ::= { sntpServerEntry 2 }

sntpServerVersion                OBJECT-TYPE
    SYNTAX      Integer32 (1..3)
    MAX-ACCESS  read-create
    STATUS      current
    DESCRIPTION
        "The SNTP Version supported by this server."
    DEFVAL      { 3 }
    ::= { sntpServerEntry 3 }

sntpServerPreference             OBJECT-TYPE
    SYNTAX      INTEGER {
        normal    (1),
        preferred (2)
    }
    MAX-ACCESS  read-create
    STATUS      current
    DESCRIPTION
        "The preference value for this SNTP server. When more then one
         time-server is configured it may be desirable that one server have
         preference over others. The value of sntpServerPreference for that
         server will be set to preferred(2). Only one server in the table can
         be a preferred server"
    DEFVAL      { normal }
    ::= { sntpServerEntry 4 }

sntpServerInterval               OBJECT-TYPE
    SYNTAX      Unsigned32 (64..1024)
    UNITS       "seconds"
    MAX-ACCESS  read-create
    STATUS      current
    DESCRIPTION
        "The frequency at which this server is queried."
    DEFVAL      { 64 }
    ::= { sntpServerEntry 5 }

sntpAdminState                   OBJECT-TYPE
    SYNTAX      INTEGER {
        noop         (1),
        inService    (2),
        outOfService (3)
    }
    MAX-ACCESS  read-write
    STATUS      current
    DESCRIPTION
        "The desired administrative state for SNTP."
    DEFVAL      { outOfService }
    ::= { sysSntpInfo 3 }

sntpOperStatus                   OBJECT-TYPE
    SYNTAX      TmnxOperState
    MAX-ACCESS  read-only
    STATUS      current
    DESCRIPTION
        "The value of sntpOperStatus indicates the current operational status
         of SNTP."
    ::= { sysSntpInfo 4 }

sysSyncInfo                      OBJECT IDENTIFIER ::= { tmnxSysObjs 4 }

ssiSaveConfig                    OBJECT-TYPE
    SYNTAX      TmnxActionType
    MAX-ACCESS  read-write
    STATUS      current
    DESCRIPTION
        "Setting this action variable to 'doAction' causes the current
         running configuration information to be saved to the location
         specified by ssiSaveConfigDest.  If no location is specified
         by ssiSaveConfigDest, the primary configuration file pointed to
         in the boot options file (bof) will be backed up and a new
         primary configuration file will be created with the current
         running configuration information.

         If ssiSaveConfigDetail has a value of 'true', default configuration
         values will be included in the saved configuration information.

         A corresponding persistent SNMP index file is created regardless of
         the setting of the persistence switch in the bof."
    DEFVAL      { notApplicable }
    ::= { sysSyncInfo 15 }

ssiSyncMode                      OBJECT-TYPE
    SYNTAX      TmnxSsiSyncMode
    MAX-ACCESS  read-write
    STATUS      current
    DESCRIPTION
        "The value of ssiSyncMode specifies the type of synchronization
         operation to perform between the primary and secondary CPMs after a
         change has been made to the configuration files or the boot
         environment information contained in the boot options file (bof)."
    DEFVAL      { none }
    ::= { sysSyncInfo 16 }

ssiSyncForce                     OBJECT-TYPE
    SYNTAX      TmnxSsiSyncMode
    MAX-ACCESS  read-write
    STATUS      current
    DESCRIPTION
        "The value of ssiSyncForce specifies the type of synchronization
         operation to perform when an SNMP set is made to this object. 'config'
         synchronizes only configuration files. 'bootEnv' synchronizes all
         files required to boot the system.

         The result of a read operation on this object is always 'none'."
    DEFVAL      { none }
    ::= { sysSyncInfo 17 }

ssiSyncStatus                    OBJECT-TYPE
    SYNTAX      INTEGER {
        unknown           (0),
        configOnly        (1),
        bootEnv           (2),
        configFail        (3),
        bootEnvFail       (4),
        configInProgress  (5),
        bootEnvInProgress (6)
    }
    MAX-ACCESS  read-only
    STATUS      current
    DESCRIPTION
        "The value of ssiSyncStatus indicates the results of the last
         synchronization operation between the primary and secondary CPMs."
    ::= { sysSyncInfo 18 }

ssiSyncConfigLastTime            OBJECT-TYPE
    SYNTAX      TimeStamp
    MAX-ACCESS  read-only
    STATUS      current
    DESCRIPTION
        "The value of ssiSyncConfigLastTime is the timestamp of the last
         successful synchronization of the configuration files."
    ::= { sysSyncInfo 19 }

ssiSyncBootEnvLastTime           OBJECT-TYPE
    SYNTAX      TimeStamp
    MAX-ACCESS  read-only
    STATUS      current
    DESCRIPTION
        "The value of ssiSyncBootEnvLastTime is the timestamp of the last
         successful synchronization of the boot environment files."
    ::= { sysSyncInfo 20 }

ssiConfigMaxBackupRevisions      OBJECT-TYPE
    SYNTAX      Unsigned32 (1..200)
    MAX-ACCESS  read-write
    STATUS      current
    DESCRIPTION
        "The value of ssiConfigMaxBackupRevisions is the maximum number of
         backup revisions maintained for a configuration file. This value also
         applies to the number of revisions maintained for the BOF file."
    DEFVAL      { 5 }
    ::= { sysSyncInfo 21 }

ssiSaveConfigResult              OBJECT-TYPE
    SYNTAX      INTEGER {
        none       (1),
        inProgress (2),
        success    (3),
        failed     (4)
    }
    MAX-ACCESS  read-only
    STATUS      current
    DESCRIPTION
        "The value of ssiSaveConfigResult represents the result of the
         last ssiSaveConfig action.
         none(1)            None of the following apply
         inProgress(2)      The action is still in progress
         success(3)         The action completed successfully
         failed(4)          The action failed"
    ::= { sysSyncInfo 22 }

ssiSaveBof                       OBJECT-TYPE
    SYNTAX      TmnxActionType
    MAX-ACCESS  read-write
    STATUS      current
    DESCRIPTION
        "Setting ssiSaveBof action variable to 'doAction' causes the existing
         BOF to be backed up and a new BOF file to be created with the current
         boot options information."
    DEFVAL      { notApplicable }
    ::= { sysSyncInfo 23 }

ssiSaveBofResult                 OBJECT-TYPE
    SYNTAX      INTEGER {
        none       (1),
        inProgress (2),
        success    (3),
        failed     (4)
    }
    MAX-ACCESS  read-only
    STATUS      current
    DESCRIPTION
        "The value of ssiSaveBofResult represents the result of the
         last ssiSaveBof action.
         none(1)            None of the following apply
         inProgress(2)      The action is still in progress
         success(3)         The action completed successfully
         failed(4)          The action failed"
    ::= { sysSyncInfo 24 }

ssiSaveConfigDest                OBJECT-TYPE
    SYNTAX      TmnxDisplayStringURL
    MAX-ACCESS  read-write
    STATUS      current
    DESCRIPTION
        "The value of ssiSaveConfigDest specifies the destination filepath
         or file-URL where the current running configuration information
         will be saved when ssiSaveConfig is set to 'doAction'.  If
         ssiSaveConfigDest is set to the empty string, ''H, the primary
         configuration file pointed to in the boot options file (bof) will
         be backed up and a new primary configuration file will be created
         with the current running configuration information.

         A corresponding persistent SNMP index file is created regardless of
         the setting of the persistence switch in the bof."
    DEFVAL      { ''H }
    ::= { sysSyncInfo 25 }

ssiSaveConfigDetail              OBJECT-TYPE
    SYNTAX      TruthValue
    MAX-ACCESS  read-write
    STATUS      current
    DESCRIPTION
        "When ssiSaveConfigDetail has a value of 'true', the default
         configuration values will also be included in the current running
         configuration information that will be saved when ssiSaveConfig is set
         to 'doAction'.

         When ssiSaveConfigDetail has a value of 'false', only non-default
         configuration values are saved. "
    DEFVAL      { false }
    ::= { sysSyncInfo 26 }

ssiRedFailoverTime               OBJECT-TYPE
    SYNTAX      TimeStamp
    MAX-ACCESS  read-only
    STATUS      current
    DESCRIPTION
        "The value of ssiRedFailoverTime is the timestamp when the last
         redundancy failover occurred causing a switchover from active
         to standby CPM.  If there is no redundant CPM card in this system
         or no failover has occurred since the system last booted,
         ssiRedFailoverTime will always return 0."
    ::= { sysSyncInfo 27 }

ssiRedFailoverReason             OBJECT-TYPE
    SYNTAX      DisplayString (SIZE (0..80))
    MAX-ACCESS  read-only
    STATUS      current
    DESCRIPTION
        "The value of ssiRedFailoverReason is a text string giving an
         explanation of the cause of the last redundancy failover. If no
         failover has occurred, the empty string, ''H, will be returned."
    ::= { sysSyncInfo 28 }

ssiSyncRollbackLastTime          OBJECT-TYPE
    SYNTAX      TimeStamp
    MAX-ACCESS  read-only
    STATUS      current
    DESCRIPTION
        "The value of ssiSyncRollbackLastTime is the timestamp of the last
         successful synchronization of the rollback files."
    ::= { sysSyncInfo 29 }

ssiSyncRollbackMode              OBJECT-TYPE
    SYNTAX      TmnxSsiSyncRollbackMode
    MAX-ACCESS  read-write
    STATUS      current
    DESCRIPTION
        "The value of ssiSyncRollbackMode specifies the type of synchronization
         operation to perform between the primary and secondary CPMs after a
         change has been made to the rollback files."
    DEFVAL      { none }
    ::= { sysSyncInfo 30 }

ssiSyncRollbackForce             OBJECT-TYPE
    SYNTAX      TmnxSsiSyncRollbackMode
    MAX-ACCESS  read-write
    STATUS      current
    DESCRIPTION
        "The value of ssiSyncRollbackForce specifies the type of synchronization
         operation to perform when an SNMP set is made to this object.
         'rollbackSingle' synchronizes only the rollback file that recently
          changed.
         'rollbackAll' synchronizes all rollback files.

         The result of a read operation on this object is always 'none'."
    DEFVAL      { none }
    ::= { sysSyncInfo 31 }

ssiSyncRollbackStatus            OBJECT-TYPE
    SYNTAX      INTEGER {
        unknown            (0),
        rollbackFail       (1),
        rollbackInProgress (2),
        rollbackSuccess    (3)
    }
    MAX-ACCESS  read-only
    STATUS      current
    DESCRIPTION
        "The value of ssiSyncRollbackStatus indicates the results of the last
         rollback synchronization operation between the primary and secondary
         CPMs."
    ::= { sysSyncInfo 32 }

ssiSyncCertLastTime              OBJECT-TYPE
    SYNTAX      TimeStamp
    MAX-ACCESS  read-only
    STATUS      current
    DESCRIPTION
        "The value of ssiSyncCertLastTime is the timestamp of the last
         successful synchronization of the certificate files."
    ::= { sysSyncInfo 33 }

ssiSyncCertMode                  OBJECT-TYPE
    SYNTAX      TruthValue
    MAX-ACCESS  read-write
    STATUS      current
    DESCRIPTION
        "The value of ssiSyncCertMode specifies whether to synchronize
         certificate files between the primary and secondary CPMs."
    DEFVAL      { true }
    ::= { sysSyncInfo 34 }

ssiSyncCertForce                 OBJECT-TYPE
    SYNTAX      TmnxActionType
    MAX-ACCESS  read-write
    STATUS      current
    DESCRIPTION
        "The value of ssiSyncCertForce specifies to perform action to
         synchronize certificate files between the primary and secondary CPMs
         when an SNMP set is made to this object.

         The value of ssiSyncCertForce will always be returned as
         'notApplicable'."
    DEFVAL      { notApplicable }
    ::= { sysSyncInfo 35 }

ssiSyncCertStatus                OBJECT-TYPE
    SYNTAX      INTEGER {
        unknown    (0),
        fail       (1),
        inProgress (2),
        success    (3)
    }
    MAX-ACCESS  read-only
    STATUS      current
    DESCRIPTION
        "The value of ssiSyncCertStatus indicates the results of the last
         certificate synchronization operation between the primary and
         secondary CPMs."
    ::= { sysSyncInfo 36 }

sysBootInfo                      OBJECT IDENTIFIER ::= { tmnxSysObjs 5 }

sbiConfigStatus                  OBJECT-TYPE
    SYNTAX      INTEGER {
        configRead        (1),
        configOK          (2),
        defaultBooted     (3),
        bootConfigFailed  (4),
        bootRestoreFailed (5),
        auto-provisioning (6)
    }
    MAX-ACCESS  read-only
    STATUS      current
    DESCRIPTION
        "The value of sbiConfigStatus indicates the result of the
         last attempt to execute the configuration file upon reboot
         of the system.
            configRead (1) - The configuration file is being read.
            configOK (2) - The configuration file was successfully
                    executed.
            defaultBooted (3) - There was no configuration file and
                    the system booted using a minimal
                    default configuration.
            bootConfigFailed (4) - An error occurred while the
                    configuration file was being executed.
                    The system configuration is incomplete.
            bootRestoreFailed (5) - An error occurred while the
                    restoration was being performed. The system
                    configuration is incomplete.
            auto-provisioning (6) - Auto-Boot feature running to
                    automatically provision and retrieve configuration
                    from network. Execution of boot configuration file
                    skipped."
    ::= { sysBootInfo 1 }

sbiPersistStatus                 OBJECT-TYPE
    SYNTAX      INTEGER {
        persistOK           (1),
        noPersistFile       (2),
        persistMismatch     (3),
        persistIndexFailure (4),
        persistDisabled     (5),
        persistInvalid      (6),
        persistBoot         (7),
        persistInit         (8),
        persistInProgress   (9)
    }
    MAX-ACCESS  read-only
    STATUS      current
    DESCRIPTION
        "The value of sbiPersistStatus indicates the state of the
         rebuild of the SNMP persistent index database upon reboot of the
         system.
            persistOK (1) - The persistent index database was
                successfully created.  Persistent SNMP managed
                objects were recreated with the same SNMP
                indexes they had prior to the system reboot.
            noPersistFile (2) - There was no persistent index file with
                the same pathname as the configuration file.
            persistMismatch (3) -The headers in the persistent index
                file and the configuration file with the same name
                do not match.
            persistIndexFailure (4) - An error occurred while creating
                the persistent index database.
            persistDisabled (5) - The system was administratively
                reconfigured without maintaining persistent SNMP index
                values because sbiPersistIndex has a value of 'false'.
            persistInvalid (6) - Persistent index database was not
                                 initialized.
            persistBoot(7) - The persistent index database was in the
                             pre-initial bootup state.
            persistInit(8) - The persistent index database is initializing.
            persistInProgress(9) - The initial bootup file is loading, using the
                                   persist index database. Once complete, the
                                   persist state will go to 'persistOk (1)' if
                                   successful.

         If sbiConfigStatus has a value of 'configOK' and
         sbiPersistStatus has any value other than 'persistOK', the
         system was reconfigured without maintaining persistent SNMP index
         values.  Unless sbiPersistIndex has a value of 'false',
         sbiSnmpdOperStatus returns 'disabled' and the SNMP daemon will not
         receive SNMP requests until sbiSnmpdAdminStatus variable has
         been set to 'inService'."
    ::= { sysBootInfo 2 }

sbiPersistIndex                  OBJECT-TYPE
    SYNTAX      TruthValue
    MAX-ACCESS  read-only
    STATUS      current
    DESCRIPTION
        "When sbiPersistIndex has a value of 'true', the SNMP persistent index
         database was rebuilt when the system was rebooted.  If there was an
         error during the processing of the configuration file the system may
         have been reconfigured without persistent SNMP indexes and the SNMP
         daemon will be suspended until it is manually enabled by setting
         sbiSnmpdAdminStatus to 'inService.  When sbiPersistIndex has a
         value of 'false' the system was reconfigured without maintaining
         persistent SNMP index values and the SNMP daemon was enabled."
    ::= { sysBootInfo 3 }

sbiSnmpdAdminStatus              OBJECT-TYPE
    SYNTAX      TmnxAdminState
    MAX-ACCESS  read-write
    STATUS      current
    DESCRIPTION
        "The value of sbiSnmpdAdminStatus is the desired administrative state
         for the SNMP daemon.  When sbiSnmpdAdminStatus is set to 'inService'
         the SNMP daemon will begin receiving SNMP requests from external
         SNMP managers.  When sbiSnmpdAdminStatus is set to 'outOfService'
         the SNMP daemon is suspended and will no longer receive SNMP requests
         from external SNMP managers."
    DEFVAL      { inService }
    ::= { sysBootInfo 4 }

sbiSnmpdOperStatus               OBJECT-TYPE
    SYNTAX      TmnxOperState
    MAX-ACCESS  read-only
    STATUS      current
    DESCRIPTION
        "When sbiSnmpdOperStatus has a value of 'inService', the SNMP daemon
         will receive SNMP requests from external SNMP managers.  When
         sbiSnmpdOperStatus has a value of 'outOfService', the SNMP daemon is
         suspended and will not receive SNMP requests from external SNMP
         managers."
    ::= { sysBootInfo 5 }

sbiSnmpdMaxPktSize               OBJECT-TYPE
    SYNTAX      Integer32 (484..9216)
    MAX-ACCESS  read-write
    STATUS      current
    DESCRIPTION
        "The value of sbiSnmpdMaxPktSize specifies the maximum length in octets
         of an SNMP message which the SNMP daemon can send or receive and
         process."
    DEFVAL      { 1500 }
    ::= { sysBootInfo 6 }

sbiSnmpdPortNum                  OBJECT-TYPE
    SYNTAX      TTcpUdpPort
    MAX-ACCESS  read-write
    STATUS      current
    DESCRIPTION
        "The value of sbiSnmpdPortNum specifies the UDP port to send and
         receive SNMP messages."
    DEFVAL      { 161 }
    ::= { sysBootInfo 7 }

sbiBootConfigOKScript            OBJECT-TYPE
    SYNTAX      DisplayString
    MAX-ACCESS  read-write
    STATUS      current
    DESCRIPTION
        "The value of sbiBootConfigOKScript specifies the location and name of
         the CLI script file executed following successful completion
         of the boot-up configuration file execution. I.e. sbiPersistStatus
         has a value of 'configOK'.  When this object has the empty string
         value, ''H, no CLI script file is executed."
    DEFVAL      { ''H }
    ::= { sysBootInfo 8 }

sbiConfigOKScriptStatus          OBJECT-TYPE
    SYNTAX      INTEGER {
        notRun  (0),
        success (1),
        fail    (2)
    }
    MAX-ACCESS  read-only
    STATUS      current
    DESCRIPTION
        "The value of sbiConfigOKScriptStatus indicates the results of
         executing the CLI script file specified in sbiBootConfigOKScript."
    ::= { sysBootInfo 9 }

sbiBootConfigFailScript          OBJECT-TYPE
    SYNTAX      DisplayString
    MAX-ACCESS  read-write
    STATUS      current
    DESCRIPTION
        "The value of sbiBootConfigFailScript specifies the location and
         name of the CLI script file executed following failure of the
         boot-up configuration file execution. I.e. sbiPersistStatus
         has a value other than 'configOK'.  When this object has the empty
         string value, ''H, no CLI script file is executed."
    DEFVAL      { ''H }
    ::= { sysBootInfo 10 }

sbiConfigFailScriptStatus        OBJECT-TYPE
    SYNTAX      INTEGER {
        notRun  (0),
        success (1),
        fail    (2)
    }
    MAX-ACCESS  read-only
    STATUS      current
    DESCRIPTION
        "The value of sbiConfigFailScriptStatus indicates the results of
         executing the CLI script file specified in sbiBootConfigFailScript."
    ::= { sysBootInfo 11 }

sbiRedSwitchoverScript           OBJECT-TYPE
    SYNTAX      DisplayString
    MAX-ACCESS  read-write
    STATUS      current
    DESCRIPTION
        "The value of sbiRedSwitchoverScript specifies the location and name of
         the CLI script file executed following a redundancy switchover from
         the previously active CPM card. A switchover can happen because of a
         fatal failure or by manual action. This CLI script file can contain
         commands for environment settings, debug and mirroring settings, and
         other commands not maintained by the configuration redundancy.

         When this object has the empty string value, ''H, no CLI script file
         is executed."
    DEFVAL      { ''H }
    ::= { sysBootInfo 12 }

sbiRedSwitchoverScriptStatus     OBJECT-TYPE
    SYNTAX      INTEGER {
        notRun  (0),
        success (1),
        fail    (2)
    }
    MAX-ACCESS  read-only
    STATUS      current
    DESCRIPTION
        "The value of sbiRedSwitchoverScriptStatus indicates the results of
         executing the CLI script file specified in sbiRedSwitchoverScript."
    ::= { sysBootInfo 13 }

sbiAllowBootLicenseViolations    OBJECT-TYPE
    SYNTAX      TruthValue
    MAX-ACCESS  read-write
    STATUS      current
    DESCRIPTION
        "The value of sbiAllowBootLicenseViolations specifies whether the system
         should allow successful execution of the boot-up configuration file
         even if it contains license violations.  When enabled, the system will
         not error on any configuration that causes a license violation permitting
         the system to come into service.  However, if violations are detected the
         system will reboot after one hour if the violations are not fixed."
    DEFVAL      { true }
    ::= { sysBootInfo 14 }

sysRadiusInfo                    OBJECT IDENTIFIER ::= { tmnxSysObjs 6 }

radiusOperStatus                 OBJECT-TYPE
    SYNTAX      INTEGER {
        up   (1),
        down (2)
    }
    MAX-ACCESS  read-only
    STATUS      current
    DESCRIPTION
        "The radiusOperStatus will have a value of 'up' if any one of the
         RADIUS servers in the radiusServerTable has the radiusServerOperStatus
         value of 'up'. It will have a value of 'down' if all the RADIUS
         servers in the radiusServerTable have the radiusServerOperStatus value
         of 'down'."
    ::= { sysRadiusInfo 1 }

radiusServerTable                OBJECT-TYPE
    SYNTAX      SEQUENCE OF RadiusServerEntry
    MAX-ACCESS  not-accessible
    STATUS      current
    DESCRIPTION
        "The radiusServerEntry has an entry for each RADIUS server. The table
         can have up to a maximum of 5 entries.

         Use TIMETRA-SECURITY-MIB::tmnxRadiusServerTable to configure entries."
    ::= { sysRadiusInfo 2 }

radiusServerEntry                OBJECT-TYPE
    SYNTAX      RadiusServerEntry
    MAX-ACCESS  not-accessible
    STATUS      current
    DESCRIPTION
        "Each row entry contains information about a RADIUS server."
    INDEX       { radiusServerIndex }
    ::= { radiusServerTable 1 }

RadiusServerEntry                ::= SEQUENCE
{
    radiusServerIndex                Unsigned32,
    radiusServerAddress              IpAddress,
    radiusServerOperStatus           INTEGER,
    radiusServerInetAddressType      InetAddressType,
    radiusServerInetAddress          InetAddress
}

radiusServerIndex                OBJECT-TYPE
    SYNTAX      Unsigned32 (1..5)
    MAX-ACCESS  not-accessible
    STATUS      current
    DESCRIPTION
        "The unique value which identifies a specific radius server."
    ::= { radiusServerEntry 1 }

radiusServerAddress              OBJECT-TYPE
    SYNTAX      IpAddress
    MAX-ACCESS  read-only
    STATUS      obsolete
    DESCRIPTION
        "The IP address of the RADIUS server.

         This object was made obsolete in the 5.0 release."
    ::= { radiusServerEntry 2 }

radiusServerOperStatus           OBJECT-TYPE
    SYNTAX      INTEGER {
        up   (1),
        down (2)
    }
    MAX-ACCESS  read-only
    STATUS      current
    DESCRIPTION
        "Current status of the RADIUS server."
    ::= { radiusServerEntry 3 }

radiusServerInetAddressType      OBJECT-TYPE
    SYNTAX      InetAddressType
    MAX-ACCESS  read-only
    STATUS      current
    DESCRIPTION
        "The value of radiusServerInetAddressType indicates the address type of
         radiusServerInetAddress address."
    ::= { radiusServerEntry 4 }

radiusServerInetAddress          OBJECT-TYPE
    SYNTAX      InetAddress (SIZE (0|4|16|20))
    MAX-ACCESS  read-only
    STATUS      current
    DESCRIPTION
        "The value of radiusServerInetAddress indicates the address of the
         Radius server."
    ::= { radiusServerEntry 5 }

tmnxSysNotifyObjs                OBJECT IDENTIFIER ::= { tmnxSysObjs 7 }

tmnxNotifyRow                    OBJECT-TYPE
    SYNTAX      RowPointer
    MAX-ACCESS  accessible-for-notify
    STATUS      current
    DESCRIPTION
        "tmnxNotifyRow is used by the configuration modify, create and delete
         traps. tmnxNotifyRow specifies the OID of the MIB table entry that was
         changed."
    ::= { tmnxSysNotifyObjs 1 }

tmnxNotifyRowAdminState          OBJECT-TYPE
    SYNTAX      TmnxAdminState
    MAX-ACCESS  accessible-for-notify
    STATUS      current
    DESCRIPTION
        "tmnxNotifyRowAdminState is used by the state change notification to
         specify the administrative state of the MIB table entry reported in
         the notification."
    ::= { tmnxSysNotifyObjs 2 }

tmnxNotifyRowOperState           OBJECT-TYPE
    SYNTAX      TmnxOperState
    MAX-ACCESS  accessible-for-notify
    STATUS      current
    DESCRIPTION
        "tmnxNotifyRowOperState is used by the state change notification to
         specify the operational state of the MIB table entry reported in the
         notification."
    ::= { tmnxSysNotifyObjs 3 }

tmnxMemoryModule                 OBJECT-TYPE
    SYNTAX      TNamedItem
    MAX-ACCESS  accessible-for-notify
    STATUS      current
    DESCRIPTION
        "tmnxMemoryModule is used by the module malloc failed notification to
         specify the memory module for which the trap is generated."
    ::= { tmnxSysNotifyObjs 4 }

tmnxModuleMallocSize             OBJECT-TYPE
    SYNTAX      Unsigned32
    UNITS       "bytes"
    MAX-ACCESS  accessible-for-notify
    STATUS      current
    DESCRIPTION
        "tmnxModuleMallocSize is used by the module malloc failed notification
         to specify the memory size (in bytes) requested in the failed malloc
         call."
    ::= { tmnxSysNotifyObjs 5 }

tmnxDroppedTrapID                OBJECT-TYPE
    SYNTAX      OBJECT IDENTIFIER
    MAX-ACCESS  accessible-for-notify
    STATUS      current
    DESCRIPTION
        "tmnxDroppedTrapID is used by the trap dropped notification to specify
         the NOTIFICATION-TYPE object identifier of the dropped trap."
    ::= { tmnxSysNotifyObjs 6 }

tmnxTrapDroppedReasonCode        OBJECT-TYPE
    SYNTAX      INTEGER {
        frequencyExceeded (1)
    }
    MAX-ACCESS  accessible-for-notify
    STATUS      current
    DESCRIPTION
        "tmnxTrapDroppedReasonCode is used by the trap dropped notification to
         specify the reason for which a trap is dropped."
    ::= { tmnxSysNotifyObjs 7 }

tmnxTrapDroppedEntryID           OBJECT-TYPE
    SYNTAX      OBJECT IDENTIFIER
    MAX-ACCESS  accessible-for-notify
    STATUS      current
    DESCRIPTION
        "tmnxTrapDroppedEntryID is used by the trap dropped notification to
         specify the table entry associated with the dropped trap."
    ::= { tmnxSysNotifyObjs 8 }

tmnxNotifyEntryOID               OBJECT-TYPE
    SYNTAX      OBJECT IDENTIFIER
    MAX-ACCESS  accessible-for-notify
    STATUS      current
    DESCRIPTION
        "tmnxNotifyEntryOID is used by the configuration modify, create and
         delete traps. tmnxNotifyEntryOID specifies the OID of the MIB table
         that was changed."
    ::= { tmnxSysNotifyObjs 9 }

tmnxSnmpdErrorMsg                OBJECT-TYPE
    SYNTAX      DisplayString
    MAX-ACCESS  accessible-for-notify
    STATUS      current
    DESCRIPTION
        "tmnxSnmpdErrorMsg is used by the tmnxSnmpdError notification to
         indicate the type of SNMP daemon error detected."
    ::= { tmnxSysNotifyObjs 10 }

tmnxPersistencyClient            OBJECT-TYPE
    SYNTAX      DisplayString
    MAX-ACCESS  accessible-for-notify
    STATUS      current
    DESCRIPTION
        "tmnxPersistencyClient is used by the persistencyClosedAlarmRaised,
         persistencyClosedAlarmCleared, persistencyFileSysThresRaised and
         persistencyFileSysThresCleared notification to indicate the affected
         persistent application."
    ::= { tmnxSysNotifyObjs 11 }

tmnxPersistencyFileLocator       OBJECT-TYPE
    SYNTAX      DisplayString
    MAX-ACCESS  accessible-for-notify
    STATUS      current
    DESCRIPTION
        "tmnxPersistencyFileLocator is used by the
         persistencyClosedAlarmRaised, persistencyClosedAlarmCleared,
         persistencyFileSysThresRaised and persistencyFileSysThresCleared
         notification to indicate the affected file used to store persistence
         data."
    ::= { tmnxSysNotifyObjs 12 }

tmnxPersistencyNotifyMsg         OBJECT-TYPE
    SYNTAX      DisplayString
    MAX-ACCESS  accessible-for-notify
    STATUS      current
    DESCRIPTION
        "tmnxPersistencyNotifyMsg is used by the persistencyClosedAlarmRaised
         persistencyClosedAlarmCleared, persistencyEventReport,
         persistencyFileSysThresRaised and persistencyFileSysThresCleared
         notification to provide additional information related to the event
         that occurred."
    ::= { tmnxSysNotifyObjs 13 }

tmnxPersistenceAffectedCpm       OBJECT-TYPE
    SYNTAX      DisplayString
    MAX-ACCESS  accessible-for-notify
    STATUS      current
    DESCRIPTION
        "tmnxPersistenceAffectedCpm is used by the
         persistencyClosedAlarmRaised, persistencyClosedAlarmCleared,
         persistencyFileSysThresRaised and persistencyFileSysThresCleared
         notification to indicate the affected CPM."
    ::= { tmnxSysNotifyObjs 14 }

tmnxSysTimeSetBy                 OBJECT-TYPE
    SYNTAX      INTEGER {
        ntp      (1),
        sntp     (2),
        snmp     (3),
        manually (4),
        rtc      (5)
    }
    MAX-ACCESS  accessible-for-notify
    STATUS      current
    DESCRIPTION
        "tmnxSysTimeSetBy is used by tmnxSysTimeSetBy notification to indicate
         who set the time."
    ::= { tmnxSysNotifyObjs 15 }

tmnxFtpFailureMsg                OBJECT-TYPE
    SYNTAX      DisplayString
    MAX-ACCESS  accessible-for-notify
    STATUS      current
    DESCRIPTION
        "tmnxFtpFailureMsg is used by tmnxFtpClientFailure notification to
         indicate FTP error."
    ::= { tmnxSysNotifyObjs 16 }

tmnxFtpFailureDestAddressType    OBJECT-TYPE
    SYNTAX      InetAddressType
    MAX-ACCESS  accessible-for-notify
    STATUS      current
    DESCRIPTION
        "tmnxFtpFailureDestAddressType is used by tmnxFtpClientFailure
         notification to indicate the IP address type of the remote host."
    ::= { tmnxSysNotifyObjs 17 }

tmnxFtpFailureDestAddress        OBJECT-TYPE
    SYNTAX      InetAddress (SIZE (4|16|20))
    MAX-ACCESS  accessible-for-notify
    STATUS      current
    DESCRIPTION
        "The value of tmnxFtpFailureDestAddress indicates the IP address of the
         remote host to which an ftp operation is being attempted on. The value
         of tmnxFtpFailureDestAddress is used by tmnxFtpClientFailure
         notification."
    ::= { tmnxSysNotifyObjs 18 }

tmnxNotifyObjectName             OBJECT-TYPE
    SYNTAX      DisplayString
    MAX-ACCESS  accessible-for-notify
    STATUS      current
    DESCRIPTION
        "tmnxNotifyObjectName is used by the configuration modify, create,
         delete and state change traps. tmnxNotifyObjectName specifies the
         human readable name of the OID instance of the MIB table entry that
         was changed."
    ::= { tmnxSysNotifyObjs 19 }

tmnxSyncFailureReason            OBJECT-TYPE
    SYNTAX      DisplayString
    MAX-ACCESS  accessible-for-notify
    STATUS      current
    DESCRIPTION
        "tmnxSyncFailureReason is used by the ssiSyncConfigFailed,
         ssiSyncBootEnvFailed, and ssiSyncRollbackFailed traps to specify the
         reason for synchronization failure."
    ::= { tmnxSysNotifyObjs 20 }

tmnxSysExecScript                OBJECT-TYPE
    SYNTAX      DisplayString
    MAX-ACCESS  accessible-for-notify
    STATUS      current
    DESCRIPTION
        "The value of tmnxSysExecScript specifies the location and name of the
         CLI command script file executed by a SROS CLI 'exec' command when the
         value of tmnxLogExRbkOpType is 'exec (1)'.

         When the value of tmnxLogExRbkOpType is 'vsd (4)', then the value of
         tmnxSysExecScript specifies an empty string.

         It is used by the tmnxSysExecStarted and tmnxSysExecFinished
         notifications."
    ::= { tmnxSysNotifyObjs 21 }

tmnxSysExecResult                OBJECT-TYPE
    SYNTAX      INTEGER {
        none    (0),
        success (1),
        fail    (2)
    }
    MAX-ACCESS  accessible-for-notify
    STATUS      current
    DESCRIPTION
        "The value of tmnxSysExecResult indicates the results of executing the
         CLI script file specified in tmnxSysExecScript. It is used by the
         tmnxSysExecFinished notification."
    ::= { tmnxSysNotifyObjs 22 }

tmnxSysRollbackFileType          OBJECT-TYPE
    SYNTAX      INTEGER {
        rollback (1),
        rescue   (2)
    }
    MAX-ACCESS  accessible-for-notify
    STATUS      current
    DESCRIPTION
        "tmnxSysRollbackFileType is used by tmnxSysRollbackStarted,
         tmnxSysRollbackSaveStarted, tmnxSysRollbackDeleteStarted,
         tmnxSysRollbackStatusChange, tmnxSysRollbackSaveStatusChange, and
         tmnxSysRollbackFileDeleteStatus notifications to indicate the type of
         file involved in a rollback operation."
    ::= { tmnxSysNotifyObjs 23 }

tmnxSysFileErrorType             OBJECT-TYPE
    SYNTAX      INTEGER {
        read  (1),
        write (2)
    }
    MAX-ACCESS  accessible-for-notify
    STATUS      current
    DESCRIPTION
        "tmnxSysFileErrorType is used by tmnxSysNvsysFileError notification to
         indicate the type of file error occurred."
    ::= { tmnxSysNotifyObjs 24 }

tmnxTrapDroppedCount             OBJECT-TYPE
    SYNTAX      Unsigned32
    MAX-ACCESS  accessible-for-notify
    STATUS      current
    DESCRIPTION
        "The object tmnxTrapDroppedCount is used by the tmnxTrapDropped
         notification to indicate the number of traps dropped.

         The value zero indicates that the number of traps dropped is purposely
         not included in the notification, for example because it is not
         accurately known."
    ::= { tmnxSysNotifyObjs 25 }

tmnxSysDNSSecDomainName          OBJECT-TYPE
    SYNTAX      TmnxDisplayStringURL
    MAX-ACCESS  accessible-for-notify
    STATUS      current
    DESCRIPTION
        "tmnxSysDNSSecDomainName is used by the sysDNSSecFailedAuthentication
         notification to indicate the domain name of the DNS query."
    ::= { tmnxSysNotifyObjs 26 }

tmnxSysLicenseErrorReason        OBJECT-TYPE
    SYNTAX      TItemDescription
    MAX-ACCESS  accessible-for-notify
    STATUS      current
    DESCRIPTION
        "The object tmnxSysLicenseErrorReason indicates the reason for an
         invalid license."
    ::= { tmnxSysNotifyObjs 27 }

tmnxSysLicenseTimeLeft           OBJECT-TYPE
    SYNTAX      Unsigned32
    UNITS       "minutes"
    MAX-ACCESS  accessible-for-notify
    STATUS      current
    DESCRIPTION
        "The object tmnxSysLicenseTimeLeft indicates the time remaining for the
         system to reboot as the result of an invalid license."
    ::= { tmnxSysNotifyObjs 28 }

tmnxSysNotifVsdServerName        OBJECT-TYPE
    SYNTAX      TLDisplayString
    MAX-ACCESS  accessible-for-notify
    STATUS      current
    DESCRIPTION
        "The value of tmnxSysNotifVsdServerName specifies the VSD server name."
    ::= { tmnxSysNotifyObjs 30 }

tmnxSysNotifXmppServerName       OBJECT-TYPE
    SYNTAX      DisplayString (SIZE (0..32))
    MAX-ACCESS  accessible-for-notify
    STATUS      current
    DESCRIPTION
        "The value of tmnxSysNotifXmppServerName indicates the name associated
         with the XMPP Server."
    ::= { tmnxSysNotifyObjs 31 }

tmnxSysLicenseErrorAction        OBJECT-TYPE
    SYNTAX      TItemDescription
    MAX-ACCESS  accessible-for-notify
    STATUS      current
    DESCRIPTION
        "The object tmnxSysLicenseErrorAction indicates the system action taken
         as a result of tmnxSysLicenseErrorReason."
    ::= { tmnxSysNotifyObjs 32 }

tmnxSysNotifAppStatsApplication  OBJECT-TYPE
    SYNTAX      TmnxSysLicenseApplication
    MAX-ACCESS  accessible-for-notify
    STATUS      current
    DESCRIPTION
        "The object tmnxSysNotifAppStatsApplication indicates an application in
         a virtual machine implementation that is subject to licensing."
    ::= { tmnxSysNotifyObjs 33 }

tmnxSysNotifAppStatsType         OBJECT-TYPE
    SYNTAX      TmnxSysLicenseAppStatsType
    MAX-ACCESS  accessible-for-notify
    STATUS      current
    DESCRIPTION
        "The object tmnxSysNotifAppStatsType indicates a type of statistics
         collected about an application in a virtual machine implementation
         subject to licensing."
    ::= { tmnxSysNotifyObjs 34 }

tmnxSysNotifAppStatsTime         OBJECT-TYPE
    SYNTAX      DateAndTime
    MAX-ACCESS  accessible-for-notify
    STATUS      current
    DESCRIPTION
        "The object tmnxSysNotifAppStatsTime indicates the time that the system
         collected statistics' values."
    ::= { tmnxSysNotifyObjs 35 }

tmnxNotifySysMgmtIfOriginalMode  OBJECT-TYPE
    SYNTAX      INTEGER {
        classic     (1),
        modelDriven (2),
        mixed       (3)
    }
    MAX-ACCESS  accessible-for-notify
    STATUS      current
    DESCRIPTION
        "tmnxNotifySysMgmtIfOriginalMode indicates the active system interface
         management mode the system was in when the configuration mode change
         request was sent."
    ::= { tmnxSysNotifyObjs 36 }

tmnxSysLicensingNotifyGroup      OBJECT-TYPE
    SYNTAX      TmnxSysLicensingGroup
    MAX-ACCESS  accessible-for-notify
    STATUS      current
    DESCRIPTION
        "The object tmnxSysLicensingNotifyGroup specifies the licensing group
         of an application license"
    ::= { tmnxSysNotifyObjs 37 }

tmnxSysLicensedNotifyAppName     OBJECT-TYPE
    SYNTAX      TNamedItem
    MAX-ACCESS  accessible-for-notify
    STATUS      current
    DESCRIPTION
        "The object tmnxSysLicensedNotifyAppName specifies the name of the
         licensed application"
    ::= { tmnxSysNotifyObjs 38 }

tmnxPrimaryConfigFileFormatType  OBJECT-TYPE
    SYNTAX      TmnxConfigFileFormatType
    MAX-ACCESS  accessible-for-notify
    STATUS      current
    DESCRIPTION
        "The value of tmnxPrimaryConfigFileFormatType specifies format of the
         primary configuration file."
    ::= { tmnxSysNotifyObjs 39 }

tmnxLiConfigFileFormatType       OBJECT-TYPE
    SYNTAX      TmnxConfigFileFormatType
    MAX-ACCESS  accessible-for-notify
    STATUS      current
    DESCRIPTION
        "The value of tmnxLiConfigFileFormatType specifies format of the li
         configuration file."
    ::= { tmnxSysNotifyObjs 40 }

sysLoginControlInfo              OBJECT IDENTIFIER ::= { tmnxSysObjs 8 }

slcFtpInboundMaxSessions         OBJECT-TYPE
    SYNTAX      Unsigned32 (0..5)
    MAX-ACCESS  read-write
    STATUS      current
    DESCRIPTION
        "The maximum number of concurrent inbound FTP sessions permitted."
    DEFVAL      { 3 }
    ::= { sysLoginControlInfo 1 }

slcTelnetInboundMaxSessions      OBJECT-TYPE
    SYNTAX      Unsigned32 (0..50)
    MAX-ACCESS  read-write
    STATUS      current
    DESCRIPTION
        "The value of slcTelnetInboundMaxSessions specifies the maximum number
         of concurrent inbound telnet sessions permitted.

         Note: The actual number of permitted concurrent inbound TELNET
         sessions may also be restricted by a system wide cumulative limit of
         50 concurrent inbound (SSH / TELNET) sessions."
    DEFVAL      { 5 }
    ::= { sysLoginControlInfo 2 }

slcTelnetOutboundMaxSessions     OBJECT-TYPE
    SYNTAX      Unsigned32 (0..15)
    MAX-ACCESS  read-write
    STATUS      current
    DESCRIPTION
        "The value of slcTelnetOutboundMaxSessions specifies the maximum number
         of concurrent outbound telnet sessions permitted."
    DEFVAL      { 5 }
    ::= { sysLoginControlInfo 3 }

slcPreLoginMessage               OBJECT-TYPE
    SYNTAX      TmnxLongDisplayString (SIZE (0..900))
    MAX-ACCESS  read-write
    STATUS      current
    DESCRIPTION
        "The message to be displayed prior to the login prompt of an inbound
         FTP or telnet session."
    DEFVAL      { ''H }
    ::= { sysLoginControlInfo 4 }

slcPreLoginMessageInclName       OBJECT-TYPE
    SYNTAX      TruthValue
    MAX-ACCESS  read-write
    STATUS      current
    DESCRIPTION
        "If the value of slcPreLoginMessageInclName is set to 'TRUE', the
         slcPreLoginMessage which is displayed prior to the login prompt will
         contain the system name."
    DEFVAL      { false }
    ::= { sysLoginControlInfo 5 }

slcMessageOfTheDay               OBJECT-TYPE
    SYNTAX      TmnxLongDisplayString (SIZE (0..900))
    MAX-ACCESS  read-write
    STATUS      current
    DESCRIPTION
        "The value of object slcMessageOfTheDay specifies the message to
         display when the user successfully logs in to an inbound FTP, Telnet,
         SSH or console session.

         If slcMessageOfTheDayType is set to 'motd-type-none(0)', the value of
         slcMessageOfTheDay is not displayed.

         If slcMessageOfTheDayType is set to 'motd-type-url(1)', the syntax of
         slcMessageOfTheDay is refined to TmnxDisplayStringURL.

         If slcMessageOfTheDayType is set to 'motd-type-text(2)', the value of
         slcMessageOfTheDay is the NVT ASCII text to display.

         Objects slcMessageOfTheDay and slcMessageOfTheDayType must be set
         together in the same SNMP SET request PDU."
    DEFVAL      { ''H }
    ::= { sysLoginControlInfo 6 }

slcMessageOfTheDayType           OBJECT-TYPE
    SYNTAX      INTEGER {
        motd-type-none (0),
        motd-type-url  (1),
        motd-type-text (2)
    }
    MAX-ACCESS  read-write
    STATUS      current
    DESCRIPTION
        "The value of object slcMessageOfTheDayType specifies the type of
         slcMessageOfTheDay.

         If the value of slcMessageOfTheDayType is set to 'motd-type-none(0)',
         then the message of the day is not displayed.

         If the value of slcMessageOfTheDayType is set to 'motd-type-url(1)',
         then the message is fetched from the URL specified in object
         slcMessageOfTheDay.

         If the value of slcMessageOfTheDayType is set to 'motd-type-text(2)',
         then the value of slcMessageOfTheDay is displayed.

         Objects slcMessageOfTheDay and slcMessageOfTheDayType must be set
         together in the same SNMP SET request PDU."
    DEFVAL      { motd-type-none }
    ::= { sysLoginControlInfo 7 }

slcLoginBanner                   OBJECT-TYPE
    SYNTAX      TruthValue
    MAX-ACCESS  read-write
    STATUS      current
    DESCRIPTION
        "If the value of slcLoginBanner is set to 'true', the login banner
         containing Nokia copyright and version information is displayed prior
         to the login prompt. If the value is set to 'false', the login banner
         is not displayed."
    DEFVAL      { false }
    ::= { sysLoginControlInfo 8 }

slcLoginExponentialBackOff       OBJECT-TYPE
    SYNTAX      TruthValue
    MAX-ACCESS  read-write
    STATUS      current
    DESCRIPTION
        "The value of slcLoginExponentialBackOff specifies if
         exponential-backoff of the login prompt is enabled.
         Exponential-backoff is used to deter dictionary attacks. A value of
         'true' specifies that exponential-backoff is enabled, while a value of
         'false' indicates that exponential-backoff is disabled."
    DEFVAL      { false }
    ::= { sysLoginControlInfo 9 }

slcTelnetGracefulShutdown        OBJECT-TYPE
    SYNTAX      TruthValue
    MAX-ACCESS  read-write
    STATUS      current
    DESCRIPTION
        "The value of slcTelnetGracefulShutdown specifies if graceful shutdown
         is enabled. A value of 'true' specifies that telnet sessions are
         closed gracefully by using a TCP FIN/ACK handshake. A value of 'false'
         indicates that telnet sessions are disconnected by sending a RST
         (reset) TCP packet."
    DEFVAL      { false }
    ::= { sysLoginControlInfo 10 }

slcSSHGracefulShutdown           OBJECT-TYPE
    SYNTAX      TruthValue
    MAX-ACCESS  read-write
    STATUS      current
    DESCRIPTION
        "The value of slcSSHGracefulShutdown specifies if graceful shutdown is
         enabled. A value of 'true' specifies that SSH sessions are closed
         gracefully by using a TCP FIN/ACK handshake. A value of 'false'
         indicates that SSH sessions are disconnected by sending a RST (reset)
         TCP packet."
    DEFVAL      { true }
    ::= { sysLoginControlInfo 11 }

slcTelnetMinTTLValue             OBJECT-TYPE
    SYNTAX      Unsigned32 (0..255)
    MAX-ACCESS  read-write
    STATUS      current
    DESCRIPTION
        "The value of slcTelnetMinTTLValue specifies the minimum TTL value for
         an incoming packet.

         This object can only be set if the value of tmnxCpmPerPeerQueuing is
         'true (1)'.

         This value is applied after restarting the Telnet server.

         If slcTelnetMinTTLValue is set to zero (0), the TTL Security feature
         is disabled."
    DEFVAL      { 0 }
    ::= { sysLoginControlInfo 12 }

slcSSHMinTTLValue                OBJECT-TYPE
    SYNTAX      Unsigned32 (0..255)
    MAX-ACCESS  read-write
    STATUS      current
    DESCRIPTION
        "The value of slcSSHMinTTLValue specifies the minimum TTL value for an
         incoming packet.

         This object can only be set if the value of tmnxCpmPerPeerQueuing is
         'true (1)'.

         This value is applied after restarting the SSH server.

         If slcSSHMinTTLValue is set to zero (0), the TTL Security feature is
         disabled."
    DEFVAL      { 0 }
    ::= { sysLoginControlInfo 13 }

slcSSHInboundMaxSessions         OBJECT-TYPE
    SYNTAX      Unsigned32 (0..50)
    MAX-ACCESS  read-write
    STATUS      current
    DESCRIPTION
        "The value of slcSSHInboundMaxSessions specifies the maximum number of
         concurrent inbound SSH sessions permitted.

         Note: The actual number of permitted concurrent inbound SSH sessions
         may also be restricted by a system wide cumulative limit of 50
         concurrent inbound (SSH / TELNET) sessions."
    DEFVAL      { 5 }
    ::= { sysLoginControlInfo 14 }

slcSSHOutboundMaxSessions        OBJECT-TYPE
    SYNTAX      Unsigned32 (0..15)
    MAX-ACCESS  read-write
    STATUS      current
    DESCRIPTION
        "The value of slcSSHOutboundMaxSessions specifies the maximum number of
         concurrent outbound SSH sessions permitted."
    DEFVAL      { 5 }
    ::= { sysLoginControlInfo 15 }

slcIdleTimeout                   OBJECT-TYPE
    SYNTAX      Unsigned32 (1..1440 | 9999)
    UNITS       "minutes"
    MAX-ACCESS  read-write
    STATUS      current
    DESCRIPTION
        "The value of the object slcIdleTimeout specifies the maximum time of
         how long a user initiated session (console, telnet, SSH, FTP) can be
         inactive before it will be automatically closed by the system. The
         value of 9999 specifies that the system will never automatically close
         an inactive user initiated session."
    DEFVAL      { 30 }
    ::= { sysLoginControlInfo 16 }

slcLoginScriptGlobal             OBJECT-TYPE
    SYNTAX      TmnxDisplayStringURL
    MAX-ACCESS  read-write
    STATUS      current
    DESCRIPTION
        "The value of the object slcLoginScriptGlobal specifies the URL of a
         CLI script that is executed when any user opens a CLI session.

         This allows an operator, for example, to define a common set of CLI
         aliases that are made available on the router for all users. This
         global login-exec script is executed before any user-specific
         login-exec file that may be configured."
    DEFVAL      { ''H }
    ::= { sysLoginControlInfo 17 }

slcLoginScriptPerUserDirectory   OBJECT-TYPE
    SYNTAX      TmnxDisplayStringURL
    MAX-ACCESS  read-write
    STATUS      current
    DESCRIPTION
        "The value of the object slcLoginScriptPerUserDirectory specifies the
         user-directory of the per-user login script configured in
         slcLoginScriptPerUserFilename.

         This per-user script is executed before any other user-specific login
         script, like the one configured in tmnxUserConsoleLoginExecFile or the
         one specified in RADIUS attribute Timetra-Exec-File (6527-8)."
    DEFVAL      { ''H }
    ::= { sysLoginControlInfo 18 }

slcLoginScriptPerUserFilename    OBJECT-TYPE
    SYNTAX      DisplayString (SIZE (0..180))
    MAX-ACCESS  read-write
    STATUS      current
    DESCRIPTION
        "The value of the object slcLoginScriptPerUserFilename specifies the
         filename of the per-user login script.

         The per-user login script is defined by concatenating the value of
         slcLoginScriptPerUserDirectory, the username, and the value of
         slcLoginScriptPerUserFilename. For example : If the value of
         slcLoginScriptPerUserDirectory is 'cf1:/local/users' and the value of
         slcLoginScriptPerUserFilename is 'login-script.txt', then file
         'cf1:/local/users/john/login-script.txt' is executed when user 'john'
         opens a CLI session."
    DEFVAL      { ''H }
    ::= { sysLoginControlInfo 19 }

sysLACPInfo                      OBJECT IDENTIFIER ::= { tmnxSysObjs 9 }

sysLACPSystemPriority            OBJECT-TYPE
    SYNTAX      Unsigned32 (1..65535)
    MAX-ACCESS  read-write
    STATUS      current
    DESCRIPTION
        "sysLACPSystemPriority is the Link Aggregation Control Protocol (LACP)
         system priority which is combined with the system MAC address to make
         up a unique system ID that is used by LACP in communications with LACP
         peer systems on Link Aggregation (LAG) ports."
    DEFVAL      { 32768 }
    ::= { sysLACPInfo 1 }

sysTacplusInfo                   OBJECT IDENTIFIER ::= { tmnxSysObjs 10 }

tacplusOperStatus                OBJECT-TYPE
    SYNTAX      INTEGER {
        up   (1),
        down (2)
    }
    MAX-ACCESS  read-only
    STATUS      current
    DESCRIPTION
        "The tacplusOperStatus will have a value of 'up' if any one of the
         TACACS+ servers in the tacplusServerTable has the
         tacplusServerOperStatus value of 'up'. It will have a value of 'down'
         if all the TACACS+ servers in the tacplusServerTable have the
         tacplusServerOperStatus value of 'down'."
    ::= { sysTacplusInfo 1 }

tacplusServerTable               OBJECT-TYPE
    SYNTAX      SEQUENCE OF TacplusServerEntry
    MAX-ACCESS  not-accessible
    STATUS      current
    DESCRIPTION
        "The tacplusServerEntry has an entry for each TACACS+ server. The table
         can have up to a maximum of 5 entries.

         Use TIMETRA-SECURITY-MIB::tmnxTacPlusServerTable to configure entries."
    ::= { sysTacplusInfo 2 }

tacplusServerEntry               OBJECT-TYPE
    SYNTAX      TacplusServerEntry
    MAX-ACCESS  not-accessible
    STATUS      current
    DESCRIPTION
        "Each row entry contains information about a TACACS+ server."
    INDEX       { tacplusServerIndex }
    ::= { tacplusServerTable 1 }

TacplusServerEntry               ::= SEQUENCE
{
    tacplusServerIndex               Unsigned32,
    tacplusServerAddress             IpAddress,
    tacplusServerOperStatus          INTEGER,
    tacPlusServerInetAddressType     InetAddressType,
    tacPlusServerInetAddress         InetAddress
}

tacplusServerIndex               OBJECT-TYPE
    SYNTAX      Unsigned32 (1..5)
    MAX-ACCESS  not-accessible
    STATUS      current
    DESCRIPTION
        "The unique value which identifies a specific TACACS+ server."
    ::= { tacplusServerEntry 1 }

tacplusServerAddress             OBJECT-TYPE
    SYNTAX      IpAddress
    MAX-ACCESS  read-only
    STATUS      obsolete
    DESCRIPTION
        "The IP address of the TACACS+ server.

         This object was made obsolete in the 5.0 release."
    ::= { tacplusServerEntry 2 }

tacplusServerOperStatus          OBJECT-TYPE
    SYNTAX      INTEGER {
        up   (1),
        down (2)
    }
    MAX-ACCESS  read-only
    STATUS      current
    DESCRIPTION
        "Current status of the TACACS+ server."
    ::= { tacplusServerEntry 3 }

tacPlusServerInetAddressType     OBJECT-TYPE
    SYNTAX      InetAddressType
    MAX-ACCESS  read-only
    STATUS      current
    DESCRIPTION
        "The value of tacPlusServerInetAddressType indicates the address type
         of tacPlusServerInetAddress address."
    ::= { tacplusServerEntry 4 }

tacPlusServerInetAddress         OBJECT-TYPE
    SYNTAX      InetAddress (SIZE (0|4|16|20))
    MAX-ACCESS  read-only
    STATUS      current
    DESCRIPTION
        "The value of tacPlusServerInetAddress indicates the address of the
         Tacplus server."
    ::= { tacplusServerEntry 5 }

sysBofInfo                       OBJECT IDENTIFIER ::= { tmnxSysObjs 11 }

sbiActiveIpAddr                  OBJECT-TYPE
    SYNTAX      IpAddress
    MAX-ACCESS  read-write
    STATUS      current
    DESCRIPTION
        "The value of sbiActiveIpAddr specifies the IP address of the ethernet
         port on the active CPM."
    DEFVAL      { 0 }
    ::= { sysBofInfo 1 }

sbiActiveIpMask                  OBJECT-TYPE
    SYNTAX      IpAddressPrefixLength
    MAX-ACCESS  read-write
    STATUS      current
    DESCRIPTION
        "The value of sbiActiveIpMask specifies the mask length of the subnet
         associated with the IP address of the ethernet port on the active CPM."
    DEFVAL      { 0 }
    ::= { sysBofInfo 2 }

sbiStandbyIpAddr                 OBJECT-TYPE
    SYNTAX      IpAddress
    MAX-ACCESS  read-write
    STATUS      current
    DESCRIPTION
        "The value of sbiStandbyIpAddr specifies the IP address of the ethernet
         port on the standby CPM."
    DEFVAL      { 0 }
    ::= { sysBofInfo 3 }

sbiStandbyIpMask                 OBJECT-TYPE
    SYNTAX      IpAddressPrefixLength
    MAX-ACCESS  read-write
    STATUS      current
    DESCRIPTION
        "The value of sbiStandbyIpMask specifies the mask length of the subnet
         associated with the IP address of the ethernet port on the standby
         CPM."
    DEFVAL      { 0 }
    ::= { sysBofInfo 4 }

sbiPrimaryImage                  OBJECT-TYPE
    SYNTAX      TmnxDisplayStringURL
    MAX-ACCESS  read-write
    STATUS      current
    DESCRIPTION
        "The value of sbiPrimaryImage specifies the primary location of the
         directory that contains the runtime image files."
    DEFVAL      { ''H }
    ::= { sysBofInfo 5 }

sbiSecondaryImage                OBJECT-TYPE
    SYNTAX      TmnxDisplayStringURL
    MAX-ACCESS  read-write
    STATUS      current
    DESCRIPTION
        "The value of sbiSecondaryImage specifies the secondary location of the
         directory that contains the runtime image files."
    DEFVAL      { ''H }
    ::= { sysBofInfo 6 }

sbiTertiaryImage                 OBJECT-TYPE
    SYNTAX      TmnxDisplayStringURL
    MAX-ACCESS  read-write
    STATUS      current
    DESCRIPTION
        "The value of sbiTertiaryImage specifies the tertiary location of the
         directory that contains the runtime image files."
    DEFVAL      { ''H }
    ::= { sysBofInfo 7 }

sbiPrimaryConfigFile             OBJECT-TYPE
    SYNTAX      TmnxDisplayStringURL
    MAX-ACCESS  read-write
    STATUS      current
    DESCRIPTION
        "The value of sbiPrimaryConfigFile specifies the location and name of
         the primary configuration file."
    DEFVAL      { ''H }
    ::= { sysBofInfo 8 }

sbiSecondaryConfigFile           OBJECT-TYPE
    SYNTAX      TmnxDisplayStringURL
    MAX-ACCESS  read-write
    STATUS      current
    DESCRIPTION
        "The value of sbiSecondaryConfigFile specifies the location and name of
         the secondary configuration file."
    DEFVAL      { ''H }
    ::= { sysBofInfo 9 }

sbiTertiaryConfigFile            OBJECT-TYPE
    SYNTAX      TmnxDisplayStringURL
    MAX-ACCESS  read-write
    STATUS      current
    DESCRIPTION
        "The value of sbiTertiaryConfigFile specifies the location and name of
         the tertiary configuration file."
    DEFVAL      { ''H }
    ::= { sysBofInfo 10 }

sbiPersist                       OBJECT-TYPE
    SYNTAX      TruthValue
    MAX-ACCESS  read-write
    STATUS      current
    DESCRIPTION
        "The value of sbiPersist specifies whether or not the system will
         preserve SNMP indexes between reboots. When set to 'true', persistent
         indexing is enabled."
    DEFVAL      { false }
    ::= { sysBofInfo 11 }

sbiConsoleSpeed                  OBJECT-TYPE
    SYNTAX      Unsigned32 (9600 | 19200 | 38400 | 57600 | 115200)
    UNITS       "bps"
    MAX-ACCESS  read-write
    STATUS      current
    DESCRIPTION
        "The value of sbiConsoleSpeed specifies the baud rate of the console
         port."
    DEFVAL      { 115200 }
    ::= { sysBofInfo 12 }

sbiAutoNegotiate                 OBJECT-TYPE
    SYNTAX      TruthValue
    MAX-ACCESS  read-write
    STATUS      current
    DESCRIPTION
        "The value of sbiAutoNegotiate determines whether or not the speed and
         duplex parameters will be automatically negotiated on the CPM ethernet
         port. When set to 'true', auto-negotiation is enabled."
    DEFVAL      { true }
    ::= { sysBofInfo 13 }

sbiSpeed                         OBJECT-TYPE
    SYNTAX      Unsigned32 (10 | 100)
    UNITS       "megabps"
    MAX-ACCESS  read-write
    STATUS      current
    DESCRIPTION
        "The value of sbiSpeed specifies the speed of the CPM ethernet port.
         This value is ignored if auto-negotiation is enabled."
    DEFVAL      { 100 }
    ::= { sysBofInfo 14 }

sbiDuplex                        OBJECT-TYPE
    SYNTAX      INTEGER {
        full (1),
        half (2)
    }
    MAX-ACCESS  read-write
    STATUS      current
    DESCRIPTION
        "The value of sbiDuplex specifies the duplex mode for the CPM ethernet
         port. This value is ignored if auto-negotiation is enabled."
    DEFVAL      { full }
    ::= { sysBofInfo 15 }

sbiPrimaryDns                    OBJECT-TYPE
    SYNTAX      IpAddress
    MAX-ACCESS  read-write
    STATUS      current
    DESCRIPTION
        "The value of sbiPrimaryDns specifies the IP address of the primary DNS
         server to use for DNS name resolution."
    DEFVAL      { 0 }
    ::= { sysBofInfo 16 }

sbiSecondaryDns                  OBJECT-TYPE
    SYNTAX      IpAddress
    MAX-ACCESS  read-write
    STATUS      current
    DESCRIPTION
        "The value of sbiSecondaryDns specifies the IP address of the secondary
         DNS server to use for DNS name resolution."
    DEFVAL      { 0 }
    ::= { sysBofInfo 17 }

sbiTertiaryDns                   OBJECT-TYPE
    SYNTAX      IpAddress
    MAX-ACCESS  read-write
    STATUS      current
    DESCRIPTION
        "The value of sbiTertiaryDns specifies the IP address of the tertiary
         DNS server to use for DNS name resolution."
    DEFVAL      { 0 }
    ::= { sysBofInfo 18 }

sbiDnsDomain                     OBJECT-TYPE
    SYNTAX      DisplayString (SIZE (0..178))
    MAX-ACCESS  read-write
    STATUS      current
    DESCRIPTION
        "The value of sbiDnsDomain specifies the domain name to use when
         performing DNS address resolution."
    DEFVAL      { ''H }
    ::= { sysBofInfo 19 }

sbiWait                          OBJECT-TYPE
    SYNTAX      Unsigned32 (1..10)
    UNITS       "seconds"
    MAX-ACCESS  read-write
    STATUS      current
    DESCRIPTION
        "The value of sbiWait specifies the number of seconds the system pauses
         at the start of the boot process. This pause allows the operator to
         interrupt the system initialization at the console and manually
         override the parameters in the BOF."
    DEFVAL      { 3 }
    ::= { sysBofInfo 20 }

sbiStaticRouteTable              OBJECT-TYPE
    SYNTAX      SEQUENCE OF SbiStaticRouteEntry
    MAX-ACCESS  not-accessible
    STATUS      current
    DESCRIPTION
        "The sbiStaticRouteTable contains an entry for each static route
         configured for the CPM ethernet port. These static routes are only
         used to route traffic generated by the CPM ethernet port. The table
         can have up to a maximum of 10 entries."
    ::= { sysBofInfo 21 }

sbiStaticRouteEntry              OBJECT-TYPE
    SYNTAX      SbiStaticRouteEntry
    MAX-ACCESS  not-accessible
    STATUS      current
    DESCRIPTION
        "Each row entry contains information about a static route configured
         for the CPM ethernet port.

         Entries in this table can be created and deleted via SNMP SET
         operations to sbiStaticRouteRowStatus."
    INDEX       {
        sbiStaticRouteDest,
        sbiStaticRouteMask
    }
    ::= { sbiStaticRouteTable 1 }

SbiStaticRouteEntry              ::= SEQUENCE
{
    sbiStaticRouteDest               IpAddress,
    sbiStaticRouteMask               IpAddressPrefixLength,
    sbiStaticRouteNextHop            IpAddress,
    sbiStaticRouteRowStatus          RowStatus
}

sbiStaticRouteDest               OBJECT-TYPE
    SYNTAX      IpAddress
    MAX-ACCESS  not-accessible
    STATUS      current
    DESCRIPTION
        "The value of sbiStaticRouteDest specifies the destination IP address
         of this static route."
    ::= { sbiStaticRouteEntry 1 }

sbiStaticRouteMask               OBJECT-TYPE
    SYNTAX      IpAddressPrefixLength
    MAX-ACCESS  not-accessible
    STATUS      current
    DESCRIPTION
        "The value of sbiStaticRouteMask specifies the length of the subnet
         mask associated with the destination IP address of this static route."
    ::= { sbiStaticRouteEntry 2 }

sbiStaticRouteNextHop            OBJECT-TYPE
    SYNTAX      IpAddress
    MAX-ACCESS  read-create
    STATUS      current
    DESCRIPTION
        "The value of sbiStaticRouteNextHop specifies the IP address of the
         next hop for this static route. This IP address should be in the same
         subnet as the ethernet port on the active CPM. The value of
         sbiStaticRouteNextHop must be set to a valid IP address for the row
         creation to succeed."
    ::= { sbiStaticRouteEntry 3 }

sbiStaticRouteRowStatus          OBJECT-TYPE
    SYNTAX      RowStatus
    MAX-ACCESS  read-create
    STATUS      current
    DESCRIPTION
        "sbiStaticRouteRowStatus controls the creation and deletion of rows in
         the table. To create a row in this table, set the row status to
         createAndGo(4)'. The value of sbiStaticRouteNextHop must also be set
         to a valid IP address for the row creation to succeed. To delete a row
         in this table, set the row status to delete(6)."
    ::= { sbiStaticRouteEntry 4 }

sbiActiveIPv6Addr                OBJECT-TYPE
    SYNTAX      InetAddressIPv6
    MAX-ACCESS  read-write
    STATUS      current
    DESCRIPTION
        "The value of sbiActiveIPv6Addr specifies the IPv6 address of the
         ethernet port on the active CPM."
    DEFVAL      { '00000000000000000000000000000000'H }
    ::= { sysBofInfo 22 }

sbiActiveIPv6PfxLen              OBJECT-TYPE
    SYNTAX      InetAddressPrefixLength (0..128)
    MAX-ACCESS  read-write
    STATUS      current
    DESCRIPTION
        "The value of sbiActiveIPv6PfxLen specifies the prefix length of the
         subnet associated with the sbiActiveIPv6Addr address of the ethernet
         port on the active CPM."
    DEFVAL      { 0 }
    ::= { sysBofInfo 23 }

sbiStandbyIPv6Addr               OBJECT-TYPE
    SYNTAX      InetAddressIPv6
    MAX-ACCESS  read-write
    STATUS      current
    DESCRIPTION
        "The value of sbiStandbyIPv6Addr specifies the IPv6 address of the
         ethernet port on the standby CPM."
    DEFVAL      { '00000000000000000000000000000000'H }
    ::= { sysBofInfo 24 }

sbiStandbyIPv6PfxLen             OBJECT-TYPE
    SYNTAX      InetAddressPrefixLength (0..128)
    MAX-ACCESS  read-write
    STATUS      current
    DESCRIPTION
        "The value of sbiStandbyIPv6PfxLen specifies the prefix length of the
         subnet associated with the sbiStandbyIPv6Addr address of the ethernet
         port on the active CPM."
    DEFVAL      { 0 }
    ::= { sysBofInfo 25 }

sbiPrimaryDnsIPv6Addr            OBJECT-TYPE
    SYNTAX      InetAddressIPv6
    MAX-ACCESS  read-write
    STATUS      current
    DESCRIPTION
        "The value of sbiPrimaryDnsIPv6Addr specifies the IPv6 address of the
         primary DNS server to use for DNS name resolution."
    DEFVAL      { '00000000000000000000000000000000'H }
    ::= { sysBofInfo 26 }

sbiSecondaryDnsIPv6Addr          OBJECT-TYPE
    SYNTAX      InetAddressIPv6
    MAX-ACCESS  read-write
    STATUS      current
    DESCRIPTION
        "The value of sbiSecondaryDnsIPv6Addr specifies the IPv6 address of the
         secondary DNS server to use for DNS name resolution."
    DEFVAL      { '00000000000000000000000000000000'H }
    ::= { sysBofInfo 27 }

sbiTertiaryDnsIPv6Addr           OBJECT-TYPE
    SYNTAX      InetAddressIPv6
    MAX-ACCESS  read-write
    STATUS      current
    DESCRIPTION
        "The value of sbiTertiaryDnsIPv6Addr specifies the IPv6 address of the
         tertiary DNS server to use for DNS name resolution."
    DEFVAL      { '00000000000000000000000000000000'H }
    ::= { sysBofInfo 28 }

sbiStaticRouteIPv6Table          OBJECT-TYPE
    SYNTAX      SEQUENCE OF SbiStaticRouteIPv6Entry
    MAX-ACCESS  not-accessible
    STATUS      current
    DESCRIPTION
        "The sbiStaticRouteIPv6Table contains an entry for each static IPv6
         route configured for the CPM ethernet port. These static routes are
         only used to route traffic generated by the CPM ethernet port. The
         table can have up to a maximum of 10 entries."
    ::= { sysBofInfo 29 }

sbiStaticRouteIPv6Entry          OBJECT-TYPE
    SYNTAX      SbiStaticRouteIPv6Entry
    MAX-ACCESS  not-accessible
    STATUS      current
    DESCRIPTION
        "Each row entry contains information about a static IPv6 route
         configured for the CPM ethernet port.

         Entries in this table can be created and deleted via SNMP SET
         operations to sbiStaticRouteIPv6RowStatus."
    INDEX       {
        sbiStaticRouteIPv6Dest,
        sbiStaticRouteIPv6PfxLen
    }
    ::= { sbiStaticRouteIPv6Table 1 }

SbiStaticRouteIPv6Entry          ::= SEQUENCE
{
    sbiStaticRouteIPv6Dest           InetAddressIPv6,
    sbiStaticRouteIPv6PfxLen         InetAddressPrefixLength,
    sbiStaticRouteIPv6NextHop        InetAddressIPv6,
    sbiStaticRouteIPv6RowStatus      RowStatus
}

sbiStaticRouteIPv6Dest           OBJECT-TYPE
    SYNTAX      InetAddressIPv6
    MAX-ACCESS  not-accessible
    STATUS      current
    DESCRIPTION
        "The value of sbiStaticRouteIPv6Dest specifies the destination IPv6
         address of this static route."
    ::= { sbiStaticRouteIPv6Entry 1 }

sbiStaticRouteIPv6PfxLen         OBJECT-TYPE
    SYNTAX      InetAddressPrefixLength (0..128)
    MAX-ACCESS  not-accessible
    STATUS      current
    DESCRIPTION
        "The value of sbiStaticRouteIPv6PfxLen specifies the prefix length of
         sbiStaticRouteIPv6Dest, the destination IPv6 address of this static
         route."
    ::= { sbiStaticRouteIPv6Entry 2 }

sbiStaticRouteIPv6NextHop        OBJECT-TYPE
    SYNTAX      InetAddressIPv6
    MAX-ACCESS  read-create
    STATUS      current
    DESCRIPTION
        "The value of sbiStaticRouteIPv6NextHop specifies the IPv6 address of
         the next hop for this static route. This IPv6 address should be in the
         same subnet as the ethernet port on the active CPM. The value of
         sbiStaticRouteIPv6NextHop must be set to a valid IPv6 address for the
         row creation to succeed."
    ::= { sbiStaticRouteIPv6Entry 3 }

sbiStaticRouteIPv6RowStatus      OBJECT-TYPE
    SYNTAX      RowStatus
    MAX-ACCESS  read-create
    STATUS      current
    DESCRIPTION
        "sbiStaticRouteIPv6RowStatus controls the creation and deletion of rows
         in the table. To create a row in this table, set the row status to
         createAndGo(4)'. The value of sbiStaticRouteIPv6NextHop must also be
         set to a valid IPv6 address for the row creation to succeed. To delete
         a row in this table, set the row status to delete(6)."
    ::= { sbiStaticRouteIPv6Entry 4 }

sbiLiSeparate                    OBJECT-TYPE
    SYNTAX      TruthValue
    MAX-ACCESS  read-write
    STATUS      current
    DESCRIPTION
        "The value of sbiLiSeparate specifies whether or not a non-LI user has
         access to Lawful Intercept (LI) information.  When sbiLiSeparate has
         a value of 'true', a user who does not have the TIMETRA-SECURITY-MIB::
         tmnxUserAccess 'li' bit set will not be allowed to access CLI or
         SNMP objects in the 'li' context.

         A change to the value of this object does not take affect until the
         system is rebooted."
    DEFVAL      { false }
    ::= { sysBofInfo 30 }

sbiLiLocalSave                   OBJECT-TYPE
    SYNTAX      TruthValue
    MAX-ACCESS  read-write
    STATUS      current
    DESCRIPTION
        "The value of sbiLiLocalSave specifies whether or not Lawful Intercept
         (LI) configuration is allowed to be save to a local file.

         A change to the value of this object does not take affect until the
         system is rebooted."
    DEFVAL      { true }
    ::= { sysBofInfo 31 }

sbiLicenseFile                   OBJECT-TYPE
    SYNTAX      TmnxDisplayStringURL
    MAX-ACCESS  read-write
    STATUS      current
    DESCRIPTION
        "The value of sbiLicenseFile specifies the location and name of the
         license file."
    DEFVAL      { ''H }
    ::= { sysBofInfo 32 }

sbiFips1402Level1                OBJECT-TYPE
    SYNTAX      TruthValue
    MAX-ACCESS  read-create
    STATUS      current
    DESCRIPTION
        "The value of sbiFips1402Level1 specifies whether or not the security
         level 1 of Federal Information Processing Standards 140 series version
         2 (FIPS-140-2) is enabled.

         A change to the value of this object does not take effect until after
         a system reboot.  If the value of sbiFips1402Level1 is 'true (1)',
         after a system reboot, any configuration that is not supported by
         FIPS-140-2 level 1, will be retrievable via SNMP requests."
    REFERENCE
        "FIPS PUB 140-2, 'Security Requirement for Cryptographic Modules',
         May 2001."
    DEFVAL      { false }
    ::= { sysBofInfo 34 }

sbiSystemBaseMacAddress          OBJECT-TYPE
    SYNTAX      MacAddress
    MAX-ACCESS  read-write
    STATUS      current
    DESCRIPTION
        "The value of sbiSystemBaseMacAddress specifies the administratively
         configured base system ethernet MAC address. Special purpose MAC
         addresses used by the system software are constructed from this base
         address. The value is the first MAC address in a contiguous range of
         1024 addresses.

         If configured, sbiSystemBaseMacAddress will override the value given
         by tmnxChassisBaseMacAddress.

         A value of all zeroes indicates this object is not configured."
    DEFVAL      { '000000000000'H }
    ::= { sysBofInfo 35 }

sbiEssSystemType                 OBJECT-TYPE
    SYNTAX      TruthValue
    MAX-ACCESS  read-write
    STATUS      current
    DESCRIPTION
        "The value of sbiEssSystemType specifies whether or not the system is
         administratively configured to function as a Nokia SROS Ethernet
         Service Switch (ESS)."
    DEFVAL      { false }
    ::= { sysBofInfo 36 }

sbiSystemProfile                 OBJECT-TYPE
    SYNTAX      INTEGER {
        none     (0),
        profileA (1),
        profileB (2)
    }
    MAX-ACCESS  read-write
    STATUS      current
    DESCRIPTION
        "The value of sbiSystemProfile specifies the system profile in the BOF.

           'none (0)'   - No system profile set, permits the co-existence of
                          FP3 and FP4-based line cards in the system.
           'profileA (1)- This system profile is primarily targeted at
                          subscriber services and layer 2/3 VPN business
                          services.
           'profileB (2)- This system profile is primarily targeted at
                          infrastructure routing, core, peering, and DC-GW
                          applications."
    DEFVAL      { none }
    ::= { sysBofInfo 37 }

sbiAutoBoot                      OBJECT-TYPE
    SYNTAX      TruthValue
    MAX-ACCESS  read-write
    STATUS      current
    DESCRIPTION
        "The value of sbiAutoBoot specifies whether or not the system will  run
         the auto-provisioning agent."
    DEFVAL      { false }
    ::= { sysBofInfo 38 }

sbiAutoBootClientId              OBJECT-TYPE
    SYNTAX      OCTET STRING (SIZE (0..58))
    MAX-ACCESS  read-write
    STATUS      current
    DESCRIPTION
        "The value of sbiAutoBootClientId specifies the identifier to use when
         performing network discovery requests."
    DEFVAL      { "" }
    ::= { sysBofInfo 39 }

sbiAutoBootClientIdType          OBJECT-TYPE
    SYNTAX      INTEGER {
        none  (1),
        ascii (2),
        hex   (3),
        mac   (4)
    }
    MAX-ACCESS  read-write
    STATUS      current
    DESCRIPTION
        "The value of sbiAutoBootClientIdType represents how the value
         of sbiAutoBootClientId is encoded:
         - 'none (1)'  : no identification has been specified
         - 'ascii(2)'  : this option contains seven-bit ASCII characters
         - 'hex  (3)'  : this option contains octets. It must be displayed in
                        hexadecimal format because it contains non-printable
                        characters.
         - 'mac  (4)'  : this type is the chassis mac in octets. It must be displayed in
                        hexadecimal format because it contains non-printable
                        characters."
    DEFVAL      { none }
    ::= { sysBofInfo 40 }

sbiAutoBootUsingMgmt             OBJECT-TYPE
    SYNTAX      TruthValue
    MAX-ACCESS  read-write
    STATUS      current
    DESCRIPTION
        "The value of sbiAutoBootUsingMgmt specifies whether or not the system
         will auto-boot using the management port."
    DEFVAL      { false }
    ::= { sysBofInfo 41 }

sbiAutoBootUsingInband           OBJECT-TYPE
    SYNTAX      TruthValue
    MAX-ACCESS  read-write
    STATUS      current
    DESCRIPTION
        "The value of sbiAutoBootUsingInband specifies whether or not the
         system  will auto-boot using the inband ports."
    DEFVAL      { false }
    ::= { sysBofInfo 42 }

sbiAutoBootInbandVlan            OBJECT-TYPE
    SYNTAX      Unsigned32 (0..4094)
    MAX-ACCESS  read-write
    STATUS      current
    DESCRIPTION
        "The value of sbiAutoBootInbandVlan specifies a VLAN that the system
         will use for auto-boot on inband ports."
    DEFVAL      { 0 }
    ::= { sysBofInfo 43 }

sbiAutoBootUsingIpv4             OBJECT-TYPE
    SYNTAX      TruthValue
    MAX-ACCESS  read-write
    STATUS      current
    DESCRIPTION
        "The value of sbiAutoBootUsingIpv4 specifies whether or not the system
         will send IPv4 DHCP Discovery requests."
    DEFVAL      { false }
    ::= { sysBofInfo 44 }

sbiAutoBootUsingIpv6             OBJECT-TYPE
    SYNTAX      TruthValue
    MAX-ACCESS  read-write
    STATUS      current
    DESCRIPTION
        "The value of sbiAutoBootUsingIpv6 specifies whether or not the system
         will send IPv6 DHCP Solicit requests."
    DEFVAL      { false }
    ::= { sysBofInfo 45 }

sbiAutoBootIncludeUserClass      OBJECT-TYPE
    SYNTAX      TruthValue
    MAX-ACCESS  read-write
    STATUS      current
    DESCRIPTION
        "The value of sbiAutoBootIncludeUserClass specifies whether or not the system
         will include User Class data information in  IPv4/IPv6 DHCP requests."
    DEFVAL      { false }
    ::= { sysBofInfo 46 }

sbiAutoConfigure                 OBJECT IDENTIFIER ::= { sysBofInfo 54 }

sbiAutoIpv4                      OBJECT IDENTIFIER ::= { sbiAutoConfigure 1 }

sbiAutoIpv4Dhcp                  OBJECT-TYPE
    SYNTAX      TruthValue
    MAX-ACCESS  read-write
    STATUS      current
    DESCRIPTION
        "The value of sbiAutoIpv4Dhcp specifies if the system  sends IPv4 DHCP
         Discovery requests."
    DEFVAL      { false }
    ::= { sbiAutoIpv4 1 }

sbiAutoIpv4DhcpClientIdType      OBJECT-TYPE
    SYNTAX      INTEGER {
        default (1),
        ascii   (2),
        hex     (3)
    }
    MAX-ACCESS  read-write
    STATUS      current
    DESCRIPTION
        "The value of sbiAutoIpv4DhcpClientIdType specifies how the value
         of sbiAutoIpv4DhcpClientId has to be interpreted:
         - 'default (1)'  : use the chassis serial number, formatted as ASCII characters
         - 'ascii(2)'  : seven-bit ASCII characters
         - 'hex  (3)'  : octets, possibly non-printable characters."
    DEFVAL      { default }
    ::= { sbiAutoIpv4 3 }

sbiAutoIpv4DhcpClientId          OBJECT-TYPE
    SYNTAX      OCTET STRING (SIZE (0..127))
    MAX-ACCESS  read-write
    STATUS      current
    DESCRIPTION
        "The value of sbiAutoIpv4DhcpClientId specifies the client identifier."
    DEFVAL      { "" }
    ::= { sbiAutoIpv4 4 }

sbiAutoIpv4DhcpOptUserClass      OBJECT-TYPE
    SYNTAX      TruthValue
    MAX-ACCESS  read-write
    STATUS      current
    DESCRIPTION
        "The value of sbiAutoIpv4DhcpOptUserClass specifies if the system  DHCP
         client sends the User Class option."
    DEFVAL      { false }
    ::= { sbiAutoIpv4 5 }

sbiAutoIpv4DhcpTimeout           OBJECT-TYPE
    SYNTAX      Unsigned32 (1..65535)
    UNITS       "seconds"
    MAX-ACCESS  read-create
    STATUS      current
    DESCRIPTION
        "The value of the object sbiAutoIpv4DhcpTimeout specifies the maximum
         time the system DHCP client waits for a DHCPOFFER message.

         While the system waits for the DHCPOFFER message, reading of the
         configuration file is suspended."
    DEFVAL      { 30 }
    ::= { sbiAutoIpv4 6 }

sbiAutoIpv6                      OBJECT IDENTIFIER ::= { sbiAutoConfigure 2 }

sbiAutoIpv6Dhcp                  OBJECT-TYPE
    SYNTAX      TruthValue
    MAX-ACCESS  read-write
    STATUS      current
    DESCRIPTION
        "The value of sbiAutoIpv6Dhcp specifies if the system  sends IPv6 DHCP
         Solicit requests."
    DEFVAL      { false }
    ::= { sbiAutoIpv6 1 }

sbiAutoIpv6DhcpClientIdType      OBJECT-TYPE
    SYNTAX      INTEGER {
        default        (1),
        duidEnterprise (2),
        duidLinkLocal  (3)
    }
    MAX-ACCESS  read-write
    STATUS      current
    DESCRIPTION
        "The value of sbiAutoIpv6DhcpClientIdType specifies how the DHCPv6
         client generates the Client Identifier option.

         A value of 'default' means the DHCPv6 client uses a Client Identifier
         with the chassis serial number, formatted as ASCII characters, in the
         variable length identifier following the DUID-EN type code and
         enterprise-number."
    DEFVAL      { default }
    ::= { sbiAutoIpv6 2 }

sbiAutoIpv6DhcpClientIdDuidType  OBJECT-TYPE
    SYNTAX      INTEGER {
        none  (1),
        ascii (2),
        hex   (3)
    }
    MAX-ACCESS  read-write
    STATUS      current
    DESCRIPTION
        "The value of sbiAutoIpv6DhcpClientIdDuidType specifies how  the DUID
         in the sbiAutoIpv6DhcpClientIdDuid has to be interpreted.

         When the value of sbiAutoIpv6DhcpClientIdType is equal to
         'duidEnterprise', a value other than 'none' must be specified.

         A value other than 'none' is only allowed when the value of
         sbiAutoIpv6DhcpClientIdType is equal to 'duidEnterprise'."
    DEFVAL      { none }
    ::= { sbiAutoIpv6 3 }

sbiAutoIpv6DhcpClientIdDuid      OBJECT-TYPE
    SYNTAX      OCTET STRING (SIZE (0..124))
    MAX-ACCESS  read-write
    STATUS      current
    DESCRIPTION
        "The value of sbiAutoIpv6DhcpClientIdDuid specifies the client
         identifier DHCP Unique Identifier (DUID).

         When the value of sbiAutoIpv6DhcpClientIdDuidType is not equal to
         'none', a non-empty value must be specified.

         A non-empty value is only allowed when the value of
         sbiAutoIpv6DhcpClientIdDuidType is not equal to 'none'."
    DEFVAL      { "" }
    ::= { sbiAutoIpv6 4 }

sbiAutoIpv6DhcpOptUserClass      OBJECT-TYPE
    SYNTAX      TruthValue
    MAX-ACCESS  read-write
    STATUS      current
    DESCRIPTION
        "The value of sbiAutoIpv6DhcpOptUserClass specifies if the system
         DHCPv6 client sends the User Class option."
    DEFVAL      { false }
    ::= { sbiAutoIpv6 5 }

sbiAutoIpv6DhcpTimeout           OBJECT-TYPE
    SYNTAX      Unsigned32 (1..65535)
    UNITS       "seconds"
    MAX-ACCESS  read-create
    STATUS      current
    DESCRIPTION
        "The value of the object sbiAutoIpv6DhcpTimeout specifies the maximum
         time the system DHCPv6 client waits for an ADVERTISE message.

         While the system waits for the ADVERTISE message, reading of the
         configuration file is suspended."
    DEFVAL      { 30 }
    ::= { sbiAutoIpv6 6 }

sbiStandbyAIpAddr                OBJECT-TYPE
    SYNTAX      IpAddress
    MAX-ACCESS  read-write
    STATUS      current
    DESCRIPTION
        "The value of sbiStandbyAIpAddr specifies the IP address of the
         ethernet port on CPM A if CPM A is the standby CPM."
    DEFVAL      { 0 }
    ::= { sysBofInfo 55 }

sbiStandbyAIpMask                OBJECT-TYPE
    SYNTAX      IpAddressPrefixLength
    MAX-ACCESS  read-write
    STATUS      current
    DESCRIPTION
        "The value of sbiStandbyAIpMask specifies the mask length of the subnet
         associated with the IP address of the ethernet port on CPM A if CPM A
         is the standby CPM."
    DEFVAL      { 0 }
    ::= { sysBofInfo 56 }

sbiStandbyAIPv6Addr              OBJECT-TYPE
    SYNTAX      InetAddressIPv6
    MAX-ACCESS  read-write
    STATUS      current
    DESCRIPTION
        "The value of sbiStandbyAIPv6Addr specifies the IPv6 address of the
         ethernet port on CPM A if CPM A is the standby CPM"
    DEFVAL      { '00000000000000000000000000000000'H }
    ::= { sysBofInfo 57 }

sbiStandbyAIPv6PfxLen            OBJECT-TYPE
    SYNTAX      InetAddressPrefixLength (0..128)
    MAX-ACCESS  read-write
    STATUS      current
    DESCRIPTION
        "The value of sbiStandbyAIPv6PfxLen specifies the prefix length of the
         subnet associated with the sbiStandbyAIPv6Addr address of the ethernet
         port on CPM A if CPM A is the standby CPM"
    DEFVAL      { 0 }
    ::= { sysBofInfo 58 }

sbiStandbyBIpAddr                OBJECT-TYPE
    SYNTAX      IpAddress
    MAX-ACCESS  read-write
    STATUS      current
    DESCRIPTION
        "The value of sbiStandbyBIpAddr specifies the IP address of the
         ethernet port on CPM B if CPM B is the standby CPM."
    DEFVAL      { 0 }
    ::= { sysBofInfo 59 }

sbiStandbyBIpMask                OBJECT-TYPE
    SYNTAX      IpAddressPrefixLength
    MAX-ACCESS  read-write
    STATUS      current
    DESCRIPTION
        "The value of sbiStandbyBIpMask specifies the mask length of the subnet
         associated with the IP address of the ethernet port on CPM B if CPM B
         is the standby CPM."
    DEFVAL      { 0 }
    ::= { sysBofInfo 60 }

sbiStandbyBIPv6Addr              OBJECT-TYPE
    SYNTAX      InetAddressIPv6
    MAX-ACCESS  read-write
    STATUS      current
    DESCRIPTION
        "The value of sbiStandbyBIPv6Addr specifies the IPv6 address of the
         ethernet port on CPM B if CPM B is the standby CPM"
    DEFVAL      { '00000000000000000000000000000000'H }
    ::= { sysBofInfo 61 }

sbiStandbyBIPv6PfxLen            OBJECT-TYPE
    SYNTAX      InetAddressPrefixLength (0..128)
    MAX-ACCESS  read-write
    STATUS      current
    DESCRIPTION
        "The value of sbiStandbyBIPv6PfxLen specifies the prefix length of the
         subnet associated with the sbiStandbyBIPv6Addr address of the ethernet
         port on CPM B if CPM B is the standby CPM"
    DEFVAL      { 0 }
    ::= { sysBofInfo 62 }

sbiStandbyCIpAddr                OBJECT-TYPE
    SYNTAX      IpAddress
    MAX-ACCESS  read-write
    STATUS      current
    DESCRIPTION
        "The value of sbiStandbyCIpAddr specifies the IP address of the
         ethernet port on CPM C if CPM C is the standby CPM."
    DEFVAL      { 0 }
    ::= { sysBofInfo 63 }

sbiStandbyCIpMask                OBJECT-TYPE
    SYNTAX      IpAddressPrefixLength
    MAX-ACCESS  read-write
    STATUS      current
    DESCRIPTION
        "The value of sbiStandbyCIpMask specifies the mask length of the subnet
         associated with the IP address of the ethernet port on CPM C if CPM C
         is the standby CPM."
    DEFVAL      { 0 }
    ::= { sysBofInfo 64 }

sbiStandbyCIPv6Addr              OBJECT-TYPE
    SYNTAX      InetAddressIPv6
    MAX-ACCESS  read-write
    STATUS      current
    DESCRIPTION
        "The value of sbiStandbyCIPv6Addr specifies the IPv6 address of the
         ethernet port on CPM C if CPM C is the standby CPM"
    DEFVAL      { '00000000000000000000000000000000'H }
    ::= { sysBofInfo 65 }

sbiStandbyCIPv6PfxLen            OBJECT-TYPE
    SYNTAX      InetAddressPrefixLength (0..128)
    MAX-ACCESS  read-write
    STATUS      current
    DESCRIPTION
        "The value of sbiStandbyCIPv6PfxLen specifies the prefix length of the
         subnet associated with the sbiStandbyCIPv6Addr address of the ethernet
         port on CPM C if CPM C is the standby CPM"
    DEFVAL      { 0 }
    ::= { sysBofInfo 66 }

sbiStandbyDIpAddr                OBJECT-TYPE
    SYNTAX      IpAddress
    MAX-ACCESS  read-write
    STATUS      current
    DESCRIPTION
        "The value of sbiStandbyDIpAddr specifies the IP address of the
         ethernet port on CPM D if CPM D is the standby CPM."
    DEFVAL      { 0 }
    ::= { sysBofInfo 67 }

sbiStandbyDIpMask                OBJECT-TYPE
    SYNTAX      IpAddressPrefixLength
    MAX-ACCESS  read-write
    STATUS      current
    DESCRIPTION
        "The value of sbiStandbyDIpMask specifies the mask length of the subnet
         associated with the IP address of the ethernet port on CPM D if CPM D
         is the standby CPM."
    DEFVAL      { 0 }
    ::= { sysBofInfo 68 }

sbiStandbyDIPv6Addr              OBJECT-TYPE
    SYNTAX      InetAddressIPv6
    MAX-ACCESS  read-write
    STATUS      current
    DESCRIPTION
        "The value of sbiStandbyDIPv6Addr specifies the IPv6 address of the
         ethernet port on CPM D if CPM D is the standby CPM"
    DEFVAL      { '00000000000000000000000000000000'H }
    ::= { sysBofInfo 69 }

sbiStandbyDIPv6PfxLen            OBJECT-TYPE
    SYNTAX      InetAddressPrefixLength (0..128)
    MAX-ACCESS  read-write
    STATUS      current
    DESCRIPTION
        "The value of sbiStandbyDIPv6PfxLen specifies the prefix length of the
         subnet associated with the sbiStandbyDIPv6Addr address of the ethernet
         port on CPM D if CPM D is the standby CPM"
    DEFVAL      { 0 }
    ::= { sysBofInfo 70 }

sbiMgmtIfIpMtu                   OBJECT-TYPE
    SYNTAX      Unsigned32 (0 | 512..9786)
    UNITS       "bytes"
    MAX-ACCESS  read-write
    STATUS      current
    DESCRIPTION
        "The value of sbiMgmtIfIpMtu is used to reflect configures the
         IP maximum transmit unit (packet)  for the management router
         instance. The configured IP-MTU cannot be larger than
         the calculated IP MTU based on the port MTU configuration.

         When a SNMP SET request is received with a value of zero (0), the
         agent actually sets vRtrIfMtu to the calculated default size."
    DEFVAL      { 0 }
    ::= { sysBofInfo 71 }

sysPersistenceInfo               OBJECT IDENTIFIER ::= { tmnxSysObjs 12 }

sysPersistenceDhcpL2Info         OBJECT IDENTIFIER ::= { sysPersistenceInfo 1 }

spiDhcpL2PersistenceFileLocation OBJECT-TYPE
    SYNTAX      Unsigned32 (0..32)
    MAX-ACCESS  read-write
    STATUS      obsolete
    DESCRIPTION
        "The value of spiDhcpL2PersistenceFileLocation specifies the flash
         device on a CPM card where the data for handling DHCP Layer2
         persistency is stored. The value 0 indicates that no flash device is
         specified.

         This object was made obsolete in the 5.0 release."
    DEFVAL      { 0 }
    ::= { sysPersistenceDhcpL2Info 1 }

spiDhcpL2PersistenceDescription  OBJECT-TYPE
    SYNTAX      TItemDescription
    MAX-ACCESS  read-write
    STATUS      obsolete
    DESCRIPTION
        "The value of the object spiDhcpL2PersistenceDescription specifies a
         user provided description related to DHCP Layer-2 persistency. It
         consists of any printable, seven-bit ASCII characters up to 80
         characters in length.

         This object was made obsolete in the 5.0 release."
    DEFVAL      { "" }
    ::= { sysPersistenceDhcpL2Info 2 }

sysPersistenceDhcpL3Info         OBJECT IDENTIFIER ::= { sysPersistenceInfo 2 }

spiDhcpL3PersistenceFileLocation OBJECT-TYPE
    SYNTAX      Unsigned32 (0..32)
    MAX-ACCESS  read-write
    STATUS      obsolete
    DESCRIPTION
        "The value of spiDhcpL3PersistenceFileLocation specifies the flash
         device on a CPM card where the data for handling DHCP Layer3
         persistency is stored. The value 0 indicates that no flash device is
         specified.

         This object was made obsolete in the 5.0 release."
    DEFVAL      { 0 }
    ::= { sysPersistenceDhcpL3Info 1 }

spiDhcpL3PersistenceDescription  OBJECT-TYPE
    SYNTAX      TItemDescription
    MAX-ACCESS  read-write
    STATUS      obsolete
    DESCRIPTION
        "The value of the object spiDhcpL3PersistenceDescription specifies a
         user provided description related to DHCP Layer-3 persistency. It
         consists of any printable, seven-bit ASCII characters up to 80
         characters in length.

         This object was made obsolete in the 5.0 release."
    DEFVAL      { "" }
    ::= { sysPersistenceDhcpL3Info 2 }

sysPersistenceSubMgmtInfo        OBJECT IDENTIFIER ::= { sysPersistenceInfo 3 }

spiSubMgmtPersistenceFileLocation OBJECT-TYPE
    SYNTAX      Unsigned32 (0..32)
    MAX-ACCESS  read-write
    STATUS      current
    DESCRIPTION
        "The value of spiSubMgmtPersistenceFileLocation specifies the flash
         device on a CPM card where the data for handling subscriber management
         persistency is stored. The value 0 indicates that no flash device is
         specified."
    DEFVAL      { 0 }
    ::= { sysPersistenceSubMgmtInfo 1 }

spiSubMgmtPersistenceDescription OBJECT-TYPE
    SYNTAX      TItemDescription
    MAX-ACCESS  read-write
    STATUS      current
    DESCRIPTION
        "The value of the object spiSubMgmtPersistenceDescription specifies a
         user provided description related to subscriber management
         persistency. It consists of any printable, seven-bit ASCII characters
         up to 80 characters in length."
    DEFVAL      { "" }
    ::= { sysPersistenceSubMgmtInfo 2 }

sysPersistenceDhcpSrvInfo        OBJECT IDENTIFIER ::= { sysPersistenceInfo 4 }

spiDhcpSrvPersistenceFileLoc     OBJECT-TYPE
    SYNTAX      Unsigned32 (0..32)
    MAX-ACCESS  read-write
    STATUS      current
    DESCRIPTION
        "The value of spiDhcpSrvPersistenceFileLoc specifies the flash device
         on a CPM card where the data for handling the local DHCP server
         persistency is stored. The value 0 indicates that no flash device is
         specified."
    DEFVAL      { 0 }
    ::= { sysPersistenceDhcpSrvInfo 1 }

spiDhcpSrvPersistenceDescr       OBJECT-TYPE
    SYNTAX      TItemDescription
    MAX-ACCESS  read-write
    STATUS      current
    DESCRIPTION
        "The value of the object spiDhcpSrvPersistenceDescr specifies a user
         provided description related to the local DHCP server persistency. It
         consists of any printable, seven-bit ASCII characters up to 80
         characters in length."
    DEFVAL      { "" }
    ::= { sysPersistenceDhcpSrvInfo 2 }

sysPersistenceNatInfo            OBJECT IDENTIFIER ::= { sysPersistenceInfo 5 }

spiNatFwdPersistenceFileLoc      OBJECT-TYPE
    SYNTAX      Unsigned32 (0..32)
    MAX-ACCESS  read-write
    STATUS      current
    DESCRIPTION
        "The value of spiNatFwdPersistenceFileLoc specifies the flash device on
         a CPM card where the data for handling the NAT (Network Address
         Translation) port forwarding persistence is stored.

         The value 0 indicates that no flash device is specified."
    DEFVAL      { 0 }
    ::= { sysPersistenceNatInfo 1 }

spiNatFwdPersistenceDescr        OBJECT-TYPE
    SYNTAX      TItemDescription
    MAX-ACCESS  read-write
    STATUS      current
    DESCRIPTION
        "The value of the object spiNatFwdPersistenceDescr specifies a user
         provided description related to the NAT port forwarding persistence.
         It consists of any printable, seven-bit ASCII characters up to 80
         characters in length."
    DEFVAL      { "" }
    ::= { sysPersistenceNatInfo 2 }

sysPersistenceAAInfo             OBJECT IDENTIFIER ::= { sysPersistenceInfo 6 }

spiAAPersistenceFileLoc          OBJECT-TYPE
    SYNTAX      Unsigned32 (0..32)
    MAX-ACCESS  read-write
    STATUS      current
    DESCRIPTION
        "The value of spiAAPersistenceFileLoc specifies the flash device on a
         CPM card where the data for handling the AA (Application Assurance)
         persistence is stored.

         The value 0 indicates that no flash device is specified."
    DEFVAL      { 0 }
    ::= { sysPersistenceAAInfo 1 }

spiAAPersistenceDescr            OBJECT-TYPE
    SYNTAX      TItemDescription
    MAX-ACCESS  read-write
    STATUS      current
    DESCRIPTION
        "The value of the object spiAAPersistenceDescr specifies a user
         provided description related to the AA (Application Assurance)
         persistence. It consists of any printable, seven-bit ASCII characters
         up to 80 characters in length."
    DEFVAL      { "" }
    ::= { sysPersistenceAAInfo 2 }

sysPersistenceAncpInfo           OBJECT IDENTIFIER ::= { sysPersistenceInfo 7 }

spiAncpPersistenceFileLoc        OBJECT-TYPE
    SYNTAX      Unsigned32 (0..32)
    MAX-ACCESS  read-write
    STATUS      current
    DESCRIPTION
        "The value of spiAncpPersistenceFileLoc specifies the flash device on a
         CPM card where the data for handling the Ancp persistence is stored.

         The value 0 indicates that no flash device is specified."
    DEFVAL      { 0 }
    ::= { sysPersistenceAncpInfo 1 }

spiAncpPersistenceDescr          OBJECT-TYPE
    SYNTAX      TItemDescription
    MAX-ACCESS  read-write
    STATUS      current
    DESCRIPTION
        "The value of the object spiAncpPersistenceDescr specifies a user
         provided description related to the Ancp persistence. It consists of
         any printable, seven-bit ASCII characters up to 80 characters in
         length."
    DEFVAL      { "" }
    ::= { sysPersistenceAncpInfo 2 }

sysPersistencePythonInfo         OBJECT IDENTIFIER ::= { sysPersistenceInfo 8 }

spiPythonPersistenceFileLoc      OBJECT-TYPE
    SYNTAX      Unsigned32 (0..32)
    MAX-ACCESS  read-write
    STATUS      current
    DESCRIPTION
        "The value of spiPythonPersistenceFileLoc specifies the flash device on
         a CPM card where the data for handling the python persistence is
         stored.

         The value 0 indicates that no flash device is specified."
    DEFVAL      { 0 }
    ::= { sysPersistencePythonInfo 1 }

spiPythonPersistenceDescr        OBJECT-TYPE
    SYNTAX      TItemDescription
    MAX-ACCESS  read-write
    STATUS      current
    DESCRIPTION
        "The value of the object spiPythonPersistenceDescr specifies a user
         provided description related to the Python persistence. It consists of
         any printable, seven-bit ASCII characters up to 80 characters in
         length."
    DEFVAL      { "" }
    ::= { sysPersistencePythonInfo 2 }

tmnxDhcpLeaseTimeModeThreshold   OBJECT-TYPE
    SYNTAX      Unsigned32 (0..631152000)
    UNITS       "seconds"
    MAX-ACCESS  read-create
    STATUS      current
    DESCRIPTION
        "The value of tmnxDhcpLeaseTimeModeThreshold specifies the threshold
         time for DHCP leases to be eligible for persistence in the 'lease time
         mode' of operation.

         Normally, the expiry time of a DHCP lease is stored in the persistent
         database; in 'lease time mode', however, the full lease time is
         stored; the resource usage penalty is reasonably small for leases with
         sufficiently short lease times.

         DHCP leases with a lease time greater than the value of
         tmnxDhcpLeaseTimeModeThreshold have their expiry time stored as usual.

         DHCP leases with a lease time smaller than or equal to the value of
         tmnxDhcpLeaseTimeModeThreshold have their full lease time stored."
    DEFVAL      { 0 }
    ::= { sysPersistenceInfo 20 }

sysLiInfo                        OBJECT IDENTIFIER ::= { tmnxSysObjs 13 }

sliConfigStatus                  OBJECT-TYPE
    SYNTAX      INTEGER {
        notRun  (0),
        success (1),
        fail    (2)
    }
    MAX-ACCESS  read-only
    STATUS      current
    DESCRIPTION
        "The value of sliConfigStatus indicates the results of restoring the
         Lawful Intercept (LI) configuration at boot-up time."
    ::= { sysLiInfo 1 }

sliSaveConfig                    OBJECT-TYPE
    SYNTAX      TmnxActionType
    MAX-ACCESS  read-write
    STATUS      current
    DESCRIPTION
        "The value of sliSaveConfig specifies a desired action.  Setting
         this action variable to 'doAction' causes the current Lawful
         Intercept (LI) running configuration information, to be saved to
         a file called li.cfg in the same location as the BOF file.
         If the li.cfg file already exists, it will be renamed and a
         new file is created with the current running configuration.

         An attempt to set this object to 'doAction' when the booted value of
         sbiLiLocalSave is 'false' will result in an 'inconsistentValue' error.

         Default configuration values will be included in the saved
         configuration information."
    DEFVAL      { notApplicable }
    ::= { sysLiInfo 2 }

sliSaveConfigResult              OBJECT-TYPE
    SYNTAX      INTEGER {
        none       (1),
        inProgress (2),
        success    (3),
        failed     (4)
    }
    MAX-ACCESS  read-only
    STATUS      current
    DESCRIPTION
        "The value of sliSaveConfigResult represents the result of the
         last sliSaveConfig action.
         none(1)            None of the following apply
         inProgress(2)      The action is still in progress
         success(3)         The action completed successfully
         failed(4)          The action failed"
    ::= { sysLiInfo 3 }

sliConfigLastModified            OBJECT-TYPE
    SYNTAX      DateAndTime
    MAX-ACCESS  read-only
    STATUS      current
    DESCRIPTION
        "The value of sliConfigLastModified indicates the date and time the
         Lawful Intercept (LI) running configuration was last modified. If
         sliConfigLastModified is more recent than TIMETRA-CHASSIS-MIB::
         tmnxHwSwLastBoot, the current configuration may be different than that
         in the configuration file read upon system initialization."
    ::= { sysLiInfo 4 }

sliConfigLastSaved               OBJECT-TYPE
    SYNTAX      DateAndTime
    MAX-ACCESS  read-only
    STATUS      current
    DESCRIPTION
        "The value of sliConfigLastSaved indicates the date and
         time the current Lawful Intercept (LI) configuration was
         last saved.  If sliConfigLastSaved is more recent than the
         value of TIMETRA-CHASSIS-MIB::tmnxHwSwLastBoot, the
         initial configuration is likely to be different the next
         time the system is rebooted."
    ::= { sysLiInfo 5 }

sliFilterLock                    OBJECT-TYPE
    SYNTAX      INTEGER {
        locked             (0),
        unlockedForLiUsers (1),
        unlockedForAll     (2)
    }
    MAX-ACCESS  read-write
    STATUS      current
    DESCRIPTION
        "The of sliFilterLock specifies who can modify the Lawful Intercept
         (LI) filters.

         The value:
         'locked':             no users can modify the LI filters
         'unlockedForLiUsers': only users with LI privileges can modify the
                               LI filters
         'unlockedForAll':     all users can modify the LI filters."
    DEFVAL      { locked }
    ::= { sysLiInfo 6 }

sysDNSInfo                       OBJECT IDENTIFIER ::= { tmnxSysObjs 14 }

sysDNSInfoLastChanged            OBJECT-TYPE
    SYNTAX      TimeStamp
    MAX-ACCESS  read-only
    STATUS      current
    DESCRIPTION
        "The value of sysDNSInfoLastChanged is the timestamp of the last
         configuration changes to any of the DNS global settings."
    ::= { sysDNSInfo 1 }

sysDNSAddressResolvePref         OBJECT-TYPE
    SYNTAX      INTEGER {
        ipv4Only  (1),
        ipv6First (2)
    }
    MAX-ACCESS  read-write
    STATUS      current
    DESCRIPTION
        "The value of sysDNSAddressResolvePref specifies how the DNS client
         will request for address resolution.

         ipv4-only:  The DNS client will only try to resolve a domain name
                     into an ipv4 address.

         ipv6-first: the DNS client will first try to resolve the
                     domain name in to ipv6 address. If no ipv6 address
                     is available it will try to resolve the domain name
                     into an ipv4 address."
    DEFVAL      { ipv4Only }
    ::= { sysDNSInfo 2 }

sysDNSSecAdValidation            OBJECT-TYPE
    SYNTAX      TruthValue
    MAX-ACCESS  read-write
    STATUS      current
    DESCRIPTION
        "The value of sysDNSSecAdValidation specifies whether or not the
         presence of the Authenticated Data (AD) bit in responses is validated
         from the DNS servers.

         When sysDNSSecAdValidation is set to 'true (1)', DNSSEC validation is
         enabled and a warning is reported to the SECURITY log if the AD-bit is
         not set in responses from the DNS servers. The notification
         responsible for the warning is sysDNSSecFailedAuthentication.

         When sysDNSSecAdValidation is set to 'false (2)', DNSSEC validation of
         the AD-bit is disabled."
    DEFVAL      { false }
    ::= { sysDNSInfo 3 }

sysDNSSecRespCtrl                OBJECT-TYPE
    SYNTAX      INTEGER {
        fallThrough (1),
        drop        (2)
    }
    MAX-ACCESS  read-write
    STATUS      current
    DESCRIPTION
        "The value of sysDNSSecRespCtrl specifies whether the system will
         permit or reject DNS responses that do not pass DNSSEC validation. The
         value of this object is ignored if sysDNSSecAdValidation is set to
         'false (2)'.

         When sysDNSSecRespCtrl is set to 'fallThrough (1)', the system will
         permit DNS responses that do not pass DNSSEC validation, allowing the
         resolution to complete.

         When sysDNSSecRespCtrl is set to 'drop (2)', the system will reject
         DNS responses that do not pass DNSSEC validation, and the resolution
         will appear to fail."
    DEFVAL      { drop }
    ::= { sysDNSInfo 4 }

sysIcmpVSInfo                    OBJECT IDENTIFIER ::= { tmnxSysObjs 15 }

sysIcmpVSEnhancement             OBJECT-TYPE
    SYNTAX      TmnxEnabledDisabled
    MAX-ACCESS  read-write
    STATUS      current
    DESCRIPTION
        "The value of sysIcmpVSEnhancement specifies if vendor specific
         extensions to ICMP is enabled or not."
    DEFVAL      { disabled }
    ::= { sysIcmpVSInfo 1 }

sysEthInfo                       OBJECT IDENTIFIER ::= { tmnxSysObjs 16 }

sysNewQinqUntaggedSap            OBJECT-TYPE
    SYNTAX      TruthValue
    MAX-ACCESS  read-write
    STATUS      current
    DESCRIPTION
        "The value of sysNewQinqUntaggedSap controls the forwarding of packets
         on a QinQ X.0 access SAP.

         When sysNewQinqUntaggedSap is set to true, the SAP will only accept:

         - frames with a single tag matching the SAP's outer tag or,
         - frames with double tag where the outer tag matches the SAP's outer
           tag and inner tag is set to 0.

         When sysNewQinqUntaggedSap is set to false, forwarding of packets
         remains unchanged."
    DEFVAL      { false }
    ::= { sysEthInfo 1 }

tmnxSysRollbackInfo              OBJECT IDENTIFIER ::= { tmnxSysObjs 17 }

tmnxSysRollbackIndex             OBJECT-TYPE
    SYNTAX      Unsigned32 (0..199)
    MAX-ACCESS  read-write
    STATUS      current
    DESCRIPTION
        "The value of tmnxSysRollbackIndex specifies a specific rollback
         checkpoint file to which a rollback action can be taken.

         The value of the tmnxSysRollbackIndex corresponds to a rollback
         checkpoint file with suffix .rb.index.

         The maximum checkpoint file that can be specified is determined by the
         rollback location as specified by tmnxSysRollbackLocation. If the
         location is on a compact flash, then the maximum value of
         tmnxSysRollbackIndex can be tmnxSysRollbackMaxLocalFiles minus 1. If
         the location is a remote ftp location, then the maximum value of
         tmnxSysRollbackIndex can be tmnxSysRollbackMaxRemoteFiles minus 1.

         This index is SET along with another action object, including
         tmnxSysRollbackStart to initiate a rollback revert of a file and
         tmnxSysRollbackFileDelete to delete a rollback file.

         An SNMP GET request on this object should return the last SET value."
    ::= { tmnxSysRollbackInfo 1 }

tmnxSysRollbackStart             OBJECT-TYPE
    SYNTAX      TmnxActionType
    MAX-ACCESS  read-write
    STATUS      current
    DESCRIPTION
        "The value of tmnxSysRollbackStart specifies whether to revert the
         rollback file specified by tmnxSysRollbackIndex.

         When SET to the value of 'doAction' the system will revert the
         rollback file specified by tmnxSysRollbackIndex.

         This variable must be set along with tmnxSysRollbackIndex to indicate
         the specific rollback file to revert.

         An SNMP GET request on this object should return 'notApplicable'."
    DEFVAL      { notApplicable }
    ::= { tmnxSysRollbackInfo 2 }

tmnxSysRollbackResult            OBJECT-TYPE
    SYNTAX      INTEGER {
        none        (1),
        inProgress  (2),
        success     (3),
        failed      (4),
        interrupted (5)
    }
    MAX-ACCESS  read-only
    STATUS      current
    DESCRIPTION
        "The value of tmnxSysRollbackResult indicates the result of the last
         tmnxSysRollbackStart action.

         none(1)            None of the following apply
         inProgress(2)      The action is still in progress
         success(3)         The action completed successfully
         failed(4)          The action failed
         interrupted (5)    The action was interrupted"
    ::= { tmnxSysRollbackInfo 3 }

tmnxSysRollbackSave              OBJECT-TYPE
    SYNTAX      TmnxActionType
    MAX-ACCESS  read-write
    STATUS      current
    DESCRIPTION
        "The value of tmnxSysRollbackSave specifies whether to save the
         existing configuration in a rollback checkpoint file.

         When SET to the value of 'doAction' the system will save the
         configuration in a new rollback checkpoint file, with suffix '.rb'.
         Previously saved rollback files with the same name will increment the
         filename suffix by 1 up to a maximum of 9. For example, file.rb is
         moved to file.rb.1. The higher the number, the older the file is.

         An SNMP GET request on this object should return 'notApplicable'."
    DEFVAL      { notApplicable }
    ::= { tmnxSysRollbackInfo 4 }

tmnxSysRollbackSaveResult        OBJECT-TYPE
    SYNTAX      INTEGER {
        none       (1),
        inProgress (2),
        success    (3),
        failed     (4)
    }
    MAX-ACCESS  read-only
    STATUS      current
    DESCRIPTION
        "The value of tmnxSysRollbackSaveResult indicates the result of the
         last tmnxSysRollbackSave action.

         none(1)            None of the following apply
         inProgress(2)      The action is still in progress
         success(3)         The action completed successfully
         failed(4)          The action failed"
    ::= { tmnxSysRollbackInfo 5 }

tmnxSysRollbackLocation          OBJECT-TYPE
    SYNTAX      TmnxDisplayStringURL
    MAX-ACCESS  read-write
    STATUS      current
    DESCRIPTION
        "The value of tmnxSysRollbackLocation specifies the destination filepath
         or file-URL where the current running configuration information
         will be saved when tmnxSysRollbackSave is set to 'doAction'.  If
         the value of tmnxSysRollbackLocation is an empty string the system will
         attempt to store the file in the best available location locally,
         for example compact flash 1 or 2 if either is present."
    DEFVAL      { ''H }
    ::= { tmnxSysRollbackInfo 6 }

tmnxSysRollbackRevertIndex       OBJECT-TYPE
    SYNTAX      Unsigned32 (0..199)
    MAX-ACCESS  read-only
    STATUS      current
    DESCRIPTION
        "The value of tmnxSysRollbackRevertIndex indicates the last rollback
         checkpoint file reverted on the system."
    ::= { tmnxSysRollbackInfo 7 }

tmnxSysRollbackRevertEndTime     OBJECT-TYPE
    SYNTAX      DateAndTime
    MAX-ACCESS  read-only
    STATUS      current
    DESCRIPTION
        "The value of tmnxSysRollbackRevertEndTime indicates the timestamp the
         last rollback revert on the system is completed.

         The value of tmnxSysRollbackRevertEndTime is affected by the value of
         stiPreferLocalTime."
    ::= { tmnxSysRollbackInfo 8 }

tmnxSysRollbackSavedTime         OBJECT-TYPE
    SYNTAX      DateAndTime
    MAX-ACCESS  read-only
    STATUS      current
    DESCRIPTION
        "The value of tmnxSysRollbackSavedTime indicates the timestamp the last
         rollback save on the system is completed.

         The value of tmnxSysRollbackSavedTime is affected by the value of
         stiPreferLocalTime."
    ::= { tmnxSysRollbackInfo 9 }

tmnxSysRollbackRevertStartTime   OBJECT-TYPE
    SYNTAX      DateAndTime
    MAX-ACCESS  read-only
    STATUS      current
    DESCRIPTION
        "The value of tmnxSysRollbackRevertStartTime indicates the timestamp
         the last rollback file reverted on the system is initiated.

         The value of tmnxSysRollbackRevertStartTime is affected by the value
         of stiPreferLocalTime."
    ::= { tmnxSysRollbackInfo 10 }

tmnxSysRollbackRevertUserName    OBJECT-TYPE
    SYNTAX      TNamedItemOrEmpty
    MAX-ACCESS  read-only
    STATUS      current
    DESCRIPTION
        "The value of tmnxSysRollbackRevertUserName indicates the name of a
         system user who initiated the last rollback revert."
    DEFVAL      { ''H }
    ::= { tmnxSysRollbackInfo 11 }

tmnxSysRollbackRevertFilename    OBJECT-TYPE
    SYNTAX      TmnxDisplayStringURL
    MAX-ACCESS  read-only
    STATUS      current
    DESCRIPTION
        "The value of tmnxSysRollbackRevertFilename specifies the filepath or
         file-URL of the last reverted rollback file."
    DEFVAL      { ''H }
    ::= { tmnxSysRollbackInfo 12 }

tmnxSysRollbackSaveComment       OBJECT-TYPE
    SYNTAX      DisplayString (SIZE (0..255))
    MAX-ACCESS  read-write
    STATUS      current
    DESCRIPTION
        "The value of the object tmnxSysRollbackSaveComment specifies a user
         provided comment related to the rollback checkpoint file about to be
         saved.

         It consists of any printable, seven-bit ASCII characters up to 255
         characters in length."
    DEFVAL      { ''H }
    ::= { tmnxSysRollbackInfo 13 }

tmnxSysRollbackFileDelete        OBJECT-TYPE
    SYNTAX      TmnxActionType
    MAX-ACCESS  read-write
    STATUS      current
    DESCRIPTION
        "The value of tmnxSysRollbackFileDelete specifies whether to delete the
         rollback file specified by tmnxSysRollbackIndex.

         When SET to the value of 'doAction' the system will delete the
         rollback file specified by tmnxSysRollbackIndex.

         This variable must be set along with tmnxSysRollbackIndex to specify
         the specific rollback file to delete.

         An SNMP GET request on this object should return 'notApplicable'."
    DEFVAL      { notApplicable }
    ::= { tmnxSysRollbackInfo 14 }

tmnxSysRollbackFileDeleteResult  OBJECT-TYPE
    SYNTAX      INTEGER {
        none       (1),
        inProgress (2),
        success    (3),
        failed     (4)
    }
    MAX-ACCESS  read-only
    STATUS      current
    DESCRIPTION
        "The value of tmnxSysRollbackFileDeleteResult indicates the result of
         the last tmnxSysRollbackFileDelete action.

         none(1)            None of the following apply
         inProgress(2)      The action is still in progress
         success(3)         The action completed successfully
         failed(4)          The action failed"
    ::= { tmnxSysRollbackInfo 15 }

tmnxSysRollbackAbortRevert       OBJECT-TYPE
    SYNTAX      TmnxActionType
    MAX-ACCESS  read-write
    STATUS      current
    DESCRIPTION
        "The value of tmnxSysRollbackAbortRevert specifies whether to abort the
         rollback revert that's currently in progress.

         When SET to the value of 'doAction' the system will abort the active
         rollback revert. This will leave the system in an unknown state, so it
         should be used with care.

         An SNMP GET request on this object should return 'notApplicable'."
    DEFVAL      { notApplicable }
    ::= { tmnxSysRollbackInfo 16 }

tmnxSysRollbackRescueLocation    OBJECT-TYPE
    SYNTAX      TmnxDisplayStringURL
    MAX-ACCESS  read-write
    STATUS      current
    DESCRIPTION
        "The value of tmnxSysRollbackRescueLocation specifies the destination
         file path or file-URL where the rollback rescue configuration file
         will be saved.  If the value of tmnxSysRollbackRescueLocation is
         an empty string the system will attempt to store the file in the
         best available location locally, for example compact flash 1 or 2
         if either is present."
    DEFVAL      { ''H }
    ::= { tmnxSysRollbackInfo 17 }

tmnxSysRollbackRescueRevert      OBJECT-TYPE
    SYNTAX      TmnxActionType
    MAX-ACCESS  read-write
    STATUS      current
    DESCRIPTION
        "The value of tmnxSysRollbackRescueRevert specifies whether to revert
         the rollback rescue file located in tmnxSysRollbackRescueLocation.

         When SET to the value of 'doAction' the system will revert the
         rollback rescue file.

         An SNMP GET request on this object should return 'notApplicable'."
    DEFVAL      { notApplicable }
    ::= { tmnxSysRollbackInfo 18 }

tmnxSysRollbackRescueSave        OBJECT-TYPE
    SYNTAX      TmnxActionType
    MAX-ACCESS  read-write
    STATUS      current
    DESCRIPTION
        "The value of tmnxSysRollbackRescueSave specifies whether to save the
         existing configuration in the rollback rescue file located in
         tmnxSysRollbackRescueLocation.

         When SET to the value of 'doAction' the system will save the
         configuration to the rollback rescue file.

         An SNMP GET request on this object should return 'notApplicable'."
    DEFVAL      { notApplicable }
    ::= { tmnxSysRollbackInfo 19 }

tmnxSysRollbackRescueDelete      OBJECT-TYPE
    SYNTAX      TmnxActionType
    MAX-ACCESS  read-write
    STATUS      current
    DESCRIPTION
        "The value of tmnxSysRollbackRescueDelete specifies whether to delete
         the rollback rescue file located in tmnxSysRollbackRescueLocation.

         When SET to the value of 'doAction' the system will delete the
         rollback rescue file.

         An SNMP GET request on this object should return 'notApplicable'."
    DEFVAL      { notApplicable }
    ::= { tmnxSysRollbackInfo 20 }

tmnxSysRollbackRescueSaveRes     OBJECT-TYPE
    SYNTAX      INTEGER {
        none       (1),
        inProgress (2),
        success    (3),
        failed     (4)
    }
    MAX-ACCESS  read-only
    STATUS      current
    DESCRIPTION
        "The value of tmnxSysRollbackRescueSaveRes indicates the result of the
         last tmnxSysRollbackRescueSave action.

         none(1)            None of the following apply
         inProgress(2)      The action is still in progress
         success(3)         The action completed successfully
         failed(4)          The action failed"
    ::= { tmnxSysRollbackInfo 21 }

tmnxSysRollbackRescueRevertRes   OBJECT-TYPE
    SYNTAX      INTEGER {
        none        (1),
        inProgress  (2),
        success     (3),
        failed      (4),
        interrupted (5)
    }
    MAX-ACCESS  read-only
    STATUS      current
    DESCRIPTION
        "The value of tmnxSysRollbackRescueRevertRes indicates the result of
         the last tmnxSysRollbackRescueRevert action.

         none(1)            None of the following apply
         inProgress(2)      The action is still in progress
         success(3)         The action completed successfully
         failed(4)          The action failed
         interrupted (5)    The action was interrupted"
    ::= { tmnxSysRollbackInfo 22 }

tmnxSysRollbackRescueDeleteRes   OBJECT-TYPE
    SYNTAX      INTEGER {
        none       (1),
        inProgress (2),
        success    (3),
        failed     (4)
    }
    MAX-ACCESS  read-only
    STATUS      current
    DESCRIPTION
        "The value of tmnxSysRollbackRescueDeleteRes indicates the result of
         the last tmnxSysRollbackRescueDelete action.

         none(1)            None of the following apply
         inProgress(2)      The action is still in progress
         success(3)         The action completed successfully
         failed(4)          The action failed"
    ::= { tmnxSysRollbackInfo 23 }

tmnxSysRollbackRescueSavedTime   OBJECT-TYPE
    SYNTAX      DateAndTime
    MAX-ACCESS  read-only
    STATUS      current
    DESCRIPTION
        "The value of tmnxSysRollbackRescueSavedTime indicates the timestamp
         the last rollback rescue save on the system is completed.

         The value of tmnxSysRollbackRescueSavedTime is affected by the value
         of stiPreferLocalTime."
    ::= { tmnxSysRollbackInfo 24 }

tmnxSysRollbackRescueRevStTime   OBJECT-TYPE
    SYNTAX      DateAndTime
    MAX-ACCESS  read-only
    STATUS      current
    DESCRIPTION
        "The value of tmnxSysRollbackRescueRevStTime indicates the timestamp
         the last rescue rollback file reverted on the system is initiated.

         The value of tmnxSysRollbackRescueRevStTime is affected by the value
         of stiPreferLocalTime."
    ::= { tmnxSysRollbackInfo 25 }

tmnxSysRollbackRescueRevEdTime   OBJECT-TYPE
    SYNTAX      DateAndTime
    MAX-ACCESS  read-only
    STATUS      current
    DESCRIPTION
        "The value of tmnxSysRollbackRescueRevEdTime indicates the timestamp
         the last rollback rescue revert on the system is completed.

         The value of tmnxSysRollbackRescueRevEdTime is affected by the value
         of stiPreferLocalTime."
    ::= { tmnxSysRollbackInfo 26 }

tmnxSysRollbackRescueRevUser     OBJECT-TYPE
    SYNTAX      TNamedItemOrEmpty
    MAX-ACCESS  read-only
    STATUS      current
    DESCRIPTION
        "The value of tmnxSysRollbackRescueRevUser indicates the name of a
         system user who initiated the last rollback rescue revert."
    DEFVAL      { ''H }
    ::= { tmnxSysRollbackInfo 27 }

tmnxSysRollbackRescueSaveComment OBJECT-TYPE
    SYNTAX      DisplayString (SIZE (0..255))
    MAX-ACCESS  read-write
    STATUS      current
    DESCRIPTION
        "The value of the object tmnxSysRollbackRescueSaveComment specifies a
         user provided comment related to the rollback rescue file about to be
         saved.

         It consists of any printable, seven-bit ASCII characters up to 255
         characters in length."
    DEFVAL      { ''H }
    ::= { tmnxSysRollbackInfo 28 }

tmnxSysRollbackRescueAbortRevert OBJECT-TYPE
    SYNTAX      TmnxActionType
    MAX-ACCESS  read-write
    STATUS      current
    DESCRIPTION
        "The value of tmnxSysRollbackRescueAbortRevert specifies whether to
         abort the rescue revert that's currently in progress.

         When SET to the value of 'doAction' the system will abort the active
         rollback revert. This will leave the system in an unknown state, so it
         should be used with care.

         An SNMP GET request on this object should return 'notApplicable'."
    DEFVAL      { notApplicable }
    ::= { tmnxSysRollbackInfo 29 }

tmnxSysRollbackRescueFileExists  OBJECT-TYPE
    SYNTAX      TruthValue
    MAX-ACCESS  read-only
    STATUS      current
    DESCRIPTION
        "The value of tmnxSysRollbackRescueFileExists indicates whether a
         rollback rescue file specified by tmnxSysRollbackRescueLocation and
         suffix '.rc' is present.

         A value of 'true' indicates the file is present and a value of 'false'
         indicates the file is not present."
    DEFVAL      { false }
    ::= { tmnxSysRollbackInfo 30 }

tmnxSysRollbackMaxLocalFiles     OBJECT-TYPE
    SYNTAX      Unsigned32 (1..50)
    MAX-ACCESS  read-write
    STATUS      current
    DESCRIPTION
        "The value of tmnxSysRollbackMaxLocalFiles specifies the maximum number
         of rollback checkpoint files that can be saved locally on the compact
         flash."
    DEFVAL      { 10 }
    ::= { tmnxSysRollbackInfo 31 }

tmnxSysRollbackMaxRemoteFiles    OBJECT-TYPE
    SYNTAX      Unsigned32 (1..200)
    MAX-ACCESS  read-write
    STATUS      current
    DESCRIPTION
        "The value of tmnxSysRollbackMaxRemoteFiles specifies the maximum
         number of rollback checkpoint files that can be saved at a remote ftp
         location."
    DEFVAL      { 10 }
    ::= { tmnxSysRollbackInfo 32 }

tmnxSysRollbackTableLastChanged  OBJECT-TYPE
    SYNTAX      TimeStamp
    MAX-ACCESS  read-only
    STATUS      current
    DESCRIPTION
        "The value of tmnxSysRollbackTableLastChanged indicates the timestamp
         of the last configuration changes to any of the rows in
         tmnxSysRollbackFileTable."
    ::= { tmnxSysObjs 18 }

tmnxSysRollbackFileTable         OBJECT-TYPE
    SYNTAX      SEQUENCE OF TmnxSysRollbackFileEntry
    MAX-ACCESS  not-accessible
    STATUS      current
    DESCRIPTION
        "The table tmnxSysRollbackFileTable contains information pertaining to
         an entry for each rollback checkpoint file.

         If the configured rollback location as specified by
         tmnxSysRollbackLocation is on compact flash, this table can have up to
         a maximum of tmnxSysRollbackMaxLocalFiles.

         If the configured rollback location as specified by
         tmnxSysRollbackLocation is a remote ftp location, this table can have
         up to a maximum of tmnxSysRollbackMaxRemoteFiles."
    ::= { tmnxSysObjs 19 }

tmnxSysRollbackFileEntry         OBJECT-TYPE
    SYNTAX      TmnxSysRollbackFileEntry
    MAX-ACCESS  not-accessible
    STATUS      current
    DESCRIPTION
        "Each row entry contains information about a rollback checkpoint file."
    INDEX       { tmnxSysRollbackFileIndex }
    ::= { tmnxSysRollbackFileTable 1 }

TmnxSysRollbackFileEntry         ::= SEQUENCE
{
    tmnxSysRollbackFileIndex         Unsigned32,
    tmnxSysRollbackFileCreationTime  DateAndTime,
    tmnxSysRollbackFileComment       DisplayString,
    tmnxSysRollbackFileUserName      TNamedItem,
    tmnxSysRollbackFileVersion       DisplayString
}

tmnxSysRollbackFileIndex         OBJECT-TYPE
    SYNTAX      Unsigned32 (0..199)
    MAX-ACCESS  not-accessible
    STATUS      current
    DESCRIPTION
        "The value of tmnxSysRollbackFileIndex specifies the index of the
         rollback checkpoint file."
    ::= { tmnxSysRollbackFileEntry 1 }

tmnxSysRollbackFileCreationTime  OBJECT-TYPE
    SYNTAX      DateAndTime
    MAX-ACCESS  read-only
    STATUS      current
    DESCRIPTION
        "The value of tmnxSysRollbackFileCreationTime indicates the timestamp
         of the creation time of this row in tmnxSysRollbackFileTable.

         The value of tmnxSysRollbackFileCreationTime is affected by the value
         of stiPreferLocalTime."
    ::= { tmnxSysRollbackFileEntry 2 }

tmnxSysRollbackFileComment       OBJECT-TYPE
    SYNTAX      DisplayString (SIZE (0..255))
    MAX-ACCESS  read-only
    STATUS      current
    DESCRIPTION
        "The value of the object tmnxSysRollbackFileComment specifies a user
         provided comment related to a rollback checkpoint file.

         It consists of any printable, seven-bit ASCII characters up to 255
         characters in length."
    ::= { tmnxSysRollbackFileEntry 3 }

tmnxSysRollbackFileUserName      OBJECT-TYPE
    SYNTAX      TNamedItem
    MAX-ACCESS  read-only
    STATUS      current
    DESCRIPTION
        "The value of tmnxSysRollbackFileUserName indicates the name of a
         system user who saves this rollback file."
    ::= { tmnxSysRollbackFileEntry 4 }

tmnxSysRollbackFileVersion       OBJECT-TYPE
    SYNTAX      DisplayString (SIZE (0..32))
    MAX-ACCESS  read-only
    STATUS      current
    DESCRIPTION
        "The value of tmnxSysRollbackFileVersion indicates the version number
         of the software running on the system when the rollback file is saved."
    ::= { tmnxSysRollbackFileEntry 5 }

sysBootedBofInfo                 OBJECT IDENTIFIER ::= { tmnxSysObjs 20 }

sbbiLiSeparate                   OBJECT-TYPE
    SYNTAX      TruthValue
    MAX-ACCESS  read-only
    STATUS      current
    DESCRIPTION
        "This object gives the currently active (booted) value of li-separate.
         This value specifies whether or not a non-LI user has access to Lawful
         Intercept (LI) information. When sbbiLiSeparate has a value of 'true',
         a user who does not have the TIMETRA-SECURITY-MIB:: tmnxUserAccess
         'li' bit set will not be allowed to access CLI or SNMP objects in the
         'li' context."
    ::= { sysBootedBofInfo 1 }

sbbiLiLocalSave                  OBJECT-TYPE
    SYNTAX      TruthValue
    MAX-ACCESS  read-only
    STATUS      current
    DESCRIPTION
        "This object gives the currently active (booted) value of
         li-local-save. This value specifies whether or not Lawful Intercept
         (LI) configuration is allowed to be save to a local file."
    ::= { sysBootedBofInfo 2 }

sysMGMCSwitchOverInfo            OBJECT IDENTIFIER ::= { tmnxSysObjs 21 }

tmnxSysCandidateCfgInfo          OBJECT IDENTIFIER ::= { tmnxSysObjs 22 }

tmnxSysCandidateCfgState         OBJECT-TYPE
    SYNTAX      INTEGER {
        unmodified  (0),
        modified    (1),
        unconfirmed (2)
    }
    MAX-ACCESS  read-only
    STATUS      current
    DESCRIPTION
        "The value of tmnxSysCandidateCfgState indicates the current state of
         the global candidate config.

         A value of 'unmodified(0)' indicates nobody has entered the candidate
         config since boot or the last commit/discard. A value of 'modified(1)'
         indicates there are uncommitted changes in the candidate config. A
         value of 'unconfirmed(2)' indicates there are no uncommitted changes
         in the candidate config but the result of the last commit will be
         auto-reverted unless it is confirmed before the timeout expires."
    ::= { tmnxSysCandidateCfgInfo 1 }

tmnxSysCandidateCfgEditors       OBJECT-TYPE
    SYNTAX      Integer32
    MAX-ACCESS  read-only
    STATUS      current
    DESCRIPTION
        "The value of tmnxSysCandidateCfgEditors indicates the current amount
         of users that are editing or reading the candidate config."
    ::= { tmnxSysCandidateCfgInfo 2 }

tmnxSysCandidateCfgCommitState   OBJECT-TYPE
    SYNTAX      INTEGER {
        none               (0),
        in-progress        (1),
        success            (2),
        revert-pending     (3),
        failed             (4),
        revert-in-progress (5),
        reverted           (6),
        revert-failed      (7)
    }
    MAX-ACCESS  read-only
    STATUS      current
    DESCRIPTION
        "The value of tmnxSysCandidateCfgCommitState indicates the result of
         the last commit performed in the global candidate config.

          A value of 'none(0)' indicates there have been no commits since the
          last reboot of the node.
          A value of 'in-progress(1)' indicates the system is currently
          committing the candidate config.
          A value of 'success(2)' indicates the last commit finished
          successfully.
          A value of 'revert-pending(3)' indicates the last commit finished
          successfully but has not been confirmed yet, and will be auto-reverted
          if it is not confirmed before the time specified in
          tmnxSysCandidateCfgRevertTime.
          A value of 'failed(4)' indicates the last commit failed and has been
          undone.
          A value of 'revert-in-progress(5)' indicates the last commit finished
          successfully but was not confirmed in time and is currently being
          reverted.
          A value of 'reverted(6)' indicates the last commit finished
          successfully but was not confirmed in time and has been reverted.
          A value of 'revert-failed(7)' indicates the last commit finished
          successfully but was not confirmed in time and the system attempted to
          revert it but failed."
    ::= { tmnxSysCandidateCfgInfo 3 }

tmnxSysCandidateCfgCommitTime    OBJECT-TYPE
    SYNTAX      DateAndTime
    MAX-ACCESS  read-only
    STATUS      current
    DESCRIPTION
        "The value of tmnxSysCandidateCfgCommitTime indicates the date and time
         the last (attempted) commit of the candidate config was started."
    ::= { tmnxSysCandidateCfgInfo 4 }

tmnxSysCandidateCfgRevertTime    OBJECT-TYPE
    SYNTAX      DateAndTime
    MAX-ACCESS  read-only
    STATUS      current
    DESCRIPTION
        "The value of tmnxSysCandidateCfgRevertTime indicates the date and time
         the system will automatically revert the last committed candidate
         config, unless they are confirmed.

         If this date and time is in the past it indicates the candidate config
         was not confirmed and has been reverted.

         If no auto-revert was requested at the time of the commit the value of
         this field will be set to zero."
    ::= { tmnxSysCandidateCfgInfo 5 }

tmnxSysCandidateCfgChckptCreated OBJECT-TYPE
    SYNTAX      TruthValue
    MAX-ACCESS  read-only
    STATUS      current
    DESCRIPTION
        "The value of tmnxSysCandidateCfgChckptCreated indicates if a
         checkpoint was created after the last commit of the candidate config."
    ::= { tmnxSysCandidateCfgInfo 6 }

tmnxSysCandidateCfgUser          OBJECT-TYPE
    SYNTAX      TNamedItemOrEmpty
    MAX-ACCESS  read-only
    STATUS      current
    DESCRIPTION
        "The value of tmnxSysCandidateCfgUser indicates the name of a system
         user who initiated the last commit of the candidate config."
    ::= { tmnxSysCandidateCfgInfo 7 }

tmnxSysCandidateCfgExclusiveUsr  OBJECT-TYPE
    SYNTAX      TNamedItemOrEmpty
    MAX-ACCESS  read-only
    STATUS      current
    DESCRIPTION
        "The value of tmnxSysCandidateCfgExclusiveUsr indicates the name of a
         system user who is currently exclusively modifying the candidate
         config. This indicates no other user can modify the candidate config
         until this system user has finished modifying the candidate config.

         If this field is empty no user has requested to exclusively modify the
         candidate config."
    ::= { tmnxSysCandidateCfgInfo 8 }

tmnxSysNetconfInfo               OBJECT IDENTIFIER ::= { tmnxSysObjs 23 }

tmnxSysNetconfAdminStatus        OBJECT-TYPE
    SYNTAX      TmnxAdminState
    MAX-ACCESS  read-write
    STATUS      current
    DESCRIPTION
        "The value of tmnxSysNetconfAdminStatus specifies the desired
         administrative state of the NETCONF daemon. When
         tmnxSysNetconfAdminStatus is set to 'inService', the NETCONF daemon
         will begin receiving NETCONF requests from external NETCONF users.
         When tmnxSysNetconfAdminStatus is set to 'outOfService', the NETCONF
         daemon is suspended and will no longer receive NETCONF requests from
         external NETCONF users."
    DEFVAL      { outOfService }
    ::= { tmnxSysNetconfInfo 1 }

tmnxSysNetconfOperStatus         OBJECT-TYPE
    SYNTAX      TmnxOperState
    MAX-ACCESS  read-only
    STATUS      current
    DESCRIPTION
        "The value of tmnxSysNetconfOperStatus indicates the state of the
         NETCONF daemon. A value of 'inService' indicates that the NETCONF
         daemon will receive NETCONF requests from external NETCONF users. A
         value of 'outOfService' indicates that the NETCONF daemon is suspended
         and will no longer receive NETCONF requests from external NETCONF
         users."
    ::= { tmnxSysNetconfInfo 2 }

tmnxSysNetconfRequests           OBJECT-TYPE
    SYNTAX      Counter32
    MAX-ACCESS  read-only
    STATUS      current
    DESCRIPTION
        "The value of tmnxSysNetconfRequests indicates the total number of
         NETCONF requests which have been accepted and processed by the NETCONF
         server."
    ::= { tmnxSysNetconfInfo 3 }

tmnxSysNetconfGetRequests        OBJECT-TYPE
    SYNTAX      Counter32
    MAX-ACCESS  read-only
    STATUS      current
    DESCRIPTION
        "The value of tmnxSysNetconfGetRequests indicates the total number of
         get NETCONF requests which have been accepted and processed by the
         NETCONF server."
    ::= { tmnxSysNetconfInfo 4 }

tmnxSysNetconfGetConfigRequests  OBJECT-TYPE
    SYNTAX      Counter32
    MAX-ACCESS  read-only
    STATUS      current
    DESCRIPTION
        "The value of tmnxSysNetconfGetConfigRequests indicates the total
         number of get-config NETCONF requests which have been accepted and
         processed by the NETCONF server."
    ::= { tmnxSysNetconfInfo 5 }

tmnxSysNetconfEditConfigRequests OBJECT-TYPE
    SYNTAX      Counter32
    MAX-ACCESS  read-only
    STATUS      current
    DESCRIPTION
        "The value of tmnxSysNetconfEditConfigRequests indicates the total
         number of edit-config NETCONF requests which have been accepted and
         processed by the NETCONF server."
    ::= { tmnxSysNetconfInfo 6 }

tmnxSysNetconfCloseRequests      OBJECT-TYPE
    SYNTAX      Counter32
    MAX-ACCESS  read-only
    STATUS      current
    DESCRIPTION
        "The value of tmnxSysNetconfCloseRequests indicates the total number of
         close-session NETCONF requests which have been accepted and processed
         by the NETCONF server."
    ::= { tmnxSysNetconfInfo 7 }

tmnxSysNetconfKillRequests       OBJECT-TYPE
    SYNTAX      Counter32
    MAX-ACCESS  read-only
    STATUS      current
    DESCRIPTION
        "The value of tmnxSysNetconfKillRequests indicates the total number of
         kill-session NETCONF requests which have been accepted and processed
         by the NETCONF server."
    ::= { tmnxSysNetconfInfo 8 }

tmnxSysNetconfResponses          OBJECT-TYPE
    SYNTAX      Counter32
    MAX-ACCESS  read-only
    STATUS      current
    DESCRIPTION
        "The value of tmnxSysNetconfResponses indicates the total number of
         NETCONF responses which have been generated and sent by the NETCONF
         server."
    ::= { tmnxSysNetconfInfo 9 }

tmnxSysNetconfErrorResponses     OBJECT-TYPE
    SYNTAX      Counter32
    MAX-ACCESS  read-only
    STATUS      current
    DESCRIPTION
        "The value of tmnxSysNetconfErrorResponses indicates the total number
         of NETCONF error responses which have been generated and sent by the
         NETCONF server."
    ::= { tmnxSysNetconfInfo 10 }

tmnxSysNetconfCopyConfigRequests OBJECT-TYPE
    SYNTAX      Counter32
    MAX-ACCESS  read-only
    STATUS      current
    DESCRIPTION
        "The value of tmnxSysNetconfCopyConfigRequests indicates the total
         number of copy-config NETCONF requests which have been accepted and
         processed by the NETCONF server."
    ::= { tmnxSysNetconfInfo 11 }

tmnxSysNetconfDelConfigRequests  OBJECT-TYPE
    SYNTAX      Counter32
    MAX-ACCESS  read-only
    STATUS      current
    DESCRIPTION
        "The value of tmnxSysNetconfDelConfigRequests indicates the total
         number of delete-config NETCONF requests which have been accepted and
         processed by the NETCONF server."
    ::= { tmnxSysNetconfInfo 12 }

tmnxSysNetconfValidateRequests   OBJECT-TYPE
    SYNTAX      Counter32
    MAX-ACCESS  read-only
    STATUS      current
    DESCRIPTION
        "The value of tmnxSysNetconfValidateRequests indicates the total number
         of validate NETCONF requests which have been accepted and processed by
         the NETCONF server."
    ::= { tmnxSysNetconfInfo 13 }

tmnxSysNetconfFailedEditCfgReqs  OBJECT-TYPE
    SYNTAX      Counter32
    MAX-ACCESS  read-only
    STATUS      current
    DESCRIPTION
        "The value of tmnxSysNetconfFailedEditCfgReqs indicates the total
         number of edit-config NETCONF requests which have failed because of
         locks taken by other NETCONF sessions."
    ::= { tmnxSysNetconfInfo 14 }

tmnxSysNetconfFailedLockReqs     OBJECT-TYPE
    SYNTAX      Counter32
    MAX-ACCESS  read-only
    STATUS      current
    DESCRIPTION
        "The value of tmnxSysNetconfFailedLockReqs indicates the total number
         of lock NETCONF requests which have failed because of locks taken by
         other NETCONF sessions."
    ::= { tmnxSysNetconfInfo 15 }

tmnxSysNetconfLockRequests       OBJECT-TYPE
    SYNTAX      Counter32
    MAX-ACCESS  read-only
    STATUS      current
    DESCRIPTION
        "The value of tmnxSysNetconfLockRequests indicates the total number of
         lock NETCONF requests which have been accepted and processed by the
         NETCONF server."
    ::= { tmnxSysNetconfInfo 16 }

tmnxSysNetconfUnlockRequests     OBJECT-TYPE
    SYNTAX      Counter32
    MAX-ACCESS  read-only
    STATUS      current
    DESCRIPTION
        "The value of tmnxSysNetconfUnlockRequests indicates the total number
         of unlock NETCONF requests which have been accepted and processed by
         the NETCONF server."
    ::= { tmnxSysNetconfInfo 17 }

tmnxSysNetconfCommitRequests     OBJECT-TYPE
    SYNTAX      Counter32
    MAX-ACCESS  read-only
    STATUS      current
    DESCRIPTION
        "The value of tmnxSysNetconfCommitRequests indicates the total number
         of commit NETCONF requests which have been accepted and processed by
         the NETCONF server."
    ::= { tmnxSysNetconfInfo 18 }

tmnxSysNetconfDiscardRequests    OBJECT-TYPE
    SYNTAX      Counter32
    MAX-ACCESS  read-only
    STATUS      current
    DESCRIPTION
        "The value of tmnxSysNetconfDiscardRequests indicates the total number
         of discard change NETCONF requests which have been accepted and
         processed by the NETCONF server."
    ::= { tmnxSysNetconfInfo 19 }

tmnxSysNetconfCapCandidateCfg    OBJECT-TYPE
    SYNTAX      TruthValue
    MAX-ACCESS  read-write
    STATUS      current
    DESCRIPTION
        "The value of tmnxSysNetconfCapCandidateCfg specifies whether or not
         the candidate datastore is supported by the NETCONF server. When set
         to 'true', the NETCONF server allows access to the candidate
         datastore."
    DEFVAL      { true }
    ::= { tmnxSysNetconfInfo 20 }

tmnxSysNetconfCapRunningCfg      OBJECT-TYPE
    SYNTAX      TruthValue
    MAX-ACCESS  read-write
    STATUS      current
    DESCRIPTION
        "The value of tmnxSysNetconfCapRunningCfg specifies whether or not the
         writable running datastore is supported by the NETCONF server. When
         set to 'true', the NETCONF server allows access to the writable
         running datastore."
    DEFVAL      { false }
    ::= { tmnxSysNetconfInfo 21 }

tmnxSysNetconfYangBaseR13        OBJECT-TYPE
    SYNTAX      TruthValue
    MAX-ACCESS  read-write
    STATUS      obsolete
    DESCRIPTION
        "The value of tmnxSysNetconfYangBaseR13 specifies whether or not the
         base release 13 Yang models are supported by the NETCONF server. When
         set to 'true', the NETCONF server allows access to base release 13
         Yang models.

         This object was made obsolete in the 15.1 release."
    DEFVAL      { true }
    ::= { tmnxSysNetconfInfo 22 }

tmnxSysNetconfYangNokia          OBJECT-TYPE
    SYNTAX      TruthValue
    MAX-ACCESS  read-write
    STATUS      obsolete
    DESCRIPTION
        "The value of tmnxSysNetconfYangNokia specifies whether or not the
         Nokia Yang models are supported by the NETCONF server. When set to
         'true', the NETCONF server allows access to the Nokia Yang models.

         This object was made obsolete in the 15.1 release."
    DEFVAL      { true }
    ::= { tmnxSysNetconfInfo 23 }

tmnxSysNetconfCreateSubRequests  OBJECT-TYPE
    SYNTAX      Counter32
    MAX-ACCESS  read-only
    STATUS      current
    DESCRIPTION
        "The value of tmnxSysNetconfCreateSubRequests indicates the total
         number of create subscription NETCONF requests which have been
         accepted and processed by the NETCONF server."
    ::= { tmnxSysNetconfInfo 24 }

tmnxSysNetconfAutoCfgSave        OBJECT-TYPE
    SYNTAX      TruthValue
    MAX-ACCESS  read-write
    STATUS      current
    DESCRIPTION
        "The value of tmnxSysNetconfAutoCfgSave specifies whether the running
         configuration is saved as part of a commit operation initiated from
         Netconf."
    DEFVAL      { false }
    ::= { tmnxSysNetconfInfo 25 }

tmnxSysNetconfPort               OBJECT-TYPE
    SYNTAX      Unsigned32 (22 | 830)
    MAX-ACCESS  read-write
    STATUS      current
    DESCRIPTION
        "The value of tmnxSysNetconfPort specifies port on which is NETCONF
         server listening for connections."
    DEFVAL      { 830 }
    ::= { tmnxSysNetconfInfo 26 }

tmnxDCSysObjs                    OBJECT IDENTIFIER ::= { tmnxSysObjs 24 }

tmnxSysStrmInfo                  OBJECT IDENTIFIER ::= { tmnxSysObjs 25 }

tmnxSysStrmAdminStatus           OBJECT-TYPE
    SYNTAX      TmnxAdminState
    MAX-ACCESS  read-write
    STATUS      current
    DESCRIPTION
        "The value of tmnxSysStrmAdminStatus specifies the desired
         administrative state of the proprietary protocol streaming server
         daemon.  When tmnxSysStrmAdminStatus is set to 'inService', the
         streaming server daemon accepts and processes requests from the
         Nokia 5620 Service Aware Manager (SAM) system. When
         tmnxSysStrmAdminStatus is set to 'outOfService', the streaming server
         daemon is suspended and will no longer accept requests from the SAM
         system."
    DEFVAL      { outOfService }
    ::= { tmnxSysStrmInfo 1 }

tmnxSysStrmDumpSnmpRequests      OBJECT-TYPE
    SYNTAX      Counter32
    MAX-ACCESS  read-only
    STATUS      current
    DESCRIPTION
        "The value of tmnxSysStrmDumpSnmpRequests indicates the total number of
         streaming snmp dump request PDUs which have been accepted and
         processed by the Nokia 5620 Service Aware Manager (SAM) streaming
         protocol entity."
    ::= { tmnxSysStrmInfo 2 }

tmnxSysStrmGetManyRequests       OBJECT-TYPE
    SYNTAX      Counter32
    MAX-ACCESS  read-only
    STATUS      current
    DESCRIPTION
        "The value of tmnxSysStrmGetManyRequests indicates the total number of
         streaming get many request PDUs which have been accepted and processed
         by the Nokia 5620 Service Aware Manager (SAM) streaming protocol
         entity."
    ::= { tmnxSysStrmInfo 3 }

tmnxSysStrmResponses             OBJECT-TYPE
    SYNTAX      Counter32
    MAX-ACCESS  read-only
    STATUS      current
    DESCRIPTION
        "The value of tmnxSysStrmResponses indicates the total number of
         streaming response PDUs which have been generated by the Nokia 5620
         Service Aware Manager (SAM) streaming protocol entity."
    ::= { tmnxSysStrmInfo 4 }

tmnxSysXmppInfo                  OBJECT IDENTIFIER ::= { tmnxSysObjs 26 }

tmnxSysXmppServerTable           OBJECT-TYPE
    SYNTAX      SEQUENCE OF TmnxSysXmppServerEntry
    MAX-ACCESS  not-accessible
    STATUS      current
    DESCRIPTION
        "The tmnxSysXmppServerTable contains information pertaining to an entry
         for each server. Row entries are created and deleted by the agent."
    ::= { tmnxSysXmppInfo 1 }

tmnxSysXmppServerEntry           OBJECT-TYPE
    SYNTAX      TmnxSysXmppServerEntry
    MAX-ACCESS  not-accessible
    STATUS      current
    DESCRIPTION
        "Each row entry contains information about a XMPP server."
    INDEX       { tmnxSysXmppServName }
    ::= { tmnxSysXmppServerTable 1 }

TmnxSysXmppServerEntry           ::= SEQUENCE
{
    tmnxSysXmppServName              DisplayString,
    tmnxSysXmppServFQDN              DisplayString,
    tmnxSysXmppServRowStatus         RowStatus,
    tmnxSysXmppServUserName          TNamedItemOrEmpty,
    tmnxSysXmppServPassword          DisplayString,
    tmnxSysXmppServLastChanged       TimeStamp,
    tmnxSysXmppServUptime            TimeStamp,
    tmnxSysXmppServIQSent            Counter64,
    tmnxSysXmppServIQRcvd            Counter64,
    tmnxSysXmppServIQError           Counter64,
    tmnxSysXmppServIQTimedOut        Counter64,
    tmnxSysXmppServIQAckRcvd         Counter64,
    tmnxSysXmppServIQMinRtt          Counter64,
    tmnxSysXmppServIQMaxRtt          Counter64,
    tmnxSysXmppServVsdUpdatesRcvd    Counter64,
    tmnxSysXmppServUpdatesRcvd       Counter64,
    tmnxSysXmppServMsgSent           Counter64,
    tmnxSysXmppServMsgRcvd           Counter64,
    tmnxSysXmppServMsgAckRcvd        Counter64,
    tmnxSysXmppServMsgError          Counter64,
    tmnxSysXmppServMsgTimedOut       Counter64,
    tmnxSysXmppServMsgMinRtt         Counter64,
    tmnxSysXmppServMsgMaxRtt         Counter64,
    tmnxSysXmppServSubSent           Counter64,
    tmnxSysXmppServUnSubSent         Counter64,
    tmnxSysXmppServState             DisplayString,
    tmnxSysXmppServAdminState        TmnxAdminState,
    tmnxSysXmppServOperUserName      TNamedItemOrEmpty,
    tmnxSysXmppServAuthType          TNamedItemOrEmpty,
    tmnxSysXmppServConnMode          INTEGER,
    tmnxSysXmppServServiceId         TmnxServId,
    tmnxSysXmppServRouterId          TmnxVRtrIDOrZero
}

tmnxSysXmppServName              OBJECT-TYPE
    SYNTAX      DisplayString (SIZE (0..32))
    MAX-ACCESS  not-accessible
    STATUS      current
    DESCRIPTION
        "The value of tmnxSysXmppServName indicates the name associated with
         the XMPP Server."
    ::= { tmnxSysXmppServerEntry 1 }

tmnxSysXmppServFQDN              OBJECT-TYPE
    SYNTAX      DisplayString (SIZE (0..255))
    MAX-ACCESS  read-create
    STATUS      current
    DESCRIPTION
        "The value of tmnxSysXmppServFQDN specifies the Fully Qualified Domain
         Name (FQDN) associated with the XMPP Server."
    ::= { tmnxSysXmppServerEntry 2 }

tmnxSysXmppServRowStatus         OBJECT-TYPE
    SYNTAX      RowStatus
    MAX-ACCESS  read-create
    STATUS      current
    DESCRIPTION
        "The value of tmnxSysXmppServRowStatus specifies the row status. It is
         used to create and delete row entries in this table."
    ::= { tmnxSysXmppServerEntry 3 }

tmnxSysXmppServUserName          OBJECT-TYPE
    SYNTAX      TNamedItemOrEmpty
    MAX-ACCESS  read-create
    STATUS      current
    DESCRIPTION
        "The value of tmnxSysXmppServUserName specifies the username that
         is used in the XMPP server access requests. When no username is
         not provided,  the chassis MAC is used as the default user name."
    ::= { tmnxSysXmppServerEntry 4 }

tmnxSysXmppServPassword          OBJECT-TYPE
    SYNTAX      DisplayString (SIZE (0..32))
    MAX-ACCESS  read-create
    STATUS      current
    DESCRIPTION
        "The value of tmnxSysXmppServPassword specifies the password that is
         used in the XMPP server access requests."
    DEFVAL      { "" }
    ::= { tmnxSysXmppServerEntry 5 }

tmnxSysXmppServLastChanged       OBJECT-TYPE
    SYNTAX      TimeStamp
    MAX-ACCESS  read-only
    STATUS      current
    DESCRIPTION
        "The value of tmnxSysXmppServLastChanged indicates the timestamp of
         last change to this row in tmnxSysXmppServerTable."
    ::= { tmnxSysXmppServerEntry 6 }

tmnxSysXmppServUptime            OBJECT-TYPE
    SYNTAX      TimeStamp
    MAX-ACCESS  read-only
    STATUS      current
    DESCRIPTION
        "The tmnxSysXmppServUptime indicates the uptime of the XMPP server."
    ::= { tmnxSysXmppServerEntry 7 }

tmnxSysXmppServIQSent            OBJECT-TYPE
    SYNTAX      Counter64
    MAX-ACCESS  read-only
    STATUS      current
    DESCRIPTION
        "The value of tmnxSysXmppServIQSent indicates the number of XMPP
         Info/Query message sent."
    ::= { tmnxSysXmppServerEntry 8 }

tmnxSysXmppServIQRcvd            OBJECT-TYPE
    SYNTAX      Counter64
    MAX-ACCESS  read-only
    STATUS      current
    DESCRIPTION
        "The value of tmnxSysXmppServIQRcvd indicates the number of XMPP
         Info/Query message received."
    ::= { tmnxSysXmppServerEntry 9 }

tmnxSysXmppServIQError           OBJECT-TYPE
    SYNTAX      Counter64
    MAX-ACCESS  read-only
    STATUS      current
    DESCRIPTION
        "The value of tmnxSysXmppServIQError indicates the number of XMPP
         Info/Query error messages received."
    ::= { tmnxSysXmppServerEntry 10 }

tmnxSysXmppServIQTimedOut        OBJECT-TYPE
    SYNTAX      Counter64
    MAX-ACCESS  read-only
    STATUS      current
    DESCRIPTION
        "The value of tmnxSysXmppServIQTimedOut indicates the number of XMPP
         Info/Query messages timed out."
    ::= { tmnxSysXmppServerEntry 11 }

tmnxSysXmppServIQAckRcvd         OBJECT-TYPE
    SYNTAX      Counter64
    MAX-ACCESS  read-only
    STATUS      current
    DESCRIPTION
        "The value of tmnxSysXmppServIQAckRcvd indicates the number of XMPP
         Info/Query acknowledgement messages received."
    ::= { tmnxSysXmppServerEntry 12 }

tmnxSysXmppServIQMinRtt          OBJECT-TYPE
    SYNTAX      Counter64
    UNITS       "milliseconds"
    MAX-ACCESS  read-only
    STATUS      current
    DESCRIPTION
        "The value of tmnxSysXmppServIQMinRtt indicates the XMPP Info/Query
         minimum round trip time."
    ::= { tmnxSysXmppServerEntry 13 }

tmnxSysXmppServIQMaxRtt          OBJECT-TYPE
    SYNTAX      Counter64
    UNITS       "milliseconds"
    MAX-ACCESS  read-only
    STATUS      current
    DESCRIPTION
        "The value of tmnxSysXmppServIQMaxRtt indicates the XMPP Info/Query
         maximum round trip time."
    ::= { tmnxSysXmppServerEntry 14 }

tmnxSysXmppServVsdUpdatesRcvd    OBJECT-TYPE
    SYNTAX      Counter64
    MAX-ACCESS  read-only
    STATUS      current
    DESCRIPTION
        "The value of tmnxSysXmppServVsdUpdatesRcvd indicates the number of VSD
         updates received by the XMPP server."
    ::= { tmnxSysXmppServerEntry 15 }

tmnxSysXmppServUpdatesRcvd       OBJECT-TYPE
    SYNTAX      Counter64
    MAX-ACCESS  read-only
    STATUS      current
    DESCRIPTION
        "The value of tmnxSysXmppServUpdatesRcvd indicates the number of nuage
         updates received by the XMPP server."
    ::= { tmnxSysXmppServerEntry 16 }

tmnxSysXmppServMsgSent           OBJECT-TYPE
    SYNTAX      Counter64
    MAX-ACCESS  read-only
    STATUS      current
    DESCRIPTION
        "The value of tmnxSysXmppServMsgSent indicates the number of messages
         sent from the XMPP server."
    ::= { tmnxSysXmppServerEntry 17 }

tmnxSysXmppServMsgRcvd           OBJECT-TYPE
    SYNTAX      Counter64
    MAX-ACCESS  read-only
    STATUS      current
    DESCRIPTION
        "The value of tmnxSysXmppServMsgRcvd indicates the number of messages
         received from the XMPP server."
    ::= { tmnxSysXmppServerEntry 18 }

tmnxSysXmppServMsgAckRcvd        OBJECT-TYPE
    SYNTAX      Counter64
    MAX-ACCESS  read-only
    STATUS      current
    DESCRIPTION
        "The value of tmnxSysXmppServMsgAckRcvd indicates the number of message
         acknowledgements received from the XMPP server."
    ::= { tmnxSysXmppServerEntry 19 }

tmnxSysXmppServMsgError          OBJECT-TYPE
    SYNTAX      Counter64
    MAX-ACCESS  read-only
    STATUS      current
    DESCRIPTION
        "The value of tmnxSysXmppServMsgError indicates the number of error
         messages received from the XMPP server."
    ::= { tmnxSysXmppServerEntry 20 }

tmnxSysXmppServMsgTimedOut       OBJECT-TYPE
    SYNTAX      Counter64
    MAX-ACCESS  read-only
    STATUS      current
    DESCRIPTION
        "The value of tmnxSysXmppServMsgTimedOut indicates the number of
         timeout messages received from the XMPP server."
    ::= { tmnxSysXmppServerEntry 21 }

tmnxSysXmppServMsgMinRtt         OBJECT-TYPE
    SYNTAX      Counter64
    UNITS       "milliseconds"
    MAX-ACCESS  read-only
    STATUS      current
    DESCRIPTION
        "The value of tmnxSysXmppServMsgMinRtt indicates the minimum message
         round trip time from the XMPP server."
    ::= { tmnxSysXmppServerEntry 22 }

tmnxSysXmppServMsgMaxRtt         OBJECT-TYPE
    SYNTAX      Counter64
    UNITS       "milliseconds"
    MAX-ACCESS  read-only
    STATUS      current
    DESCRIPTION
        "The value of tmnxSysXmppServMsgMaxRtt indicates the maximum message
         round trip time from the XMPP server."
    ::= { tmnxSysXmppServerEntry 23 }

tmnxSysXmppServSubSent           OBJECT-TYPE
    SYNTAX      Counter64
    MAX-ACCESS  read-only
    STATUS      current
    DESCRIPTION
        "The value of tmnxSysXmppServSubSent indicates the number of
         subscriptions sent from the XMPP server."
    ::= { tmnxSysXmppServerEntry 24 }

tmnxSysXmppServUnSubSent         OBJECT-TYPE
    SYNTAX      Counter64
    MAX-ACCESS  read-only
    STATUS      current
    DESCRIPTION
        "The value of tmnxSysXmppServUnSubSent indicates the number of
         unsubscriptions sent from the XMPP server."
    ::= { tmnxSysXmppServerEntry 25 }

tmnxSysXmppServState             OBJECT-TYPE
    SYNTAX      DisplayString (SIZE (0..32))
    MAX-ACCESS  read-only
    STATUS      current
    DESCRIPTION
        "The value of tmnxSysXmppServState indicates the state of the XMPP
         server."
    ::= { tmnxSysXmppServerEntry 26 }

tmnxSysXmppServAdminState        OBJECT-TYPE
    SYNTAX      TmnxAdminState
    MAX-ACCESS  read-create
    STATUS      current
    DESCRIPTION
        "The value of tmnxSysXmppServAdminState specifies the administrative
         state of the XMPP server."
    DEFVAL      { outOfService }
    ::= { tmnxSysXmppServerEntry 27 }

tmnxSysXmppServOperUserName      OBJECT-TYPE
    SYNTAX      TNamedItemOrEmpty
    MAX-ACCESS  read-only
    STATUS      current
    DESCRIPTION
        "The value of tmnxSysXmppServOperUserName indicates the operational user
         name that is used in the XMPP server access requests. When no user
         name is not provided,  the chassis MAC is used as the default user
         name."
    ::= { tmnxSysXmppServerEntry 28 }

tmnxSysXmppServAuthType          OBJECT-TYPE
    SYNTAX      TNamedItemOrEmpty
    MAX-ACCESS  read-only
    STATUS      current
    DESCRIPTION
        "The value of tmnxSysXmppServAuthType indicates the authentication type
         that is used in the XMPP server access requests."
    ::= { tmnxSysXmppServerEntry 29 }

tmnxSysXmppServConnMode          OBJECT-TYPE
    SYNTAX      INTEGER {
        inBand    (1),
        outOfBand (2)
    }
    MAX-ACCESS  read-only
    STATUS      current
    DESCRIPTION
        "The value of tmnxSysXmppServConnMode indicates the connection type
         that is used in the XMPP server access requests."
    ::= { tmnxSysXmppServerEntry 30 }

tmnxSysXmppServServiceId         OBJECT-TYPE
    SYNTAX      TmnxServId
    MAX-ACCESS  read-create
    STATUS      current
    DESCRIPTION
        "The tmnxSysXmppServServiceId specifies the routing context which
         provides reachability to the DNS and XMPP servers configured.

         When tmnxSysXmppServRouterId is non-zero, tmnxSysXmppServServiceId
         must be zero and vice versa."
    DEFVAL      { 0 }
    ::= { tmnxSysXmppServerEntry 31 }

tmnxSysXmppServRouterId          OBJECT-TYPE
    SYNTAX      TmnxVRtrIDOrZero
    MAX-ACCESS  read-create
    STATUS      current
    DESCRIPTION
        "The tmnxSysXmppServRouterId specifies the routing context that
         provides reachability to the DNS and XMPP servers configured.

         When tmnxSysXmppServRouterId is non-zero, tmnxSysXmppServServiceId
         must be zero and vice versa."
    DEFVAL      { 0 }
    ::= { tmnxSysXmppServerEntry 32 }

tmnxSysVsdServerTable            OBJECT-TYPE
    SYNTAX      SEQUENCE OF TmnxSysVsdServerEntry
    MAX-ACCESS  not-accessible
    STATUS      current
    DESCRIPTION
        "The tmnxSysVsdServerTable contains information pertaining to an entry
         for each server."
    ::= { tmnxSysXmppInfo 2 }

tmnxSysVsdServerEntry            OBJECT-TYPE
    SYNTAX      TmnxSysVsdServerEntry
    MAX-ACCESS  not-accessible
    STATUS      current
    DESCRIPTION
        "Each row entry contains information about a VSwitch Controller VSD
         server."
    INDEX       { tmnxSysVsdServerInstance }
    ::= { tmnxSysVsdServerTable 1 }

TmnxSysVsdServerEntry            ::= SEQUENCE
{
    tmnxSysVsdServerInstance         Unsigned32,
    tmnxSysVsdServUptime             TimeStamp,
    tmnxSysVsdServUserName           TLDisplayString,
    tmnxSysVsdServerStatus           DisplayString,
    tmnxSysVsdServMsgSent            Counter64,
    tmnxSysVsdServMsgRcvd            Counter64,
    tmnxSysVsdServMsgAckRcvd         Counter64,
    tmnxSysVsdServMsgError           Counter64,
    tmnxSysVsdServMsgTimedOut        Counter64,
    tmnxSysVsdServMsgMinRtt          Counter64,
    tmnxSysVsdServMsgMaxRtt          Counter64
}

tmnxSysVsdServerInstance         OBJECT-TYPE
    SYNTAX      Unsigned32
    MAX-ACCESS  not-accessible
    STATUS      current
    DESCRIPTION
        "The value of tmnxSysVsdServerInstance specifies an instance of a
         VSwitch Controller VSD server.
         The instance Id is an internally generated number that is unique
         for a given  VSD server."
    ::= { tmnxSysVsdServerEntry 1 }

tmnxSysVsdServUptime             OBJECT-TYPE
    SYNTAX      TimeStamp
    MAX-ACCESS  read-only
    STATUS      current
    DESCRIPTION
        "The value of tmnxSysVsdServUptime indicates the timestamp of the
         uptime of each VSD server entry in tmnxSysXmppServerTable."
    ::= { tmnxSysVsdServerEntry 2 }

tmnxSysVsdServUserName           OBJECT-TYPE
    SYNTAX      TLDisplayString
    MAX-ACCESS  read-only
    STATUS      current
    DESCRIPTION
        "The value of tmnxSysVsdServUserName specifies the VSD username."
    ::= { tmnxSysVsdServerEntry 3 }

tmnxSysVsdServerStatus           OBJECT-TYPE
    SYNTAX      DisplayString (SIZE (0..32))
    MAX-ACCESS  read-only
    STATUS      current
    DESCRIPTION
        "The value of tmnxSysVsdServerStatus indicates the status of the VSD
         server."
    ::= { tmnxSysVsdServerEntry 4 }

tmnxSysVsdServMsgSent            OBJECT-TYPE
    SYNTAX      Counter64
    MAX-ACCESS  read-only
    STATUS      current
    DESCRIPTION
        "The value of tmnxSysVsdServMsgSent indicates the number of messages
         sent from the VSD server."
    ::= { tmnxSysVsdServerEntry 5 }

tmnxSysVsdServMsgRcvd            OBJECT-TYPE
    SYNTAX      Counter64
    MAX-ACCESS  read-only
    STATUS      current
    DESCRIPTION
        "The value of tmnxSysVsdServMsgRcvd indicates the number of messages
         received from the VSD server."
    ::= { tmnxSysVsdServerEntry 6 }

tmnxSysVsdServMsgAckRcvd         OBJECT-TYPE
    SYNTAX      Counter64
    MAX-ACCESS  read-only
    STATUS      current
    DESCRIPTION
        "The value of tmnxSysVsdServMsgAckRcvd indicates the number of message
         acknowledgements received from the VSD server."
    ::= { tmnxSysVsdServerEntry 7 }

tmnxSysVsdServMsgError           OBJECT-TYPE
    SYNTAX      Counter64
    MAX-ACCESS  read-only
    STATUS      current
    DESCRIPTION
        "The value of tmnxSysVsdServMsgError indicates the number of error
         messages received from the VSD server."
    ::= { tmnxSysVsdServerEntry 8 }

tmnxSysVsdServMsgTimedOut        OBJECT-TYPE
    SYNTAX      Counter64
    MAX-ACCESS  read-only
    STATUS      current
    DESCRIPTION
        "The value of tmnxSysVsdServMsgTimedOut indicates the number of timeout
         messages received from the VSD server."
    ::= { tmnxSysVsdServerEntry 9 }

tmnxSysVsdServMsgMinRtt          OBJECT-TYPE
    SYNTAX      Counter64
    UNITS       "milliseconds"
    MAX-ACCESS  read-only
    STATUS      current
    DESCRIPTION
        "The value of tmnxSysVsdServMsgMinRtt indicates the minimum message
         round trip time from the VSD server."
    ::= { tmnxSysVsdServerEntry 10 }

tmnxSysVsdServMsgMaxRtt          OBJECT-TYPE
    SYNTAX      Counter64
    UNITS       "milliseconds"
    MAX-ACCESS  read-only
    STATUS      current
    DESCRIPTION
        "The value of tmnxSysVsdServMsgMaxRtt indicates the maximum message
         round trip time from the VSD server."
    ::= { tmnxSysVsdServerEntry 11 }

tmnxSysResInfo                   OBJECT IDENTIFIER ::= { tmnxSysObjs 27 }

tmnxSysResCardInfo               OBJECT IDENTIFIER ::= { tmnxSysResInfo 1 }

tmnxCardCpuResMonitorTable       OBJECT-TYPE
    SYNTAX      SEQUENCE OF TmnxCardCpuResMonitorEntry
    MAX-ACCESS  not-accessible
    STATUS      current
    DESCRIPTION
        "The tmnxCardCpuResMonitorTable details the specified current card's
         CPU resources.

         The information described in this table is volatile and dependent on
         the current environmental conditions, and specified sample-time.
         Information is only displayed for online cards."
    ::= { tmnxSysResCardInfo 1 }

tmnxCardCpuResMonitorEntry       OBJECT-TYPE
    SYNTAX      TmnxCardCpuResMonitorEntry
    MAX-ACCESS  not-accessible
    STATUS      current
    DESCRIPTION
        "The tmnxCardCpuResMonitorEntry contains the card level CPU monitoring
         statistics over a specified sample-time."
    INDEX       {
        tmnxChassisIndex,
        tmnxCardResourceSlotNum,
        tmnxCardCpuResSampleTime
    }
    ::= { tmnxCardCpuResMonitorTable 1 }

TmnxCardCpuResMonitorEntry       ::= SEQUENCE
{
    tmnxCardResourceSlotNum          TmnxSlotNum,
    tmnxCardCpuResSampleTime         TmnxSysMonSampleTime,
    tmnxCardCpuResMonCpuIdle         TmnxSysMonUtilization,
    tmnxCardCpuResMonBusyCoreUtil    TmnxSysMonUtilization,
    tmnxCardCpuResMonBusyGroupName   OCTET STRING,
    tmnxCardCpuResMonBusyGroupUtil   TmnxSysMonUtilization
}

tmnxCardResourceSlotNum          OBJECT-TYPE
    SYNTAX      TmnxSlotNum
    MAX-ACCESS  not-accessible
    STATUS      current
    DESCRIPTION
        "The value of tmnxCardResourceSlotNum specifies the slot number of the
         card to which the resource information is monitored."
    ::= { tmnxCardCpuResMonitorEntry 1 }

tmnxCardCpuResSampleTime         OBJECT-TYPE
    SYNTAX      TmnxSysMonSampleTime
    MAX-ACCESS  not-accessible
    STATUS      current
    DESCRIPTION
        "The value of tmnxCardCpuResSampleTime specifies the sample-time used
         to calculate the utilization results for the row."
    ::= { tmnxCardCpuResMonitorEntry 2 }

tmnxCardCpuResMonCpuIdle         OBJECT-TYPE
    SYNTAX      TmnxSysMonUtilization
    MAX-ACCESS  read-only
    STATUS      current
    DESCRIPTION
        "The value of tmnxCardCpuResMonCpuIdle indicates the overall percentage
         of CPU idleness over the specified sample-time."
    ::= { tmnxCardCpuResMonitorEntry 3 }

tmnxCardCpuResMonBusyCoreUtil    OBJECT-TYPE
    SYNTAX      TmnxSysMonUtilization
    MAX-ACCESS  read-only
    STATUS      current
    DESCRIPTION
        "The value of tmnxCardCpuResMonBusyCoreUtil indicates the utilization
         percentage of the busiest processor core over the specified
         sample-time. On single core CPUs, this is the overall system
         utilization percentage over the specified sample-time."
    ::= { tmnxCardCpuResMonitorEntry 4 }

tmnxCardCpuResMonBusyGroupName   OBJECT-TYPE
    SYNTAX      OCTET STRING (SIZE (0..64))
    MAX-ACCESS  read-only
    STATUS      current
    DESCRIPTION
        "The value of tmnxCardCpuResMonBusyGroupName indicates the name of the
         group that is running at the highest capacity utilization.

         Capacity utilization is the CPU utilization relative to the maximum CPU
         resources available to that group.  A group is a set of related
         applications, services, tasks or protocol handlers that consumes some
         part of the system CPU resources.

         The capacity utilization of the busiest group is indicated by
         tmnxCardCpuResMonBusyGroupUtil."
    ::= { tmnxCardCpuResMonitorEntry 5 }

tmnxCardCpuResMonBusyGroupUtil   OBJECT-TYPE
    SYNTAX      TmnxSysMonUtilization
    MAX-ACCESS  read-only
    STATUS      current
    DESCRIPTION
        "The value of tmnxCardCpuResMonBusyGroupUtil indicates the capacity
         utilization of the group that is running at the highest capacity
         utilization.

         Capacity utilization is the CPU utilization relative to the maximum CPU
         resources available to that group.  A group is a set of related
         applications, services, tasks or protocol handlers that consumes some
         part of the system CPU resources.

         The name of the busiest group is indicated by
         tmnxCardCpuResMonBusyGroupName."
    ::= { tmnxCardCpuResMonitorEntry 6 }

tmnxCardMemResMonitorTable       OBJECT-TYPE
    SYNTAX      SEQUENCE OF TmnxCardMemResMonitorEntry
    MAX-ACCESS  not-accessible
    STATUS      current
    DESCRIPTION
        "The tmnxCardMemResMonitorTable details the specified current card's
         memory resources.

         The information described in this table is volatile and dependent on
         the current environmental conditions. Information is only displayed
         for online cards."
    ::= { tmnxSysResCardInfo 2 }

tmnxCardMemResMonitorEntry       OBJECT-TYPE
    SYNTAX      TmnxCardMemResMonitorEntry
    MAX-ACCESS  not-accessible
    STATUS      current
    DESCRIPTION
        "The tmnxCardMemResMonitorEntry contains the card's memory usage
         statistics."
    INDEX       {
        tmnxChassisIndex,
        tmnxCardResourceSlotNum
    }
    ::= { tmnxCardMemResMonitorTable 1 }

TmnxCardMemResMonitorEntry       ::= SEQUENCE
{
    tmnxCardMemResMemoryUsed         Gauge32,
    tmnxCardMemResMemoryAvailable    Gauge32,
    tmnxCardMemResPoolsAllocated     Gauge32
}

tmnxCardMemResMemoryUsed         OBJECT-TYPE
    SYNTAX      Gauge32
    UNITS       "kilobytes"
    MAX-ACCESS  read-only
    STATUS      current
    DESCRIPTION
        "The value of tmnxCardMemResMemoryUsed indicates the total
         pre-allocated pool memory, in kilobytes, currently in use on the card."
    ::= { tmnxCardMemResMonitorEntry 1 }

tmnxCardMemResMemoryAvailable    OBJECT-TYPE
    SYNTAX      Gauge32
    UNITS       "kilobytes"
    MAX-ACCESS  read-only
    STATUS      current
    DESCRIPTION
        "The value of tmnxCardMemResMemoryAvailable indicates the amount of
         free memory, in kilobytes, in the card that is not allocated to memory
         pools, but is available in case a memory pool needs to grow."
    ::= { tmnxCardMemResMonitorEntry 2 }

tmnxCardMemResPoolsAllocated     OBJECT-TYPE
    SYNTAX      Gauge32
    UNITS       "kilobytes"
    MAX-ACCESS  read-only
    STATUS      current
    DESCRIPTION
        "The value of tmnxCardMemResPoolsAllocated indicates the total memory,
         in kilobytes, currently allocated in memory-pools on the card.

         This memory may or may not be currently in use, but is pre-allocated
         should the software need to use it."
    ::= { tmnxCardMemResMonitorEntry 3 }

tmnxSysResEcmpProfInfo           OBJECT IDENTIFIER ::= { tmnxSysResInfo 2 }

tmnxSysResEcmpProfTable          OBJECT-TYPE
    SYNTAX      SEQUENCE OF TmnxSysResEcmpProfEntry
    MAX-ACCESS  not-accessible
    STATUS      current
    DESCRIPTION
        "The tmnxSysResEcmpProfTable contains information about the system
         resource profile to be allocated for each type of the ecmp bundle.

         The table can have up to a maximum of 2 entries."
    ::= { tmnxSysResEcmpProfInfo 1 }

tmnxSysResEcmpProfEntry          OBJECT-TYPE
    SYNTAX      TmnxSysResEcmpProfEntry
    MAX-ACCESS  not-accessible
    STATUS      current
    DESCRIPTION
        "Each row entry contains information about the resources to be created
         for each type of ecmp bundle supported.

         Entries in this table can be created and deleted via SNMP SET
         operations to tmnxSysResEcmpProfRowStatus."
    INDEX       { tmnxSysResEcmpProfId }
    ::= { tmnxSysResEcmpProfTable 1 }

TmnxSysResEcmpProfEntry          ::= SEQUENCE
{
    tmnxSysResEcmpProfId             Unsigned32,
    tmnxSysResEcmpProfRowStatus      RowStatus,
    tmnxSysResEcmpProfType           INTEGER,
    tmnxSysResEcmpProfLinksPerGrp    Unsigned32,
    tmnxSysResEcmpProfNumGrps        Unsigned32
}

tmnxSysResEcmpProfId             OBJECT-TYPE
    SYNTAX      Unsigned32 (1..2)
    MAX-ACCESS  not-accessible
    STATUS      current
    DESCRIPTION
        "The value of tmnxSysResEcmpProfId specifies the resource profile index
         for the ecmp bundle."
    ::= { tmnxSysResEcmpProfEntry 1 }

tmnxSysResEcmpProfRowStatus      OBJECT-TYPE
    SYNTAX      RowStatus
    MAX-ACCESS  read-create
    STATUS      current
    DESCRIPTION
        "The value of the tmnxSysResEcmpProfRowStatus specifies the status of this row.  It
         allows the creation and deletion of row entries in tmnxSysResEcmpProfTable.

         To create a row in this table, set tmnxSysResEcmpProfRowStatus to createAndGo(4).  The values of
         tmnxSysResEcmpProfType, tmnxSysResEcmpProfLinksPerGrp, and tmnxSysResEcmpProfNumGrps must also be
         set to valid values for the row creation to succeed.

         To delete a row in this table, set tmnxSysResEcmpProfRowStatus to
         delete(6)."
    ::= { tmnxSysResEcmpProfEntry 2 }

tmnxSysResEcmpProfType           OBJECT-TYPE
    SYNTAX      INTEGER {
        mpls (1),
        ip   (2)
    }
    MAX-ACCESS  read-create
    STATUS      current
    DESCRIPTION
        "The value of tmnxSysResEcmpProfType specifies the ecmp bundle type
         applicable to this conceptual row."
    ::= { tmnxSysResEcmpProfEntry 3 }

tmnxSysResEcmpProfLinksPerGrp    OBJECT-TYPE
    SYNTAX      Unsigned32 (1..16)
    MAX-ACCESS  read-create
    STATUS      current
    DESCRIPTION
        "The value of tmnxSysResEcmpProfLinksPerGrp specifies the maximum
         number of links per group for the ecmp bundle"
    ::= { tmnxSysResEcmpProfEntry 4 }

tmnxSysResEcmpProfNumGrps        OBJECT-TYPE
    SYNTAX      Unsigned32 (1..2048)
    MAX-ACCESS  read-create
    STATUS      current
    DESCRIPTION
        "The value of tmnxSysResEcmpProfNumGrps specifies the maximum number of
         ecmp groups allowed for the ecmp bundle. When tmnxSysResEcmpProfType
         is 'mpls', maximum value of tmnxSysResEcmpProfNumGrps is 2047, Only
         when tmnxSysResEcmpProfType is 'ip', can the maximum value of
         tmnxSysResEcmpProfNumGrps be 2048."
    ::= { tmnxSysResEcmpProfEntry 5 }

tmnxSysResItCam                  OBJECT IDENTIFIER ::= { tmnxSysResInfo 3 }

tmnxSysResItCamBank              OBJECT IDENTIFIER ::= { tmnxSysResItCam 1 }

tmnxSysResItCamBankV6Multicast   OBJECT-TYPE
    SYNTAX      Unsigned32 (0..5)
    MAX-ACCESS  read-write
    STATUS      current
    DESCRIPTION
        "The value of tmnxSysResItCamBankV6Multicast specifies the maximum
         number of internal TCAM banks to support ipv6 multicast to scale"
    DEFVAL      { 0 }
    ::= { tmnxSysResItCamBank 1 }

tmnxSysFpCam                     OBJECT IDENTIFIER ::= { tmnxSysResInfo 4 }

tmnxSysFpCamAllocation           OBJECT IDENTIFIER ::= { tmnxSysFpCam 1 }

tmnxSysFpCamAllocAdmnV6Multicast OBJECT-TYPE
    SYNTAX      Unsigned32 (0..10240)
    MAX-ACCESS  read-write
    STATUS      current
    DESCRIPTION
        "The value of tmnxSysFpCamAllocAdmnV6Multicast specifies the maximum
         number of number of IPv6 multicast routes allowed to be installed  in
         the system/FP"
    DEFVAL      { 0 }
    ::= { tmnxSysFpCamAllocation 1 }

tmnxSysFpCamAllocOperV6Multicast OBJECT-TYPE
    SYNTAX      Unsigned32 (0..10240)
    MAX-ACCESS  read-only
    STATUS      current
    DESCRIPTION
        "The value of tmnxSysFpCamAllocOperV6Multicast specifies the total
         number of IPv6 multicast routes installed in the system/FP"
    ::= { tmnxSysFpCamAllocation 2 }

tmnxSysDhcp                      OBJECT IDENTIFIER ::= { tmnxSysObjs 28 }

tmnxSysDhcp6AdvNoaddrsGlobal     OBJECT-TYPE
    SYNTAX      BITS {
        esmProxy (0),
        esmRelay (1),
        relay    (2),
        server   (3)
    }
    MAX-ACCESS  read-write
    STATUS      current
    DESCRIPTION
        "The value of tmnxSysDhcp6AdvNoaddrsGlobal specifies the composition of
         DHCPv6 Advertise Messages in case a DHCP6 application in this system
         will not assign any addresses to any Identity Association (IA) in a
         subsequent Request from the client.

         DHCP6 applications in this system are Relay, Server, Enhanced
         Subscriber Management (ESM) Proxy and ESM Relay.

         By default, a DHCP6 application in this system will send an Advertise
         message to the client that includes the IA containing a Status Code
         option with status code 'NoAddrsAvail', as specified in Errata 2472.

         If the bit corresponding to a DHCP6 application is set, that
         application will send an Advertise message to the client that includes
         only a Status Code option with code 'NoAddrsAvail'.

         This system will refuse bit combinations that are not supported: the
         'esmRelay' and 'server' bits must be toggled together, and the
         'esmProxy' and 'relay' bits are read-only."
    REFERENCE
        "RFC3315 Dynamic Host Configuration Protocol for IPv6 (DHCPv6)
         section 17.2.2 Creation and Transmission of Advertise Messages

         RFC3315 errata 2472 (section 17.2)"
    DEFVAL      { {} }
    ::= { tmnxSysDhcp 1 }

tmnxSysVsdInfo                   OBJECT IDENTIFIER ::= { tmnxSysObjs 29 }

tmnxSysVsdSystemId               OBJECT-TYPE
    SYNTAX      TNamedItemOrEmpty
    MAX-ACCESS  read-write
    STATUS      current
    DESCRIPTION
        "The value of tmnxSysVsdSystemId specifies the name used by this system
         as its identity when communicating with VSD."
    DEFVAL      { ''H }
    ::= { tmnxSysVsdInfo 1 }

tmnxSysVsdGwPubSubIsSubscrd      OBJECT-TYPE
    SYNTAX      TruthValue
    MAX-ACCESS  read-only
    STATUS      current
    DESCRIPTION
        "The value of tmnxSysVsdGwPubSubIsSubscrd indicates whether the system
         is subscribed to the gateway publish-subscribe node."
    ::= { tmnxSysVsdInfo 2 }

tmnxSysVsdGwPubSubNodeName       OBJECT-TYPE
    SYNTAX      DisplayString
    MAX-ACCESS  read-only
    STATUS      current
    DESCRIPTION
        "The value of tmnxSysVsdGwPubSubNodeName indicates the gateway
         publish-subscribe node name assigned by VSD."
    ::= { tmnxSysVsdInfo 3 }

tmnxSysVsdGwPubSubLstSubscrdTime OBJECT-TYPE
    SYNTAX      TimeStamp
    MAX-ACCESS  read-only
    STATUS      current
    DESCRIPTION
        "The value of tmnxSysVsdGwPubSubLstSubscrdTime indicates the last
         subscription time to the gateway publish-subscribe node."
    ::= { tmnxSysVsdInfo 4 }

tmnxSysVsdGwLastAuditTxTime      OBJECT-TYPE
    SYNTAX      TimeStamp
    MAX-ACCESS  read-only
    STATUS      current
    DESCRIPTION
        "The value of tmnxSysVsdGwLastAuditTxTime indicates the time last
         gateway audit was sent to the VSD."
    ::= { tmnxSysVsdInfo 5 }

tmnxSysLicense                   OBJECT IDENTIFIER ::= { tmnxSysObjs 30 }

tmnxSysLicenseStatus             OBJECT-TYPE
    SYNTAX      TItemDescription
    MAX-ACCESS  read-only
    STATUS      current
    DESCRIPTION
        "The value of tmnxSysLicenseStatus indicates the current status of the
         license."
    ::= { tmnxSysLicense 1 }

tmnxSysLicenseName               OBJECT-TYPE
    SYNTAX      TItemDescription
    MAX-ACCESS  read-only
    STATUS      current
    DESCRIPTION
        "The value of tmnxSysLicenseName indicates the license name."
    ::= { tmnxSysLicense 2 }

tmnxSysLicenseUuid               OBJECT-TYPE
    SYNTAX      TmnxUuid
    MAX-ACCESS  read-only
    STATUS      current
    DESCRIPTION
        "The value of tmnxSysLicenseUuid indicates the Universally Unique
         Identifier (UUID) for the license of the virtual machine (VM)."
    ::= { tmnxSysLicense 3 }

tmnxSysLicenseDescription        OBJECT-TYPE
    SYNTAX      TItemDescription
    MAX-ACCESS  read-only
    STATUS      current
    DESCRIPTION
        "The value of tmnxSysLicenseDescription indicates the license
         description."
    ::= { tmnxSysLicense 4 }

tmnxSysLicenseProduct            OBJECT-TYPE
    SYNTAX      TItemDescription
    MAX-ACCESS  read-only
    STATUS      current
    DESCRIPTION
        "The value of tmnxSysLicenseProduct indicates the product for which the
         license is valid."
    ::= { tmnxSysLicense 5 }

tmnxSysLicenseSwVersion          OBJECT-TYPE
    SYNTAX      TItemDescription
    MAX-ACCESS  read-only
    STATUS      current
    DESCRIPTION
        "The value of tmnxSysLicenseSwVersion indicates the SROS series system
         software version for which the license is valid."
    ::= { tmnxSysLicense 6 }

tmnxSysLicenseIssueDateAndTime   OBJECT-TYPE
    SYNTAX      DateAndTime
    MAX-ACCESS  read-only
    STATUS      current
    DESCRIPTION
        "The value of tmnxSysLicenseIssueDateAndTime indicates the day and time
         the license was issued."
    ::= { tmnxSysLicense 7 }

tmnxSysLicenseStartDateAndTime   OBJECT-TYPE
    SYNTAX      DateAndTime
    MAX-ACCESS  read-only
    STATUS      current
    DESCRIPTION
        "The value of tmnxSysLicenseStartDateAndTime indicates the day and time
         the license became active."
    ::= { tmnxSysLicense 8 }

tmnxSysLicenseEndDateAndTime     OBJECT-TYPE
    SYNTAX      DateAndTime
    MAX-ACCESS  read-only
    STATUS      current
    DESCRIPTION
        "The value of tmnxSysLicenseEndDateAndTime indicates the day and time
         the license expires."
    ::= { tmnxSysLicense 9 }

tmnxSysLicenseVChassisType       OBJECT-TYPE
    SYNTAX      TNamedItemOrEmpty
    MAX-ACCESS  read-only
    STATUS      current
    DESCRIPTION
        "The value of tmnxSysLicenseVChassisType indicates the virtual chassis
         type for which the license is valid.

         A value of empty string indicates that the license is not associated
         with a virtual chassis."
    ::= { tmnxSysLicense 10 }

tmnxSysLicenseMaxNumCPMs         OBJECT-TYPE
    SYNTAX      Unsigned32
    MAX-ACCESS  read-only
    STATUS      current
    DESCRIPTION
        "The value of tmnxSysLicenseMaxNumCPMs indicates the maximum number of
         CPMs allowed by the license.

         A value of 0 indicates that the number of CPMs is not restricted by
         the license."
    ::= { tmnxSysLicense 11 }

tmnxSysLicenseMaxNumIOMs         OBJECT-TYPE
    SYNTAX      Unsigned32
    MAX-ACCESS  read-only
    STATUS      current
    DESCRIPTION
        "The value of tmnxSysLicenseMaxNumIOMs indicates the maximum number of
         IOMs allowed by the license.

         A value of 0 indicates that the number of IOMs is not restricted by
         the license."
    ::= { tmnxSysLicense 12 }

tmnxSysCpmCardLicenseTable       OBJECT-TYPE
    SYNTAX      SEQUENCE OF TmnxSysCpmCardLicenseEntry
    MAX-ACCESS  not-accessible
    STATUS      current
    DESCRIPTION
        "The tmnxSysCpmCardLicenseTable has an entry for each CPM card in the
         first chassis in the system."
    ::= { tmnxSysLicense 13 }

tmnxSysCpmCardLicenseEntry       OBJECT-TYPE
    SYNTAX      TmnxSysCpmCardLicenseEntry
    MAX-ACCESS  not-accessible
    STATUS      current
    DESCRIPTION
        "Each row represents a CPM card in the first chassis in the system.
         When a tmnxChassisEntry is created, a tmnxSysCpmCardLicenseEntry is
         created for each CPM card in the first chassis. Entries cannot be
         created or deleted via SNMP SET operations."
    INDEX       {
        tmnxChassisIndex,
        tmnxCpmCardSlotNum,
        tmnxCpmCardNum
    }
    ::= { tmnxSysCpmCardLicenseTable 1 }

TmnxSysCpmCardLicenseEntry       ::= SEQUENCE
{
    tmnxSysCpmCardLicStatus          TItemDescription,
    tmnxSysCpmCardLicName            TItemDescription,
    tmnxSysCpmCardLicUuid            TmnxUuid,
    tmnxSysCpmCardLicDescription     TItemDescription,
    tmnxSysCpmCardLicProduct         TItemDescription,
    tmnxSysCpmCardLicSwVersion       TItemDescription,
    tmnxSysCpmCardLicIssueDateTime   DateAndTime,
    tmnxSysCpmCardLicStartDateTime   DateAndTime,
    tmnxSysCpmCardLicEndDateTime     DateAndTime,
    tmnxSysCpmCardLicVChassisType    TNamedItemOrEmpty,
    tmnxSysCpmCardLicMaxNumCPMs      Unsigned32,
    tmnxSysCpmCardLicMaxNumIOMs      Unsigned32
}

tmnxSysCpmCardLicStatus          OBJECT-TYPE
    SYNTAX      TItemDescription
    MAX-ACCESS  read-only
    STATUS      current
    DESCRIPTION
        "The value of tmnxSysCpmCardLicStatus indicates the current status of
         the license."
    ::= { tmnxSysCpmCardLicenseEntry 1 }

tmnxSysCpmCardLicName            OBJECT-TYPE
    SYNTAX      TItemDescription
    MAX-ACCESS  read-only
    STATUS      current
    DESCRIPTION
        "The value of tmnxSysCpmCardLicName indicates the license name."
    ::= { tmnxSysCpmCardLicenseEntry 2 }

tmnxSysCpmCardLicUuid            OBJECT-TYPE
    SYNTAX      TmnxUuid
    MAX-ACCESS  read-only
    STATUS      current
    DESCRIPTION
        "The value of tmnxSysCpmCardLicUuid indicates the Universally Unique
         Identifier (UUID) for the license of the CPM card in the virtual
         machine (VM)."
    ::= { tmnxSysCpmCardLicenseEntry 3 }

tmnxSysCpmCardLicDescription     OBJECT-TYPE
    SYNTAX      TItemDescription
    MAX-ACCESS  read-only
    STATUS      current
    DESCRIPTION
        "The value of tmnxSysCpmCardLicDescription indicates the license
         description."
    ::= { tmnxSysCpmCardLicenseEntry 4 }

tmnxSysCpmCardLicProduct         OBJECT-TYPE
    SYNTAX      TItemDescription
    MAX-ACCESS  read-only
    STATUS      current
    DESCRIPTION
        "The value of tmnxSysCpmCardLicProduct indicates the product for which
         the license is valid."
    ::= { tmnxSysCpmCardLicenseEntry 5 }

tmnxSysCpmCardLicSwVersion       OBJECT-TYPE
    SYNTAX      TItemDescription
    MAX-ACCESS  read-only
    STATUS      current
    DESCRIPTION
        "The value of tmnxSysCpmCardLicSwVersion indicates the SROS series
         system software version for which the license is valid."
    ::= { tmnxSysCpmCardLicenseEntry 6 }

tmnxSysCpmCardLicIssueDateTime   OBJECT-TYPE
    SYNTAX      DateAndTime
    MAX-ACCESS  read-only
    STATUS      current
    DESCRIPTION
        "The value of tmnxSysCpmCardLicIssueDateTime indicates the day and time
         the license was issued."
    ::= { tmnxSysCpmCardLicenseEntry 7 }

tmnxSysCpmCardLicStartDateTime   OBJECT-TYPE
    SYNTAX      DateAndTime
    MAX-ACCESS  read-only
    STATUS      current
    DESCRIPTION
        "The value of tmnxSysCpmCardLicStartDateTime indicates the day and time
         the license became active."
    ::= { tmnxSysCpmCardLicenseEntry 8 }

tmnxSysCpmCardLicEndDateTime     OBJECT-TYPE
    SYNTAX      DateAndTime
    MAX-ACCESS  read-only
    STATUS      current
    DESCRIPTION
        "The value of tmnxSysCpmCardLicEndDateTime indicates the day and time
         the license expires."
    ::= { tmnxSysCpmCardLicenseEntry 9 }

tmnxSysCpmCardLicVChassisType    OBJECT-TYPE
    SYNTAX      TNamedItemOrEmpty
    MAX-ACCESS  read-only
    STATUS      current
    DESCRIPTION
        "The value of tmnxSysCpmCardLicVChassisType indicates the virtual
         chassis type for which the license is valid.

         A value of empty string indicates that the license is not associated
         with a virtual chassis."
    ::= { tmnxSysCpmCardLicenseEntry 10 }

tmnxSysCpmCardLicMaxNumCPMs      OBJECT-TYPE
    SYNTAX      Unsigned32
    MAX-ACCESS  read-only
    STATUS      current
    DESCRIPTION
        "The value of tmnxSysCpmCardLicMaxNumCPMs indicates the maximum number
         of CPMs allowed by the license.

         A value of 0 indicates that the number of CPMs is not restricted by
         the license."
    ::= { tmnxSysCpmCardLicenseEntry 11 }

tmnxSysCpmCardLicMaxNumIOMs      OBJECT-TYPE
    SYNTAX      Unsigned32
    MAX-ACCESS  read-only
    STATUS      current
    DESCRIPTION
        "The value of tmnxSysCpmCardLicMaxNumIOMs indicates the maximum number
         of IOMs allowed by the license.

         A value of 0 indicates that the number of IOMs is not restricted by
         the license."
    ::= { tmnxSysCpmCardLicenseEntry 12 }

tmnxSysCpmCardLicFeatureTable    OBJECT-TYPE
    SYNTAX      SEQUENCE OF TmnxSysCpmCardLicFeatureEntry
    MAX-ACCESS  not-accessible
    STATUS      current
    DESCRIPTION
        "The tmnxSysCpmCardLicFeatureTable has an entry for each feature
         supported by the license installed on a CPM card in the chassis with
         TIMETRA-CHASSIS-MIB::tmnxPhysChassisClass 'routerChassis(3)' and
         TIMETRA-CHASSIS-MIB::tmnxPhysChassisNum '1'."
    ::= { tmnxSysLicense 14 }

tmnxSysCpmCardLicFeatureEntry    OBJECT-TYPE
    SYNTAX      TmnxSysCpmCardLicFeatureEntry
    MAX-ACCESS  not-accessible
    STATUS      current
    DESCRIPTION
        "When a TIMETRA-CHASSIS-MIB::tmnxCpmCardEntry is created for a CPM card
         in the chassis with TIMETRA-CHASSIS-MIB::tmnxPhysChassisClass
         'routerChassis(3)' and TIMETRA-CHASSIS-MIB::tmnxPhysChassisNum '1', a
         tmnxSysCpmCardLicFeatureEntry is created for each feature supported by
         the license installed on that CPM card.

         Entries cannot be created or deleted via SNMP SET operations."
    INDEX       {
        tmnxChassisIndex,
        tmnxCpmCardSlotNum,
        tmnxCpmCardNum,
        tmnxSysCpmCardLicFeatApplication,
        tmnxSysCpmCardLicFeatNumber
    }
    ::= { tmnxSysCpmCardLicFeatureTable 1 }

TmnxSysCpmCardLicFeatureEntry    ::= SEQUENCE
{
    tmnxSysCpmCardLicFeatApplication TNamedItem,
    tmnxSysCpmCardLicFeatNumber      Unsigned32,
    tmnxSysCpmCardLicFeatDescription TItemDescription
}

tmnxSysCpmCardLicFeatApplication OBJECT-TYPE
    SYNTAX      TNamedItem
    MAX-ACCESS  not-accessible
    STATUS      current
    DESCRIPTION
        "The value of tmnxSysCpmCardLicFeatApplication specifies the
         application supported by the license."
    ::= { tmnxSysCpmCardLicFeatureEntry 1 }

tmnxSysCpmCardLicFeatNumber      OBJECT-TYPE
    SYNTAX      Unsigned32 (1..4294967295)
    MAX-ACCESS  not-accessible
    STATUS      current
    DESCRIPTION
        "The value of tmnxSysCpmCardLicFeatNumber specifies the feature number
         associated with the feature supported by the license."
    ::= { tmnxSysCpmCardLicFeatureEntry 2 }

tmnxSysCpmCardLicFeatDescription OBJECT-TYPE
    SYNTAX      TItemDescription
    MAX-ACCESS  read-only
    STATUS      current
    DESCRIPTION
        "The value of tmnxSysCpmCardLicFeatDescription indicates the
         description of the feature supported by the license."
    ::= { tmnxSysCpmCardLicFeatureEntry 3 }

tmnxSysLicensingTable            OBJECT-TYPE
    SYNTAX      SEQUENCE OF TmnxSysLicensingEntry
    MAX-ACCESS  not-accessible
    STATUS      current
    DESCRIPTION
        "The tmnxSysLicensingTable an entry for each licensed applications for
         this system."
    ::= { tmnxSysLicense 16 }

tmnxSysLicensingEntry            OBJECT-TYPE
    SYNTAX      TmnxSysLicensingEntry
    MAX-ACCESS  not-accessible
    STATUS      current
    DESCRIPTION
        "Each row contains detailed information about each licensed
         application.

         Entries cannot be created or deleted via SNMP SET operations."
    INDEX       {
        tmnxSysLicensingGroup,
        tmnxSysLicensedAppName
    }
    ::= { tmnxSysLicensingTable 1 }

TmnxSysLicensingEntry            ::= SEQUENCE
{
    tmnxSysLicensingGroup            TmnxSysLicensingGroup,
    tmnxSysLicensedAppName           TNamedItem,
    tmnxSysAppLicenseDescription     DisplayString,
    tmnxSysAppLicenseType            INTEGER,
    tmnxSysAppLicensePoolSize        Integer32,
    tmnxSysAppLicenseAllocated       Unsigned32,
    tmnxSysAppLicensePresent         TruthValue,
    tmnxSysAppLicenseState           INTEGER
}

tmnxSysLicensingGroup            OBJECT-TYPE
    SYNTAX      TmnxSysLicensingGroup
    MAX-ACCESS  not-accessible
    STATUS      current
    DESCRIPTION
        "The value of tmnxSysLicensingGroup indicates the licensing group."
    ::= { tmnxSysLicensingEntry 1 }

tmnxSysLicensedAppName           OBJECT-TYPE
    SYNTAX      TNamedItem
    MAX-ACCESS  not-accessible
    STATUS      current
    DESCRIPTION
        "The value of tmnxSysLicensedAppName indicates the name of the licensed
         application."
    ::= { tmnxSysLicensingEntry 2 }

tmnxSysAppLicenseDescription     OBJECT-TYPE
    SYNTAX      DisplayString (SIZE (1..64))
    MAX-ACCESS  read-only
    STATUS      current
    DESCRIPTION
        "The value of the object tmnxSysAppLicenseDescription indicates a more
         detailed description of the application license."
    ::= { tmnxSysLicensingEntry 3 }

tmnxSysAppLicenseType            OBJECT-TYPE
    SYNTAX      INTEGER {
        unknown (0),
        pool    (1),
        rtu     (2)
    }
    MAX-ACCESS  read-only
    STATUS      current
    DESCRIPTION
        "The value of tmnxSysAppLicenseType specifies the type
         of licensing done for this application.
         pool - A pool license grants a specified number of
                concurrent allocations of the license.
         rtu  - An RTU license grants the right to use a
                feature"
    ::= { tmnxSysLicensingEntry 4 }

tmnxSysAppLicensePoolSize        OBJECT-TYPE
    SYNTAX      Integer32
    MAX-ACCESS  read-only
    STATUS      current
    DESCRIPTION
        "The value of tmnxSysAppLicensePoolSize indicates the size of the pool
         of licenses that can be allocated within the system. A value of (-1)
         indicates a pool size is not applicable to this application based on
         tmnxSysAppLicenseType."
    ::= { tmnxSysLicensingEntry 5 }

tmnxSysAppLicenseAllocated       OBJECT-TYPE
    SYNTAX      Unsigned32
    MAX-ACCESS  read-only
    STATUS      current
    DESCRIPTION
        "The value of tmnxSysAppLicenseAllocated indicates the the number of
         these licenses currently allocated in the system."
    ::= { tmnxSysLicensingEntry 6 }

tmnxSysAppLicensePresent         OBJECT-TYPE
    SYNTAX      TruthValue
    MAX-ACCESS  read-only
    STATUS      current
    DESCRIPTION
        "The value of tmnxSysAppLicensePresent specifies if the current system
         license grants the right to use feature on this system."
    ::= { tmnxSysLicensingEntry 7 }

tmnxSysAppLicenseState           OBJECT-TYPE
    SYNTAX      INTEGER {
        unknown   (0),
        valid     (1),
        error     (2),
        violation (3)
    }
    MAX-ACCESS  read-only
    STATUS      current
    DESCRIPTION
        "The value of tmnxSysAppLicenseState indicates the state
         of the license for this application.
         valid     - No issue with application license
         error     - Insufficient licensing has been detected.
         violation - License violation has been detected."
    ::= { tmnxSysLicensingEntry 8 }

tmnxSysAvailableLicensesTable    OBJECT-TYPE
    SYNTAX      SEQUENCE OF TmnxSysAvailableLicensesEntry
    MAX-ACCESS  not-accessible
    STATUS      current
    DESCRIPTION
        "The tmnxSysAvailableLicensesTable has an entry for each license
         available for this system that was matched in the license file."
    ::= { tmnxSysLicense 17 }

tmnxSysAvailableLicensesEntry    OBJECT-TYPE
    SYNTAX      TmnxSysAvailableLicensesEntry
    MAX-ACCESS  not-accessible
    STATUS      current
    DESCRIPTION
        "Each row represents a license avalalable for this system from the last
         loaded license-file."
    INDEX       { tmnxSysAvailLicenseIndex }
    ::= { tmnxSysAvailableLicensesTable 1 }

TmnxSysAvailableLicensesEntry    ::= SEQUENCE
{
    tmnxSysAvailLicenseIndex         Unsigned32,
    tmnxSysAvailLicenseName          TItemDescription,
    tmnxSysAvailLicenseUuid          TmnxUuid,
    tmnxSysAvailLicenseDescription   TItemDescription,
    tmnxSysAvailLicenseSwVersion     TItemDescription,
    tmnxSysAvailLicIssueDateTime     DateAndTime,
    tmnxSysAvailLicStartDateTime     DateAndTime,
    tmnxSysAvailLicEndDateTime       DateAndTime,
    tmnxSysAvailLicenseProduct       TItemDescription
}

tmnxSysAvailLicenseIndex         OBJECT-TYPE
    SYNTAX      Unsigned32
    MAX-ACCESS  not-accessible
    STATUS      current
    DESCRIPTION
        "The value of tmnxSysAvailLicenseIndex indicates the index of the
         matched license."
    ::= { tmnxSysAvailableLicensesEntry 1 }

tmnxSysAvailLicenseName          OBJECT-TYPE
    SYNTAX      TItemDescription
    MAX-ACCESS  read-only
    STATUS      current
    DESCRIPTION
        "The value of tmnxSysAvailLicenseName indicates the license name."
    ::= { tmnxSysAvailableLicensesEntry 2 }

tmnxSysAvailLicenseUuid          OBJECT-TYPE
    SYNTAX      TmnxUuid
    MAX-ACCESS  read-only
    STATUS      current
    DESCRIPTION
        "The value of tmnxSysAvailLicenseUuid indicates the Universally Unique
         Identifier (UUID) for the license."
    ::= { tmnxSysAvailableLicensesEntry 3 }

tmnxSysAvailLicenseDescription   OBJECT-TYPE
    SYNTAX      TItemDescription
    MAX-ACCESS  read-only
    STATUS      current
    DESCRIPTION
        "The value of tmnxSysAvailLicenseDescription indicates the license
         description."
    ::= { tmnxSysAvailableLicensesEntry 4 }

tmnxSysAvailLicenseSwVersion     OBJECT-TYPE
    SYNTAX      TItemDescription
    MAX-ACCESS  read-only
    STATUS      current
    DESCRIPTION
        "The value of tmnxSysAvailLicenseSwVersion indicates the SROS series
         system software version for which the license is valid."
    ::= { tmnxSysAvailableLicensesEntry 5 }

tmnxSysAvailLicIssueDateTime     OBJECT-TYPE
    SYNTAX      DateAndTime
    MAX-ACCESS  read-only
    STATUS      current
    DESCRIPTION
        "The value of tmnxSysAvailLicIssueDateTime indicates the day and time
         the license was issued."
    ::= { tmnxSysAvailableLicensesEntry 6 }

tmnxSysAvailLicStartDateTime     OBJECT-TYPE
    SYNTAX      DateAndTime
    MAX-ACCESS  read-only
    STATUS      current
    DESCRIPTION
        "The value of tmnxSysAvailLicStartDateTime indicates the day and time
         the license becomes active."
    ::= { tmnxSysAvailableLicensesEntry 7 }

tmnxSysAvailLicEndDateTime       OBJECT-TYPE
    SYNTAX      DateAndTime
    MAX-ACCESS  read-only
    STATUS      current
    DESCRIPTION
        "The value of tmnxSysAvailLicEndDateTime indicates the day and time the
         license expires."
    ::= { tmnxSysAvailableLicensesEntry 8 }

tmnxSysAvailLicenseProduct       OBJECT-TYPE
    SYNTAX      TItemDescription
    MAX-ACCESS  read-only
    STATUS      current
    DESCRIPTION
        "The value of tmnxSysAvailLicenseProduct indicates the licensed
         product."
    ::= { tmnxSysAvailableLicensesEntry 9 }

tmnxSysLicensingState            OBJECT-TYPE
    SYNTAX      INTEGER {
        unlicensed      (0),
        licensed        (1),
        invalid-license (2),
        expired-license (3)
    }
    MAX-ACCESS  read-only
    STATUS      current
    DESCRIPTION
        "The value of tmnxSysLicensingState indicates the current status of the
         system licensing."
    ::= { tmnxSysLicense 18 }

tmnxSysLicensingRebootPending    OBJECT-TYPE
    SYNTAX      TruthValue
    MAX-ACCESS  read-only
    STATUS      current
    DESCRIPTION
        "The value of tmnxSysLicensingRebootPending indicates whether a system
         reboot is pending due to system licensing"
    ::= { tmnxSysLicense 19 }

tmnxSysLicenseStatistics         OBJECT IDENTIFIER ::= { tmnxSysLicense 20 }

tmnxSysAppStats24HrsTable        OBJECT-TYPE
    SYNTAX      SEQUENCE OF TmnxSysAppStats24HrsEntry
    MAX-ACCESS  not-accessible
    STATUS      current
    DESCRIPTION
        "The tmnxSysAppStats24HrsTable contains statistics about a virtual
         machine application collected periodically during the last 24 hours."
    ::= { tmnxSysLicenseStatistics 1 }

tmnxSysAppStats24HrsEntry        OBJECT-TYPE
    SYNTAX      TmnxSysAppStats24HrsEntry
    MAX-ACCESS  not-accessible
    STATUS      current
    DESCRIPTION
        "Each conceptual row contains a specific instance of a statistics value
         at a specific time."
    INDEX       {
        tmnxSysAppStats24HrsApplication,
        tmnxSysAppStats24HrsType,
        tmnxSysAppStats24HrsIndex
    }
    ::= { tmnxSysAppStats24HrsTable 1 }

TmnxSysAppStats24HrsEntry        ::= SEQUENCE
{
    tmnxSysAppStats24HrsApplication  TmnxSysLicenseApplication,
    tmnxSysAppStats24HrsType         TmnxSysLicenseAppStatsType,
    tmnxSysAppStats24HrsIndex        Unsigned32,
    tmnxSysAppStats24HrsName         DisplayString,
    tmnxSysAppStats24HrsValue        CounterBasedGauge64,
    tmnxSysAppStats24HrsTime         DateAndTime
}

tmnxSysAppStats24HrsApplication  OBJECT-TYPE
    SYNTAX      TmnxSysLicenseApplication
    MAX-ACCESS  not-accessible
    STATUS      current
    DESCRIPTION
        "The value of tmnxSysAppStats24HrsApplication indicates the
         application."
    ::= { tmnxSysAppStats24HrsEntry 1 }

tmnxSysAppStats24HrsType         OBJECT-TYPE
    SYNTAX      TmnxSysLicenseAppStatsType
    MAX-ACCESS  not-accessible
    STATUS      current
    DESCRIPTION
        "The value of tmnxSysAppStats24HrsType indicates the meaning of the
         statistics in this conceptual row."
    ::= { tmnxSysAppStats24HrsEntry 2 }

tmnxSysAppStats24HrsIndex        OBJECT-TYPE
    SYNTAX      Unsigned32
    MAX-ACCESS  not-accessible
    STATUS      current
    DESCRIPTION
        "The value of tmnxSysAppStats24HrsIndex is a numerical index value
         generated by this system."
    ::= { tmnxSysAppStats24HrsEntry 3 }

tmnxSysAppStats24HrsName         OBJECT-TYPE
    SYNTAX      DisplayString (SIZE (1..64))
    MAX-ACCESS  read-only
    STATUS      current
    DESCRIPTION
        "The value of the object tmnxSysAppStats24HrsName indicates the
         human-readable identifier of the statistics contained in this
         conceptual row."
    ::= { tmnxSysAppStats24HrsEntry 4 }

tmnxSysAppStats24HrsValue        OBJECT-TYPE
    SYNTAX      CounterBasedGauge64
    MAX-ACCESS  read-only
    STATUS      current
    DESCRIPTION
        "The value of the object tmnxSysAppStats24HrsValue indicates the value
         of the statistics contained in this conceptual row."
    ::= { tmnxSysAppStats24HrsEntry 5 }

tmnxSysAppStats24HrsTime         OBJECT-TYPE
    SYNTAX      DateAndTime (SIZE (11))
    MAX-ACCESS  read-only
    STATUS      current
    DESCRIPTION
        "The value of the object tmnxSysAppStats24HrsTime indicates the time
         the system measured the value of tmnxSysAppStats24HrsValue."
    ::= { tmnxSysAppStats24HrsEntry 6 }

tmnxSysAppStatsWeekTable         OBJECT-TYPE
    SYNTAX      SEQUENCE OF TmnxSysAppStatsWeekEntry
    MAX-ACCESS  not-accessible
    STATUS      current
    DESCRIPTION
        "The tmnxSysAppStatsWeekTable contains statistics about a virtual
         machine application collected periodically during the last week."
    ::= { tmnxSysLicenseStatistics 2 }

tmnxSysAppStatsWeekEntry         OBJECT-TYPE
    SYNTAX      TmnxSysAppStatsWeekEntry
    MAX-ACCESS  not-accessible
    STATUS      current
    DESCRIPTION
        "Each conceptual row contains a specific instance of a statistics value
         associated with a specific 24 hours period."
    INDEX       {
        tmnxSysAppStatsWeekApplication,
        tmnxSysAppStatsWeekType,
        tmnxSysAppStatsWeekIndex
    }
    ::= { tmnxSysAppStatsWeekTable 1 }

TmnxSysAppStatsWeekEntry         ::= SEQUENCE
{
    tmnxSysAppStatsWeekApplication   TmnxSysLicenseApplication,
    tmnxSysAppStatsWeekType          TmnxSysLicenseAppStatsType,
    tmnxSysAppStatsWeekIndex         Unsigned32,
    tmnxSysAppStatsWeekName          DisplayString,
    tmnxSysAppStatsWeekAverage       CounterBasedGauge64,
    tmnxSysAppStatsWeekPeak          CounterBasedGauge64,
    tmnxSysAppStatsWeekTime          DateAndTime
}

tmnxSysAppStatsWeekApplication   OBJECT-TYPE
    SYNTAX      TmnxSysLicenseApplication
    MAX-ACCESS  not-accessible
    STATUS      current
    DESCRIPTION
        "The value of tmnxSysAppStatsWeekApplication indicates the application."
    ::= { tmnxSysAppStatsWeekEntry 1 }

tmnxSysAppStatsWeekType          OBJECT-TYPE
    SYNTAX      TmnxSysLicenseAppStatsType
    MAX-ACCESS  not-accessible
    STATUS      current
    DESCRIPTION
        "The value of tmnxSysAppStatsWeekType indicates the meaning of the
         statistics in this conceptual row."
    ::= { tmnxSysAppStatsWeekEntry 2 }

tmnxSysAppStatsWeekIndex         OBJECT-TYPE
    SYNTAX      Unsigned32
    MAX-ACCESS  not-accessible
    STATUS      current
    DESCRIPTION
        "The value of tmnxSysAppStatsWeekIndex is a numerical index value
         generated by this system."
    ::= { tmnxSysAppStatsWeekEntry 3 }

tmnxSysAppStatsWeekName          OBJECT-TYPE
    SYNTAX      DisplayString (SIZE (1..64))
    MAX-ACCESS  read-only
    STATUS      current
    DESCRIPTION
        "The value of the object tmnxSysAppStatsWeekName indicates the
         human-readable identifier of the statistics contained in this
         conceptual row."
    ::= { tmnxSysAppStatsWeekEntry 4 }

tmnxSysAppStatsWeekAverage       OBJECT-TYPE
    SYNTAX      CounterBasedGauge64
    MAX-ACCESS  read-only
    STATUS      current
    DESCRIPTION
        "The value of the object tmnxSysAppStatsWeekAverage indicates the
         average value of the statistics contained in this conceptual row for
         this period of 24 hours."
    ::= { tmnxSysAppStatsWeekEntry 5 }

tmnxSysAppStatsWeekPeak          OBJECT-TYPE
    SYNTAX      CounterBasedGauge64
    MAX-ACCESS  read-only
    STATUS      current
    DESCRIPTION
        "The value of the object tmnxSysAppStatsWeekPeak indicates the peak
         value of the statistics contained in this conceptual row for this
         period of 24 hours."
    ::= { tmnxSysAppStatsWeekEntry 6 }

tmnxSysAppStatsWeekTime          OBJECT-TYPE
    SYNTAX      DateAndTime (SIZE (11))
    MAX-ACCESS  read-only
    STATUS      current
    DESCRIPTION
        "The value of the object tmnxSysAppStatsWeekTime indicates the time the
         system determined the values of tmnxSysAppStatsWeekAverage and
         tmnxSysAppStatsWeekPeak."
    ::= { tmnxSysAppStatsWeekEntry 7 }

tmnxSysAppStatsPeakTable         OBJECT-TYPE
    SYNTAX      SEQUENCE OF TmnxSysAppStatsPeakEntry
    MAX-ACCESS  not-accessible
    STATUS      current
    DESCRIPTION
        "The tmnxSysAppStatsPeakTable contains peak values of statistics about
         a virtual machine application."
    ::= { tmnxSysLicenseStatistics 3 }

tmnxSysAppStatsPeakEntry         OBJECT-TYPE
    SYNTAX      TmnxSysAppStatsPeakEntry
    MAX-ACCESS  not-accessible
    STATUS      current
    DESCRIPTION
        "Each conceptual row contains a peak value of a statistic about a
         virtual machine application."
    INDEX       {
        tmnxSysAppStatsPeakApplication,
        tmnxSysAppStatsPeakType
    }
    ::= { tmnxSysAppStatsPeakTable 1 }

TmnxSysAppStatsPeakEntry         ::= SEQUENCE
{
    tmnxSysAppStatsPeakApplication   TmnxSysLicenseApplication,
    tmnxSysAppStatsPeakType          TmnxSysLicenseAppStatsType,
    tmnxSysAppStatsPeakName          DisplayString,
    tmnxSysAppStatsPeakValue         CounterBasedGauge64,
    tmnxSysAppStatsPeakTime          DateAndTime
}

tmnxSysAppStatsPeakApplication   OBJECT-TYPE
    SYNTAX      TmnxSysLicenseApplication
    MAX-ACCESS  not-accessible
    STATUS      current
    DESCRIPTION
        "The value of tmnxSysAppStatsPeakApplication indicates the application."
    ::= { tmnxSysAppStatsPeakEntry 1 }

tmnxSysAppStatsPeakType          OBJECT-TYPE
    SYNTAX      TmnxSysLicenseAppStatsType
    MAX-ACCESS  not-accessible
    STATUS      current
    DESCRIPTION
        "The value of tmnxSysAppStatsPeakType indicates the meaning of the
         statistics in this conceptual row."
    ::= { tmnxSysAppStatsPeakEntry 2 }

tmnxSysAppStatsPeakName          OBJECT-TYPE
    SYNTAX      DisplayString (SIZE (1..64))
    MAX-ACCESS  read-only
    STATUS      current
    DESCRIPTION
        "The value of the object tmnxSysAppStatsPeakName indicates the
         human-readable identifier of the statistics contained in this
         conceptual row."
    ::= { tmnxSysAppStatsPeakEntry 3 }

tmnxSysAppStatsPeakValue         OBJECT-TYPE
    SYNTAX      CounterBasedGauge64
    MAX-ACCESS  read-only
    STATUS      current
    DESCRIPTION
        "The value of the object tmnxSysAppStatsPeakValue indicates the value
         of the statistics contained in this conceptual row."
    ::= { tmnxSysAppStatsPeakEntry 4 }

tmnxSysAppStatsPeakTime          OBJECT-TYPE
    SYNTAX      DateAndTime (SIZE (11))
    MAX-ACCESS  read-only
    STATUS      current
    DESCRIPTION
        "The value of the object tmnxSysAppStatsPeakTime indicates the time the
         system measured the value of tmnxSysAppStatsPeakValue."
    ::= { tmnxSysAppStatsPeakEntry 5 }

tmnxSysAppStats48HrsTable        OBJECT-TYPE
    SYNTAX      SEQUENCE OF TmnxSysAppStats48HrsEntry
    MAX-ACCESS  not-accessible
    STATUS      current
    DESCRIPTION
        "The tmnxSysAppStats48HrsTable contains statistics about a virtual
         machine application collected periodically 24 to 48 hours ago."
    ::= { tmnxSysLicenseStatistics 4 }

tmnxSysAppStats48HrsEntry        OBJECT-TYPE
    SYNTAX      TmnxSysAppStats48HrsEntry
    MAX-ACCESS  not-accessible
    STATUS      current
    DESCRIPTION
        "Each conceptual row contains a specific instance of a statistics value
         at a specific time."
    INDEX       {
        tmnxSysAppStats48HrsApplication,
        tmnxSysAppStats48HrsType,
        tmnxSysAppStats48HrsIndex
    }
    ::= { tmnxSysAppStats48HrsTable 1 }

TmnxSysAppStats48HrsEntry        ::= SEQUENCE
{
    tmnxSysAppStats48HrsApplication  TmnxSysLicenseApplication,
    tmnxSysAppStats48HrsType         TmnxSysLicenseAppStatsType,
    tmnxSysAppStats48HrsIndex        Unsigned32,
    tmnxSysAppStats48HrsName         DisplayString,
    tmnxSysAppStats48HrsValue        CounterBasedGauge64,
    tmnxSysAppStats48HrsTime         DateAndTime
}

tmnxSysAppStats48HrsApplication  OBJECT-TYPE
    SYNTAX      TmnxSysLicenseApplication
    MAX-ACCESS  not-accessible
    STATUS      current
    DESCRIPTION
        "The value of tmnxSysAppStats48HrsApplication indicates the
         application."
    ::= { tmnxSysAppStats48HrsEntry 1 }

tmnxSysAppStats48HrsType         OBJECT-TYPE
    SYNTAX      TmnxSysLicenseAppStatsType
    MAX-ACCESS  not-accessible
    STATUS      current
    DESCRIPTION
        "The value of tmnxSysAppStats48HrsType indicates the meaning of the
         statistics in this conceptual row."
    ::= { tmnxSysAppStats48HrsEntry 2 }

tmnxSysAppStats48HrsIndex        OBJECT-TYPE
    SYNTAX      Unsigned32
    MAX-ACCESS  not-accessible
    STATUS      current
    DESCRIPTION
        "The value of tmnxSysAppStats48HrsIndex is a numerical index value
         generated by this system."
    ::= { tmnxSysAppStats48HrsEntry 3 }

tmnxSysAppStats48HrsName         OBJECT-TYPE
    SYNTAX      DisplayString (SIZE (1..64))
    MAX-ACCESS  read-only
    STATUS      current
    DESCRIPTION
        "The value of the object tmnxSysAppStats48HrsName indicates the
         human-readable identifier of the statistics contained in this
         conceptual row."
    ::= { tmnxSysAppStats48HrsEntry 4 }

tmnxSysAppStats48HrsValue        OBJECT-TYPE
    SYNTAX      CounterBasedGauge64
    MAX-ACCESS  read-only
    STATUS      current
    DESCRIPTION
        "The value of the object tmnxSysAppStats48HrsValue indicates the value
         of the statistics contained in this conceptual row."
    ::= { tmnxSysAppStats48HrsEntry 5 }

tmnxSysAppStats48HrsTime         OBJECT-TYPE
    SYNTAX      DateAndTime (SIZE (11))
    MAX-ACCESS  read-only
    STATUS      current
    DESCRIPTION
        "The value of the object tmnxSysAppStats48HrsTime indicates the time
         the system measured the value of tmnxSysAppStats48HrsValue."
    ::= { tmnxSysAppStats48HrsEntry 6 }

tmnxSysLicensingProduct          OBJECT-TYPE
    SYNTAX      TItemDescription
    MAX-ACCESS  read-only
    STATUS      current
    DESCRIPTION
        "The value of tmnxSysLicensingProduct indicates the type of license
         expected based on the running system."
    ::= { tmnxSysLicense 21 }

tmnxSysLicensingUuid             OBJECT-TYPE
    SYNTAX      TmnxUuid
    MAX-ACCESS  read-only
    STATUS      current
    DESCRIPTION
        "The value of tmnxSysLicensingUuid indicates the Universally Unique
         Identifier (UUID) being used to match license."
    ::= { tmnxSysLicense 22 }

tmnxSysFibInfo                   OBJECT IDENTIFIER ::= { tmnxSysObjs 31 }

tmnxSysFibSelective              OBJECT-TYPE
    SYNTAX      TruthValue
    MAX-ACCESS  read-write
    STATUS      current
    DESCRIPTION
        "The value of tmnxSysFibSelective specifies whether selective FIB is
         enabled in the system.

         If the value of tmnxSysFibSelective is set to false, then all active
         routes are installed on all line cards.

         If the value of tmnxSysFibSelective is set to true, then a line card
         installs a particular IP route only if that route is relevant to the
         card based on the current configuration of interfaces and services."
    DEFVAL      { false }
    ::= { tmnxSysFibInfo 1 }

tmnxSysSnmpSrcAccessObjs         OBJECT IDENTIFIER ::= { tmnxSysObjs 32 }

tmnxSysSnmpConfigObjs            OBJECT IDENTIFIER ::= { tmnxSysSnmpSrcAccessObjs 1 }

tmnxSysSnmpSrcAccessTblLstChgd   OBJECT-TYPE
    SYNTAX      TimeStamp
    MAX-ACCESS  read-only
    STATUS      current
    DESCRIPTION
        "The value of tmnxSysSnmpSrcAccessTblLstChgd indicates the sysUpTime at
         the time of the last modification to tmnxSysSnmpSrcAccessLstTable by
         adding, deleting an entry or change to a writable object in the table.

         If no changes were made to the table since the last re-initialization
         of the local network management subsystem, then this object contains a
         zero value."
    ::= { tmnxSysSnmpConfigObjs 1 }

tmnxSysSnmpSrcAccessLstTable     OBJECT-TYPE
    SYNTAX      SEQUENCE OF TmnxSysSnmpSrcAccessLstEntry
    MAX-ACCESS  not-accessible
    STATUS      current
    DESCRIPTION
        "The tmnxSysSnmpSrcAccessLstTable contains objects for creating entries
         corresponding to source access list."
    ::= { tmnxSysSnmpConfigObjs 2 }

tmnxSysSnmpSrcAccessLstEntry     OBJECT-TYPE
    SYNTAX      TmnxSysSnmpSrcAccessLstEntry
    MAX-ACCESS  not-accessible
    STATUS      current
    DESCRIPTION
        "The tmnxSysSnmpSrcAccessLstEntry contains configuration items for
         creating src-access-list."
    INDEX       { IMPLIED tmnxSysSnmpSrcAccessLstName }
    ::= { tmnxSysSnmpSrcAccessLstTable 1 }

TmnxSysSnmpSrcAccessLstEntry     ::= SEQUENCE
{
    tmnxSysSnmpSrcAccessLstName      TNamedItem,
    tmnxSysSnmpSrcAccessLstRowStatus RowStatus,
    tmnxSysSnmpSrcAccessLstLastChg   TimeStamp
}

tmnxSysSnmpSrcAccessLstName      OBJECT-TYPE
    SYNTAX      TNamedItem
    MAX-ACCESS  not-accessible
    STATUS      current
    DESCRIPTION
        "The value of tmnxSysSnmpSrcAccessLstName specifies the name given to
         this src-access-list."
    ::= { tmnxSysSnmpSrcAccessLstEntry 1 }

tmnxSysSnmpSrcAccessLstRowStatus OBJECT-TYPE
    SYNTAX      RowStatus
    MAX-ACCESS  read-create
    STATUS      current
    DESCRIPTION
        "The value of tmnxSysSnmpSrcAccessLstRowStatus specifies the row status
         used for creation and deletion of src-access-list entries."
    ::= { tmnxSysSnmpSrcAccessLstEntry 2 }

tmnxSysSnmpSrcAccessLstLastChg   OBJECT-TYPE
    SYNTAX      TimeStamp
    MAX-ACCESS  read-only
    STATUS      current
    DESCRIPTION
        "The value of tmnxSysSnmpSrcAccessLstLastChg indicates the sysUpTime at
         the time of the last modification of this row.

         If no changes were made to the row since the last re-initialization of
         the local network management subsystem, then this object contains the
         value zero."
    ::= { tmnxSysSnmpSrcAccessLstEntry 3 }

tmnxSysSnmpStatsObjs             OBJECT IDENTIFIER ::= { tmnxSysSnmpSrcAccessObjs 2 }

tmnxSysSnmpCommunityStatsTable   OBJECT-TYPE
    SYNTAX      SEQUENCE OF TmnxSysSnmpCommunityStatsEntry
    MAX-ACCESS  not-accessible
    STATUS      current
    DESCRIPTION
        "The tmnxSysSnmpCommunityStatsTable contains statistics for SNMP
         Community."
    ::= { tmnxSysSnmpStatsObjs 1 }

tmnxSysSnmpCommunityStatsEntry   OBJECT-TYPE
    SYNTAX      TmnxSysSnmpCommunityStatsEntry
    MAX-ACCESS  not-accessible
    STATUS      current
    DESCRIPTION
        "Each row entry represents a collection of statistics for each SNMP
         Community within a virtual router.

         Entries cannot be created and deleted via SNMP SET operations."
    AUGMENTS    { snmpCommunityEntry }
    ::= { tmnxSysSnmpCommunityStatsTable 1 }

TmnxSysSnmpCommunityStatsEntry   ::= SEQUENCE
{ tmnxSysSnmpCommunityPktDropped   Gauge32 }

tmnxSysSnmpCommunityPktDropped   OBJECT-TYPE
    SYNTAX      Gauge32
    MAX-ACCESS  read-only
    STATUS      current
    DESCRIPTION
        "The value of tmnxSysSnmpCommunityPktDropped indicates the total number
         of packets dropped when a SNMP GET request has been made."
    ::= { tmnxSysSnmpCommunityStatsEntry 1 }

tmnxSysMgmtProtocolObjs          OBJECT IDENTIFIER ::= { tmnxSysObjs 33 }

tmnxSysMgmtProtocolTblLstChng    OBJECT-TYPE
    SYNTAX      TimeStamp
    MAX-ACCESS  read-only
    STATUS      current
    DESCRIPTION
        "The value of tmnxSysMgmtProtocolTblLstChng indicates the sysUpTime at
         the time of the last modification to tmnxSysMgmtProtocolTable by
         change to a writable object in the table.

         If no changes were made to the table since the last re-initialization
         of the local network management subsystem, then this object contains a
         zero value."
    ::= { tmnxSysMgmtProtocolObjs 1 }

tmnxSysMgmtProtocolTable         OBJECT-TYPE
    SYNTAX      SEQUENCE OF TmnxSysMgmtProtocolEntry
    MAX-ACCESS  not-accessible
    STATUS      current
    DESCRIPTION
        "The tmnxSysMgmtProtocolTable contains objects for managing the
         capabilities of the different network management protocols."
    ::= { tmnxSysMgmtProtocolObjs 2 }

tmnxSysMgmtProtocolEntry         OBJECT-TYPE
    SYNTAX      TmnxSysMgmtProtocolEntry
    MAX-ACCESS  not-accessible
    STATUS      current
    DESCRIPTION
        "The tmnxSysMgmtProtocolEntry contains configuration items for managing
         the different network management protocols.

         Entries in this table cannot be created or deleted."
    INDEX       { tmnxSysMgmtProtocol }
    ::= { tmnxSysMgmtProtocolTable 1 }

TmnxSysMgmtProtocolEntry         ::= SEQUENCE
{
    tmnxSysMgmtProtocol              INTEGER,
    tmnxSysMgmtProtLastChange        TimeStamp,
    tmnxSysMgmtAllowImmediateChange  TruthValue,
    tmnxSysMgmtCliEngine1            TmnxCliEngine,
    tmnxSysMgmtCliEngine2            TmnxCliEngine
}

tmnxSysMgmtProtocol              OBJECT-TYPE
    SYNTAX      INTEGER {
        cli (0)
    }
    MAX-ACCESS  not-accessible
    STATUS      current
    DESCRIPTION
        "The value of tmnxSysMgmtProtocol specifies the name of the network
         management protocol to which this row applies."
    ::= { tmnxSysMgmtProtocolEntry 1 }

tmnxSysMgmtProtLastChange        OBJECT-TYPE
    SYNTAX      TimeStamp
    MAX-ACCESS  read-only
    STATUS      current
    DESCRIPTION
        "The value of tmnxSysMgmtProtLastChange indicates the sysUpTime at the
         time of the last modification of this row.

         If no changes were made to the row since the last re-initialization of
         the local network management subsystem, then this object contains the
         value zero."
    ::= { tmnxSysMgmtProtocolEntry 2 }

tmnxSysMgmtAllowImmediateChange  OBJECT-TYPE
    SYNTAX      TruthValue
    MAX-ACCESS  read-create
    STATUS      current
    DESCRIPTION
        "The value of tmnxSysMgmtAllowImmediateChange specifies whether the
         user is allowed to make direct changes to the configuration, or
         whether all changes need to be applied through use of a candidate
         config."
    DEFVAL      { true }
    ::= { tmnxSysMgmtProtocolEntry 3 }

tmnxSysMgmtCliEngine1            OBJECT-TYPE
    SYNTAX      TmnxCliEngine
    MAX-ACCESS  read-create
    STATUS      current
    DESCRIPTION
        "The value of tmnxSysMgmtCliEngine1 specifies the CLI engine that is
         active when a user logs in.

         Value systemDerived specifies that the CLI engine is derived
         from the current value of tmnxSysMgmtIfWriteMode:
           tmnxSysMgmtIfWriteMode  ->  CLI engine
           ----------------------      ---------------------
           classic                 ->  Classic CLI
           modelDriven             ->  MD CLI
           mixed                   ->  MD CLI

         Both tmnxSysMgmtCliEngine1 and tmnxSysMgmtCliEngine2 must be present
         in the same set request."
    DEFVAL      { systemDerived }
    ::= { tmnxSysMgmtProtocolEntry 4 }

tmnxSysMgmtCliEngine2            OBJECT-TYPE
    SYNTAX      TmnxCliEngine
    MAX-ACCESS  read-create
    STATUS      current
    DESCRIPTION
        "The value of tmnxSysMgmtCliEngine2 specifies the secondary CLI engine
         that is accessible to a logged-in user.

         Value systemDerived specifies that the user does not have access to
         secondary engine (i.e.: can only access engine specified by
         tmnxSysMgmtCliEngine1).

         Values other than systemDerived are used only if tmnxSysMgmtCliEngine1
         also has value other than systemDerived and must differ from that
         value.

         Both tmnxSysMgmtCliEngine1 and tmnxSysMgmtCliEngine2 must be present
         in the same set request."
    DEFVAL      { systemDerived }
    ::= { tmnxSysMgmtProtocolEntry 5 }

tmnxSysFileTransProfObjs         OBJECT IDENTIFIER ::= { tmnxSysObjs 34 }

tmnxSysFileTransProfTableLstChgd OBJECT-TYPE
    SYNTAX      TimeStamp
    MAX-ACCESS  read-only
    STATUS      current
    DESCRIPTION
        "The value of tmnxSysFileTransProfTableLstChgd indicates the time,
         since system startup, when tmnxSysFileTransProfTable last changed
         configuration.

         A value of zero indicates that no changes were made to this table
         since the system was last initialized."
    ::= { tmnxSysFileTransProfObjs 1 }

tmnxSysFileTransProfTable        OBJECT-TYPE
    SYNTAX      SEQUENCE OF TmnxSysFileTransProfEntry
    MAX-ACCESS  not-accessible
    STATUS      current
    DESCRIPTION
        "The tmnxSysFileTransProfTable contains objects used to configure
         instances of the file transmission profile, which are used by a device
         to download files from a server (e.g. File Transfer Protocol (FTP)
         server or Hypertext Transfer Protocol(HTTP) server).

         A file transmission profile specifies 1) the local configuration for
         sending and receiving a file in an Nokia SROS device; and 2) the
         behaviours of the device when the transmission fails.

         Usage example:
             Auto Certificate Revocation List (CRL) retrieval: downloading
             CRL from a FTP or an HTTP server to an Nokia SROS device.

         Entries in this table are created and deleted via SNMP set operations
         to tmnxSysFileTransProfRowStatus."
    ::= { tmnxSysFileTransProfObjs 2 }

tmnxSysFileTransProfEntry        OBJECT-TYPE
    SYNTAX      TmnxSysFileTransProfEntry
    MAX-ACCESS  not-accessible
    STATUS      current
    DESCRIPTION
        "Each tmnxSysFileTransProfEntry contains the configuration for one file
         transmission profile."
    INDEX       { tmnxSysFileTransProfName }
    ::= { tmnxSysFileTransProfTable 1 }

TmnxSysFileTransProfEntry        ::= SEQUENCE
{
    tmnxSysFileTransProfName         TNamedItem,
    tmnxSysFileTransProfRowStatus    RowStatus,
    tmnxSysFileTransProfLastChanged  TimeStamp,
    tmnxSysFileTransProfRtrId        TmnxVRtrIDOrZero,
    tmnxSysFileTransProfSvcId        TmnxServId,
    tmnxSysFileTransProfSrcAddrV4T   InetAddressType,
    tmnxSysFileTransProfSrcAddrV4    InetAddress,
    tmnxSysFileTransProfSrcAddrV6T   InetAddressType,
    tmnxSysFileTransProfSrcAddrV6    InetAddress,
    tmnxSysFileTransProfTimeout      Unsigned32,
    tmnxSysFileTransProfRetry        Unsigned32,
    tmnxSysFileTransProfRedirection  Unsigned32,
    tmnxSysFileTransProfSvcName      TLNamedItemOrEmpty
}

tmnxSysFileTransProfName         OBJECT-TYPE
    SYNTAX      TNamedItem
    MAX-ACCESS  not-accessible
    STATUS      current
    DESCRIPTION
        "The value of tmnxSysFileTransProfName uniquely specifies one file
         transmission profile configured on this system."
    ::= { tmnxSysFileTransProfEntry 1 }

tmnxSysFileTransProfRowStatus    OBJECT-TYPE
    SYNTAX      RowStatus
    MAX-ACCESS  read-create
    STATUS      current
    DESCRIPTION
        "The value of tmnxSysFileTransProfRowStatus specifies the status of
         this row. It is used to create and delete row entries in
         tmnxSysFileTransProfTable."
    ::= { tmnxSysFileTransProfEntry 2 }

tmnxSysFileTransProfLastChanged  OBJECT-TYPE
    SYNTAX      TimeStamp
    MAX-ACCESS  read-only
    STATUS      current
    DESCRIPTION
        "The value of tmnxSysFileTransProfLastChanged indicates the time, since
         system startup, that the configuration of this row was created or
         modified."
    ::= { tmnxSysFileTransProfEntry 3 }

tmnxSysFileTransProfRtrId        OBJECT-TYPE
    SYNTAX      TmnxVRtrIDOrZero
    MAX-ACCESS  read-create
    STATUS      current
    DESCRIPTION
        "The value of tmnxSysFileTransProfRtrId specifies the virtual router
         instance. The file transmission connection(s) will be established
         between the virtual router and a server (e.g. FTP or HTTP server).

         Exactly one of tmnxSysFileTransProfSvcName, tmnxSysFileTransProfSvcId
         and tmnxSysFileTransProfRtrId must be configured to a non-default
         value. For example, when the value of tmnxSysFileTransProfRtrId is
         zero, the virtual router must be specified using
         tmnxSysFileTransProfSvcId or tmnxSysFileTransProfSvcName.

         Only those IDs corresponding to the 'Base' and 'management' virtual
         routers may be set in this object. Refer to
         TIMETRA-VRTR-MIB.mib::vRtrName."
    DEFVAL      { 1 }
    ::= { tmnxSysFileTransProfEntry 4 }

tmnxSysFileTransProfSvcId        OBJECT-TYPE
    SYNTAX      TmnxServId (0..2147483647)
    MAX-ACCESS  read-create
    STATUS      current
    DESCRIPTION
        "The value of tmnxSysFileTransProfSvcId specifies the service
         identifier for a virtual router. The file transmission connection(s)
         will be established between the virtual router and a server (e.g. FTP
         or HTTP server).

         Exactly one of tmnxSysFileTransProfSvcName, tmnxSysFileTransProfSvcId
         and tmnxSysFileTransProfRtrId must be configured to a non-default
         value. For example, when the value of tmnxSysFileTransProfSvcId is
         zero, the virtual router must be specified using
         tmnxSysFileTransProfSvcName or tmnxSysFileTransProfRtrId.

         Only VPRN service IDs are allowed."
    DEFVAL      { 0 }
    ::= { tmnxSysFileTransProfEntry 5 }

tmnxSysFileTransProfSrcAddrV4T   OBJECT-TYPE
    SYNTAX      InetAddressType
    MAX-ACCESS  read-create
    STATUS      current
    DESCRIPTION
        "The value of tmnxSysFileTransProfSrcAddrV4T specifies the IP address
         type of tmnxSysFileTransProfSrcAddrV4.

         The value of tmnxSysFileTransProfSrcAddrV4T can be either of 'ipv4(1)'
         or 'unknown (0)'.

         The value of 'unknown(0)' specifies no IPv4 source address is
         configured."
    DEFVAL      { unknown }
    ::= { tmnxSysFileTransProfEntry 6 }

tmnxSysFileTransProfSrcAddrV4    OBJECT-TYPE
    SYNTAX      InetAddress (SIZE (0|4))
    MAX-ACCESS  read-create
    STATUS      current
    DESCRIPTION
        "The value of tmnxSysFileTransProfSrcAddrV4 specifies the IPv4 source
         address specified in tmnxSysFileTransProfRtrId.

         The value of an empty string specifies no IPv4 source address is
         configured."
    DEFVAL      { ''H }
    ::= { tmnxSysFileTransProfEntry 7 }

tmnxSysFileTransProfSrcAddrV6T   OBJECT-TYPE
    SYNTAX      InetAddressType
    MAX-ACCESS  read-create
    STATUS      current
    DESCRIPTION
        "The value of tmnxSysFileTransProfSrcAddrV6T specifies the IP address
         type of tmnxSysFileTransProfSrcAddrV6.

         The value of tmnxSysFileTransProfSrcAddrV6T can be either of 'ipv6(2)'
         or 'unknown (0)'.

         The value of 'unknown(0)' specifies no IPv6 source address is
         configured."
    DEFVAL      { unknown }
    ::= { tmnxSysFileTransProfEntry 8 }

tmnxSysFileTransProfSrcAddrV6    OBJECT-TYPE
    SYNTAX      InetAddress (SIZE (0|16))
    MAX-ACCESS  read-create
    STATUS      current
    DESCRIPTION
        "The value of tmnxSysFileTransProfSrcAddrV6 specifies the IPv6 source
         address specified in tmnxSysFileTransProfRtrId.

         The value of an empty string specifies no IPv6 source address is
         configured."
    DEFVAL      { ''H }
    ::= { tmnxSysFileTransProfEntry 9 }

tmnxSysFileTransProfTimeout      OBJECT-TYPE
    SYNTAX      Unsigned32 (1..3600)
    UNITS       "seconds"
    MAX-ACCESS  read-create
    STATUS      current
    DESCRIPTION
        "The value of tmnxSysFileTransProfTimeout specifies the connection
         timeout (in seconds) for the file transmission.

         The timeout is the maximum waiting time to receive any data from the
         server (e.g. FTP or HTTP server)."
    DEFVAL      { 60 }
    ::= { tmnxSysFileTransProfEntry 10 }

tmnxSysFileTransProfRetry        OBJECT-TYPE
    SYNTAX      Unsigned32 (0..256)
    MAX-ACCESS  read-create
    STATUS      current
    DESCRIPTION
        "The value of tmnxSysFileTransProfRetry specifies the number of retries
         of the file transmission profile.

         When the virtual router does not receive any data from a server (e.g.
         FTP or HTTP server) after the configured tmnxSysFileTransProfTimeout
         interval, the router may repeat the request to the server. The number
         of retries specifies the maximum number of repeated requests.

         Virtual router instances are configured using
         tmnxSysFileTransProfRtrId.

         The value of zero specifies that the request should not be resent by
         the virtual router after the configured tmnxSysFileTransProfTimeout
         interval elapsed."
    DEFVAL      { 0 }
    ::= { tmnxSysFileTransProfEntry 11 }

tmnxSysFileTransProfRedirection  OBJECT-TYPE
    SYNTAX      Unsigned32 (0..8)
    MAX-ACCESS  read-create
    STATUS      current
    DESCRIPTION
        "The value of tmnxSysFileTransProfRedirection specifies the maximum
         level of redirection of the file transmission profile.

         The virtual router may send a new request to another server if the
         requested resources are not available (e.g. temporarily available to
         another server).

         Usage example:
           When a virtual router receives an HTTP response with status code of
           redirection 3xx (e.g. 301 Moved Permanently), the router may send
           a new request to another location. The level of redirection specifies
           the maximum number of new requests that can be sent by a virtual
           router.

         For any file transmission protocols (e.g. FTP), which do not support
         redirection, the value of tmnxSysFileTransProfRedirection will be
         ignored.

         The value of zero specifies that no new request should be sent by a
         virtual router to another server."
    REFERENCE
        "RFC 2616, 'Hypertext Transfer Protocol -- HTTP/1.1', IETF, June 1999,
         section 10.3 'Redirection 3xx'."
    DEFVAL      { 0 }
    ::= { tmnxSysFileTransProfEntry 12 }

tmnxSysFileTransProfSvcName      OBJECT-TYPE
    SYNTAX      TLNamedItemOrEmpty
    MAX-ACCESS  read-create
    STATUS      current
    DESCRIPTION
        "The value of tmnxSysFileTransProfSvcName specifies the service name
         for a virtual router. The file transmission connection(s) will be
         established between the virtual router and a server (e.g. FTP or HTTP
         server).

         Exactly one of tmnxSysFileTransProfSvcName, tmnxSysFileTransProfSvcId
         and tmnxSysFileTransProfRtrId must be configured to a non-default
         value. For example, when the value of tmnxSysFileTransProfSvcName is
         an empty string, the virtual router must be specified using
         tmnxSysFileTransProfSvcId or tmnxSysFileTransProfRtrId.

         Only VPRN service names are allowed."
    DEFVAL      { ''H }
    ::= { tmnxSysFileTransProfEntry 13 }

tmnxEhsExtObjs                   OBJECT IDENTIFIER ::= { tmnxSysObjs 35 }

tmnxSmLaunchExtTable             OBJECT-TYPE
    SYNTAX      SEQUENCE OF TmnxSmLaunchExtEntry
    MAX-ACCESS  not-accessible
    STATUS      current
    DESCRIPTION
        "The tmnxSmLaunchExtTable is an extension of the
         DISMAN-SCRIPT-MIB::smLaunchTable."
    ::= { tmnxEhsExtObjs 1 }

tmnxSmLaunchExtEntry             OBJECT-TYPE
    SYNTAX      TmnxSmLaunchExtEntry
    MAX-ACCESS  not-accessible
    STATUS      current
    DESCRIPTION
        "Each row entry represents contains additional attributes for the
         smLaunchEntry.

         Entries cannot be created and deleted via SNMP SET operations."
    AUGMENTS    { smLaunchEntry }
    ::= { tmnxSmLaunchExtTable 1 }

TmnxSmLaunchExtEntry             ::= SEQUENCE
{
    tmnxSmLaunchExtAuthType          TmnxScriptAuthType,
    tmnxSmLaunchExtLockOverride      TruthValue
}

tmnxSmLaunchExtAuthType          OBJECT-TYPE
    SYNTAX      TmnxScriptAuthType
    MAX-ACCESS  read-only
    STATUS      current
    DESCRIPTION
        "The value of tmnxSmLaunchExtAuthType indicates the module
         that last started a script by writing to
         DISMAN-SCRIPT-MIB::smLaunchStart.  If no script has yet
         been started the value 'none(0)' is returned."
    ::= { tmnxSmLaunchExtEntry 1 }

tmnxSmLaunchExtLockOverride      OBJECT-TYPE
    SYNTAX      TruthValue
    MAX-ACCESS  read-create
    STATUS      current
    DESCRIPTION
        "If true script run is able to overide explicit lock of MD database.
         Hence giving priority to EHS/Cron script runs."
    DEFVAL      { false }
    ::= { tmnxSmLaunchExtEntry 2 }

tmnxSmRunExtTable                OBJECT-TYPE
    SYNTAX      SEQUENCE OF TmnxSmRunExtEntry
    MAX-ACCESS  not-accessible
    STATUS      current
    DESCRIPTION
        "The tmnxSmRunExtTable is an extension of the
         DISMAN-SCRIPT-MIB::smRunTable."
    ::= { tmnxEhsExtObjs 2 }

tmnxSmRunExtEntry                OBJECT-TYPE
    SYNTAX      TmnxSmRunExtEntry
    MAX-ACCESS  not-accessible
    STATUS      current
    DESCRIPTION
        "Each row entry represents contains additional attributes for the
         smRunEntry.

         Entries cannot be created and deleted via SNMP SET operations."
    AUGMENTS    { smRunEntry }
    ::= { tmnxSmRunExtTable 1 }

TmnxSmRunExtEntry                ::= SEQUENCE
{
    tmnxSmRunExtAuthType             TmnxScriptAuthType,
    tmnxSmRunExtUserName             TNamedItemOrEmpty
}

tmnxSmRunExtAuthType             OBJECT-TYPE
    SYNTAX      TmnxScriptAuthType
    MAX-ACCESS  read-only
    STATUS      current
    DESCRIPTION
        "The value of tmnxSmRunExtAuthType indicates the module
         that started this run of a script by writing to
         DISMAN-SCRIPT-MIB::smLaunchStart.  If no script has yet
         been started the value 'none(0)' is returned."
    ::= { tmnxSmRunExtEntry 1 }

tmnxSmRunExtUserName             OBJECT-TYPE
    SYNTAX      TNamedItemOrEmpty
    MAX-ACCESS  read-only
    STATUS      current
    DESCRIPTION
        "The value of tmnxSmRunExtUserName indicates the name of
         the user account used to check access to CLI commands while
         executing the script.  If no script has yet been started
         the empty string is returned."
    ::= { tmnxSmRunExtEntry 2 }

tmnxSmRunArgsTable               OBJECT-TYPE
    SYNTAX      SEQUENCE OF TmnxSmRunArgsEntry
    MAX-ACCESS  not-accessible
    STATUS      current
    DESCRIPTION
        "The tmnxSmRunArgsTable contains information pertaining to the
         arguments passed to the exec script."
    ::= { tmnxEhsExtObjs 3 }

tmnxSmRunArgsEntry               OBJECT-TYPE
    SYNTAX      TmnxSmRunArgsEntry
    MAX-ACCESS  not-accessible
    STATUS      current
    DESCRIPTION
        "The tmnxSmRunArgsEntry provides the argument information for a
         specified exec script."
    INDEX       {
        smLaunchOwner,
        smLaunchName,
        smRunIndex,
        tmnxSmRunEventArgIndex
    }
    ::= { tmnxSmRunArgsTable 1 }

TmnxSmRunArgsEntry               ::= SEQUENCE
{
    tmnxSmRunEventArgIndex           Unsigned32,
    tmnxSmRunEventArgName            TLNamedItem,
    tmnxSmRunEventArgValue           TItemDescription
}

tmnxSmRunEventArgIndex           OBJECT-TYPE
    SYNTAX      Unsigned32
    MAX-ACCESS  not-accessible
    STATUS      current
    DESCRIPTION
        "The value of tmnxSmRunEventArgIndex specifies the argument index
         number associated with a particular tmnxSmRunArgsEntry."
    ::= { tmnxSmRunArgsEntry 1 }

tmnxSmRunEventArgName            OBJECT-TYPE
    SYNTAX      TLNamedItem
    MAX-ACCESS  read-only
    STATUS      current
    DESCRIPTION
        "The value of tmnxSmRunEventArgName indicates the name of an argument
         passed to the exec script."
    ::= { tmnxSmRunArgsEntry 2 }

tmnxSmRunEventArgValue           OBJECT-TYPE
    SYNTAX      TItemDescription
    MAX-ACCESS  read-only
    STATUS      current
    DESCRIPTION
        "The value of tmnxSmRunEventArgValue indicates the ASCII printable
         contents of the specified argument passed to the exec script."
    ::= { tmnxSmRunArgsEntry 3 }

tmnxSysSwReposObjs               OBJECT IDENTIFIER ::= { tmnxSysObjs 36 }

tmnxSysSwReposTableLastChanged   OBJECT-TYPE
    SYNTAX      TimeStamp
    MAX-ACCESS  read-only
    STATUS      current
    DESCRIPTION
        "The value of tmnxSysSwReposTableLastChanged indicates the time, since
         system startup, when tmnxSysSoftwareRepositoryTable last changed
         configuration."
    ::= { tmnxSysSwReposObjs 1 }

tmnxSysSoftwareRepositoryTable   OBJECT-TYPE
    SYNTAX      SEQUENCE OF TmnxSysSoftwareRepositoryEntry
    MAX-ACCESS  not-accessible
    STATUS      current
    DESCRIPTION
        "The tmnxSysSoftwareRepositoryTable contains configuration information
         about the system software repositories for extension chassis."
    ::= { tmnxSysSwReposObjs 2 }

tmnxSysSoftwareRepositoryEntry   OBJECT-TYPE
    SYNTAX      TmnxSysSoftwareRepositoryEntry
    MAX-ACCESS  not-accessible
    STATUS      current
    DESCRIPTION
        "The tmnxSysSoftwareRepositoryEntry consists of the configurable
         objects for the system software repositories."
    INDEX       { tmnxSysSwReposName }
    ::= { tmnxSysSoftwareRepositoryTable 1 }

TmnxSysSoftwareRepositoryEntry   ::= SEQUENCE
{
    tmnxSysSwReposName               TNamedItem,
    tmnxSysSwReposRowStatus          RowStatus,
    tmnxSysSwReposLastChanged        TimeStamp,
    tmnxSysSwReposDescription        TItemDescription,
    tmnxSysSwReposPrimaryLocation    TmnxDisplayStringURL,
    tmnxSysSwReposSecondaryLocation  TmnxDisplayStringURL,
    tmnxSysSwReposTertiaryLocation   TmnxDisplayStringURL
}

tmnxSysSwReposName               OBJECT-TYPE
    SYNTAX      TNamedItem
    MAX-ACCESS  not-accessible
    STATUS      current
    DESCRIPTION
        "The value of tmnxSysSwReposName specifies a unique name which
         identifies the system software repository."
    ::= { tmnxSysSoftwareRepositoryEntry 1 }

tmnxSysSwReposRowStatus          OBJECT-TYPE
    SYNTAX      RowStatus
    MAX-ACCESS  read-create
    STATUS      current
    DESCRIPTION
        "The value of tmnxSysSwReposRowStatus specifies the row status. It
         allows the creation and deletion of rows in
         tmnxSysSoftwareRepositoryTable."
    ::= { tmnxSysSoftwareRepositoryEntry 2 }

tmnxSysSwReposLastChanged        OBJECT-TYPE
    SYNTAX      TimeStamp
    MAX-ACCESS  read-only
    STATUS      current
    DESCRIPTION
        "The value of tmnxSysSwReposLastChanged indicates the time, since
         system startup, that the configuration of the system software
         repository was created or modified."
    ::= { tmnxSysSoftwareRepositoryEntry 3 }

tmnxSysSwReposDescription        OBJECT-TYPE
    SYNTAX      TItemDescription
    MAX-ACCESS  read-create
    STATUS      current
    DESCRIPTION
        "The value of tmnxSysSwReposDescription specifies the description of
         the system software repository.

         An empty string indicates this object has not been configured."
    DEFVAL      { ''H }
    ::= { tmnxSysSoftwareRepositoryEntry 4 }

tmnxSysSwReposPrimaryLocation    OBJECT-TYPE
    SYNTAX      TmnxDisplayStringURL
    MAX-ACCESS  read-create
    STATUS      current
    DESCRIPTION
        "The value of tmnxSysSwReposPrimaryLocation specifies the primary
         location of the directory that contains the runtime image files for
         the system software repository.

         An empty string indicates this object has not been configured."
    DEFVAL      { ''H }
    ::= { tmnxSysSoftwareRepositoryEntry 5 }

tmnxSysSwReposSecondaryLocation  OBJECT-TYPE
    SYNTAX      TmnxDisplayStringURL
    MAX-ACCESS  read-create
    STATUS      current
    DESCRIPTION
        "The value of tmnxSysSwReposSecondaryLocation specifies the secondary
         location of the directory that contains the runtime image files for
         the system software repository.

         An empty string indicates this object has not been configured."
    DEFVAL      { ''H }
    ::= { tmnxSysSoftwareRepositoryEntry 6 }

tmnxSysSwReposTertiaryLocation   OBJECT-TYPE
    SYNTAX      TmnxDisplayStringURL
    MAX-ACCESS  read-create
    STATUS      current
    DESCRIPTION
        "The value of tmnxSysSwReposTertiaryLocation specifies the tertiary
         location of the directory that contains the runtime image files for
         the system software repository.

         An empty string indicates this object has not been configured."
    DEFVAL      { ''H }
    ::= { tmnxSysSoftwareRepositoryEntry 7 }

tmnxSysNspProxyInfo              OBJECT IDENTIFIER ::= { tmnxSysObjs 37 }

tmnxSysGrpcInfo                  OBJECT IDENTIFIER ::= { tmnxSysObjs 39 }

tmnxSysGrpcAdminState            OBJECT-TYPE
    SYNTAX      TmnxAdminState
    MAX-ACCESS  read-write
    STATUS      current
    DESCRIPTION
        "The value of tmnxSysGrpcAdminState specifies the desired
         administrative state of the gRPC server."
    DEFVAL      { outOfService }
    ::= { tmnxSysGrpcInfo 1 }

tmnxSysGrpcOperState             OBJECT-TYPE
    SYNTAX      TmnxOperState
    MAX-ACCESS  read-only
    STATUS      current
    DESCRIPTION
        "The value of tmnxSysGrpcOperState indicates the current operational
         state of gRPC server."
    ::= { tmnxSysGrpcInfo 2 }

tmnxSysGrpcTlsServerProfile      OBJECT-TYPE
    SYNTAX      TNamedItemOrEmpty
    MAX-ACCESS  read-write
    STATUS      current
    DESCRIPTION
        "The value of tmnxSysGrpcTlsServerProfile specifies the name of the TLS
         server profile to be used."
    DEFVAL      { ''H }
    ::= { tmnxSysGrpcInfo 3 }

tmnxSysGrpcMaxMsgSize            OBJECT-TYPE
    SYNTAX      Unsigned32 (1..1024)
    UNITS       "megabytes"
    MAX-ACCESS  read-write
    STATUS      current
    DESCRIPTION
        "The value of tmnxSysGrpcMaxMsgSize specifies the maximum size of the
         received decompressed serialized protobuf message without metadata."
    DEFVAL      { 512 }
    ::= { tmnxSysGrpcInfo 4 }

tmnxSysGrpcAutoCfgSave           OBJECT-TYPE
    SYNTAX      TruthValue
    MAX-ACCESS  read-write
    STATUS      current
    DESCRIPTION
        "The value of tmnxSysGrpcAutoCfgSave specifies whether the running
         configuration is saved as part of a commit operation initiated from
         gRPC."
    DEFVAL      { false }
    ::= { tmnxSysGrpcInfo 5 }

tmnxSysGrpcGnmiVersion           OBJECT-TYPE
    SYNTAX      DisplayString (SIZE (1..10))
    MAX-ACCESS  read-only
    STATUS      current
    DESCRIPTION
        "The value of tmnxSysGrpcGnmiVersion indicates the version of gNMI
         service provided by gRPC server."
    ::= { tmnxSysGrpcInfo 6 }

tmnxSysGrpcAllowUnsecure         OBJECT-TYPE
    SYNTAX      TruthValue
    MAX-ACCESS  read-write
    STATUS      current
    DESCRIPTION
        "The value of tmnxSysGrpcAllowUnsecure specifies whether gRPC server
         will run without secured transport protocol. Username and password
         will be transferred in unencrypted form with each RPC request."
    DEFVAL      { false }
    ::= { tmnxSysGrpcInfo 7 }

tmnxSysGrpcGnmiAdminState        OBJECT-TYPE
    SYNTAX      TmnxAdminState
    MAX-ACCESS  read-write
    STATUS      current
    DESCRIPTION
        "The value of tmnxSysGrpcGnmiAdminState specifies the desired
         administrative state of the gNMI service."
    DEFVAL      { inService }
    ::= { tmnxSysGrpcInfo 8 }

tmnxSysGrpcTcpKaAdminState       OBJECT-TYPE
    SYNTAX      TmnxAdminState
    MAX-ACCESS  read-write
    STATUS      current
    DESCRIPTION
        "The value of tmnxSysGrpcTcpKaAdminState specifies the administrative
         state of the TCP keepalive algorithm."
    DEFVAL      { outOfService }
    ::= { tmnxSysGrpcInfo 9 }

tmnxSysGrpcTcpKaIdle             OBJECT-TYPE
    SYNTAX      Unsigned32 (1..100000)
    UNITS       "seconds"
    MAX-ACCESS  read-write
    STATUS      current
    DESCRIPTION
        "The value of the object tmnxSysGrpcTcpKaIdle specifies the number of
         seconds until the first TCP keepalive probe is sent."
    DEFVAL      { 600 }
    ::= { tmnxSysGrpcInfo 10 }

tmnxSysGrpcTcpKaInterval         OBJECT-TYPE
    SYNTAX      Unsigned32 (1..100000)
    UNITS       "seconds"
    MAX-ACCESS  read-write
    STATUS      current
    DESCRIPTION
        "The value of the object tmnxSysGrpcTcpKaInterval specifies the number
         of seconds between two TCP keepalives probes."
    DEFVAL      { 15 }
    ::= { tmnxSysGrpcInfo 11 }

tmnxSysGrpcTcpKaCount            OBJECT-TYPE
    SYNTAX      Unsigned32 (3..100)
    UNITS       "seconds"
    MAX-ACCESS  read-write
    STATUS      current
    DESCRIPTION
        "The value of the object tmnxSysGrpcTcpKaCount specifies the number of
         missed keepalives before the TCP connection is declared down."
    DEFVAL      { 4 }
    ::= { tmnxSysGrpcInfo 12 }

tmnxSysGrpcRibApiAdminState      OBJECT-TYPE
    SYNTAX      TmnxAdminState
    MAX-ACCESS  read-write
    STATUS      current
    DESCRIPTION
        "The value of tmnxSysGrpcRibApiAdminState specifies the desired
         administrative state of the 'RibApi' service."
    DEFVAL      { outOfService }
    ::= { tmnxSysGrpcInfo 13 }

tmnxSysGrpcRibApiPurgeTimeout    OBJECT-TYPE
    SYNTAX      Unsigned32 (0..100000)
    UNITS       "seconds"
    MAX-ACCESS  read-write
    STATUS      current
    DESCRIPTION
        "The value of the object tmnxSysGrpcRibApiPurgeTimeout specifies the
         number of seconds until stale entries are purged.

         The value of zero specifies that the purge will happen immediately
         after controller disconnection is detected."
    DEFVAL      { 0 }
    ::= { tmnxSysGrpcInfo 14 }

tmnxSysGrpcRibApiVersion         OBJECT-TYPE
    SYNTAX      DisplayString (SIZE (1..10))
    MAX-ACCESS  read-only
    STATUS      current
    DESCRIPTION
        "The value of tmnxSysGrpcRibApiVersion indicates the version of RibApi
         service provided by gRPC server."
    ::= { tmnxSysGrpcInfo 15 }

tmnxSysGrpcGnoiCertMgmtAdmnState OBJECT-TYPE
    SYNTAX      TmnxAdminState
    MAX-ACCESS  read-write
    STATUS      current
    DESCRIPTION
        "The value of tmnxSysGrpcGnoiCertMgmtAdmnState specifies the desired
         administrative state of the 'gNOI CertificateManagement' service."
    DEFVAL      { outOfService }
    ::= { tmnxSysGrpcInfo 16 }

tmnxSysGrpcGnoiCertMgmtVersion   OBJECT-TYPE
    SYNTAX      DisplayString (SIZE (1..10))
    MAX-ACCESS  read-only
    STATUS      current
    DESCRIPTION
        "The value of tmnxSysGrpcGnoiCertMgmtVersion indicates the version of
         'gNOI CertificateManagement' service provided by gRPC server."
    ::= { tmnxSysGrpcInfo 17 }

tmnxSysMgmtInterfaceMDCli        OBJECT IDENTIFIER ::= { tmnxSysObjs 40 }

tmnxSysMgmtIfMDCliAutoCfgSave    OBJECT-TYPE
    SYNTAX      TruthValue
    MAX-ACCESS  read-write
    STATUS      current
    DESCRIPTION
        "The value of tmnxSysMgmtIfMDCliAutoCfgSave specifies whether the
         running configuration is saved as part of a commit operation initiated
         from MD CLI."
    DEFVAL      { false }
    ::= { tmnxSysMgmtInterfaceMDCli 1 }

tmnxSysMgmtIfMDEnvComplEnter     OBJECT-TYPE
    SYNTAX      TruthValue
    MAX-ACCESS  read-write
    STATUS      current
    DESCRIPTION
        "The value of tmnxSysMgmtIfMDEnvComplEnter specifies whether the
         command completion on enter character is allowed in MD CLI."
    DEFVAL      { true }
    ::= { tmnxSysMgmtInterfaceMDCli 2 }

tmnxSysMgmtIfMDEnvComplSpace     OBJECT-TYPE
    SYNTAX      TruthValue
    MAX-ACCESS  read-write
    STATUS      current
    DESCRIPTION
        "The value of tmnxSysMgmtIfMDEnvComplSpace specifies whether the
         command completion on space character is allowed in MD CLI."
    DEFVAL      { true }
    ::= { tmnxSysMgmtInterfaceMDCli 3 }

tmnxSysMgmtIfMDEnvComplTab       OBJECT-TYPE
    SYNTAX      TruthValue
    MAX-ACCESS  read-write
    STATUS      current
    DESCRIPTION
        "The value of tmnxSysMgmtIfMDEnvComplTab specifies whether the command
         completion on tab character is allowed in MD CLI."
    DEFVAL      { true }
    ::= { tmnxSysMgmtInterfaceMDCli 4 }

tmnxSysMgmtIfMDEnvConsLength     OBJECT-TYPE
    SYNTAX      Unsigned32 (24..512)
    MAX-ACCESS  read-write
    STATUS      current
    DESCRIPTION
        "The value of tmnxSysMgmtIfMDEnvConsLength specifies number of lines
         displayed on the console screen in MD CLI."
    DEFVAL      { 24 }
    ::= { tmnxSysMgmtInterfaceMDCli 5 }

tmnxSysMgmtIfMDEnvConsWidth      OBJECT-TYPE
    SYNTAX      Unsigned32 (80..512)
    MAX-ACCESS  read-write
    STATUS      current
    DESCRIPTION
        "The value of tmnxSysMgmtIfMDEnvConsWidth specifies number of columns
         displayed on the console screen in MD CLI."
    DEFVAL      { 80 }
    ::= { tmnxSysMgmtInterfaceMDCli 6 }

tmnxSysMgmtIfMDEnvMore           OBJECT-TYPE
    SYNTAX      TruthValue
    MAX-ACCESS  read-write
    STATUS      current
    DESCRIPTION
        "The value of tmnxSysMgmtIfMDEnvMore specifies whether paging of the
         output text in MD CLI is enabled. This applies to continuous text
         output from a single command that is capable of filling the entire
         screen."
    DEFVAL      { true }
    ::= { tmnxSysMgmtInterfaceMDCli 8 }

tmnxSysMgmtIfMDEnvPromptCtx      OBJECT-TYPE
    SYNTAX      TruthValue
    MAX-ACCESS  read-write
    STATUS      current
    DESCRIPTION
        "The value of tmnxSysMgmtIfMDEnvPromptCtx controls displaying of the
         current command context in MD CLI prompt."
    DEFVAL      { true }
    ::= { tmnxSysMgmtInterfaceMDCli 9 }

tmnxSysMgmtIfMDEnvPromptNewline  OBJECT-TYPE
    SYNTAX      TruthValue
    MAX-ACCESS  read-write
    STATUS      current
    DESCRIPTION
        "The value of tmnxSysMgmtIfMDEnvPromptNewline controls displaying of a
         newline before every prompt line in MD CLI."
    DEFVAL      { true }
    ::= { tmnxSysMgmtInterfaceMDCli 10 }

tmnxSysMgmtIfMDEnvPromptTime     OBJECT-TYPE
    SYNTAX      TruthValue
    MAX-ACCESS  read-write
    STATUS      current
    DESCRIPTION
        "The value of tmnxSysMgmtIfMDEnvPromptTime controls displaying of a
         timestamp before the first prompt line in MD CLI."
    DEFVAL      { false }
    ::= { tmnxSysMgmtInterfaceMDCli 11 }

tmnxSysMgmtIfMDEnvPromptIndic    OBJECT-TYPE
    SYNTAX      TruthValue
    MAX-ACCESS  read-write
    STATUS      current
    DESCRIPTION
        "The value of tmnxSysMgmtIfMDEnvPromptIndic controls displaying of the
         indicator of uncommitted changes in MD CLI prompt.

         The value set to true indicates that asterisk (*) is displayed in case
         of uncommitted changes are present in global configuration candidate
         datastore.

         The value set to false means that no indicator is displayed."
    DEFVAL      { true }
    ::= { tmnxSysMgmtInterfaceMDCli 12 }

tmnxSysMgmtIfMDEnvTimeDisplay    OBJECT-TYPE
    SYNTAX      INTEGER {
        local (1),
        utc   (2)
    }
    MAX-ACCESS  read-write
    STATUS      current
    DESCRIPTION
        "The value of tmnxSysMgmtIfMDEnvTimeDisplay specifies the time zone to
         be used, when displaying timestamp before prompt in MD CLI."
    DEFVAL      { local }
    ::= { tmnxSysMgmtInterfaceMDCli 13 }

tmnxSysMgmtIfMDEnvMsgCliSvrt     OBJECT-TYPE
    SYNTAX      INTEGER {
        warning (6),
        info    (7)
    }
    MAX-ACCESS  read-write
    STATUS      current
    DESCRIPTION
        "The value of tmnxSysMgmtIfMDEnvMsgCliSvrt specifies severity threshold
         for MD-CLI messages."
    DEFVAL      { info }
    ::= { tmnxSysMgmtInterfaceMDCli 14 }

tmnxSysMgmtIfMDEnvProIndAdminSt  OBJECT-TYPE
    SYNTAX      TmnxAdminStateTruthValue
    MAX-ACCESS  read-write
    STATUS      current
    DESCRIPTION
        "The value of tmnxSysMgmtIfMDEnvProIndAdminSt specifies whether
         progress indicator is active in MD-CLI."
    DEFVAL      { true }
    ::= { tmnxSysMgmtInterfaceMDCli 15 }

tmnxSysMgmtIfMDEnvProIndType     OBJECT-TYPE
    SYNTAX      INTEGER {
        dots (1)
    }
    MAX-ACCESS  read-write
    STATUS      current
    DESCRIPTION
        "Type of the progress indicator used in the MD-CLI."
    DEFVAL      { dots }
    ::= { tmnxSysMgmtInterfaceMDCli 16 }

tmnxSysMgmtIfMDEnvProIndDelay    OBJECT-TYPE
    SYNTAX      Unsigned32 (0..10000)
    MAX-ACCESS  read-write
    STATUS      current
    DESCRIPTION
        "Delay before progress indicator is displayed in MD-CLI."
    DEFVAL      { 1000 }
    ::= { tmnxSysMgmtInterfaceMDCli 17 }

tmnxSysMgmtIfMDCliCmdAccntLoad   OBJECT-TYPE
    SYNTAX      TruthValue
    MAX-ACCESS  read-write
    STATUS      current
    DESCRIPTION
        "The value of tmnxSysMgmtIfMDCliCmdAccntLoad specifies whether remote
         command accounting is performed during an MD-CLI load or rollback
         operation."
    DEFVAL      { true }
    ::= { tmnxSysMgmtInterfaceMDCli 18 }

tmnxSysMgmtIfMDEnvTimeFormat     OBJECT-TYPE
    SYNTAX      INTEGER {
        iso-8601 (1),
        rfc-1123 (2),
        rfc-3339 (3)
    }
    MAX-ACCESS  read-write
    STATUS      current
    DESCRIPTION
        "The value of tmnxSysMgmtIfMDEnvTimeFormat specifies the time format to
         be used, when displaying timestamp in info command in MD CLI."
    DEFVAL      { rfc-3339 }
    ::= { tmnxSysMgmtInterfaceMDCli 19 }

tmnxMGSysObjs                    OBJECT IDENTIFIER ::= { tmnxSysObjs 41 }

tmnxSysMgmtInterfaceYangModules  OBJECT IDENTIFIER ::= { tmnxSysObjs 42 }

tmnxSysMgmtIfYangBaseR13         OBJECT-TYPE
    SYNTAX      TruthValue
    MAX-ACCESS  read-write
    STATUS      current
    DESCRIPTION
        "The value of tmnxSysMgmtIfYangBaseR13 specifies whether or not the
         base release 13 YANG models are supported. When set to 'true', network
         managers can access base release 13 YANG models."
    DEFVAL      { false }
    ::= { tmnxSysMgmtInterfaceYangModules 1 }

tmnxSysMgmtIfYangNokia           OBJECT-TYPE
    SYNTAX      TruthValue
    MAX-ACCESS  read-write
    STATUS      current
    DESCRIPTION
        "The value of tmnxSysMgmtIfYangNokia specifies whether or not the Nokia
         YANG models are supported. When set to 'true', network managers can
         access Nokia YANG models."
    ::= { tmnxSysMgmtInterfaceYangModules 2 }

tmnxSysMgmtIfYangOpenConfig      OBJECT-TYPE
    SYNTAX      TruthValue
    MAX-ACCESS  read-only
    STATUS      current
    DESCRIPTION
        "The value of tmnxSysMgmtIfYangOpenConfig specifies whether or not the
         OpenConfig YANG models are supported. When set to 'true', network
         managers can access OpenConfig YANG models."
    DEFVAL      { false }
    ::= { tmnxSysMgmtInterfaceYangModules 3 }

tmnxSysMgmtIfYangNokiaCombined   OBJECT-TYPE
    SYNTAX      TruthValue
    MAX-ACCESS  read-write
    STATUS      current
    DESCRIPTION
        "The value of tmnxSysMgmtIfYangNokiaCombined specifies whether or not
         the combined Nokia YANG models are supported. When set to 'true',
         network managers can access combined Nokia YANG models.

         tmnxSysMgmtIfYangNokiaCombined and tmnxSysMgmtIfYangNokia are mutually
         exclusive and cannot be both set to true at the same time."
    ::= { tmnxSysMgmtInterfaceYangModules 4 }

tmnxSysMgmtInterfaces            OBJECT IDENTIFIER ::= { tmnxSysObjs 43 }

tmnxSysMgmtIfWriteMode           OBJECT-TYPE
    SYNTAX      INTEGER {
        classic     (1),
        modelDriven (2),
        mixed       (3)
    }
    MAX-ACCESS  read-write
    STATUS      current
    DESCRIPTION
        "The value of tmnxSysMgmtIfWriteMode specifies the router
         configuration mode's requested provisional state.
            classic (1)     - configuration is managed by classic
                              interfaces only (e.g. classic CLI and
                              SNMP).
            modelDriven (2) - configuration is managed by
                              model-driven interfaces only
                              (e.g. MD-CLI, Netconf, and gNMI).
            mixed (3)       - configuration is managed (with
                              restrictions) with both classic and
                              model-driven interfaces.

         When the value of tmnxSysMgmtIfWriteOperMode is in 'modelDriven (2)'
         mode, SNMP Set-PDUs are rejected (ResourceUnavailable(13))). To
         re-enable SNMP access an operator MUST have write-access to CLI or a
         newer interface such as Netconf or gNMI and set the mode to either
         'classic (1)' or 'mixed (3)'."
    DEFVAL      { classic }
    ::= { tmnxSysMgmtInterfaces 1 }

tmnxSysMgmtIfWriteOperMode       OBJECT-TYPE
    SYNTAX      INTEGER {
        syncing     (0),
        classic     (1),
        modelDriven (2),
        mixed       (3)
    }
    MAX-ACCESS  read-only
    STATUS      current
    DESCRIPTION
        "The value of tmnxSysMgmtIfWriteOperMode indicates the router
         configuration mode operationalized by the system.
            syncing (0)     - The system is in transition between
                              modes. Write access is restricted in
                              all interfaces.
            classic (1)     - configuration is managed by classic
                              interfaces only (e.g. classic CLI and
                              SNMP).
            modelDriven (2) - configuration is managed by
                              modelDriven interfaces only
                              (e.g. MD-CLI, Netconf, and gNMI).
            mixed (3)       - configuration is managed (with
                              restrictions) with both classic and
                              modelDriven interfaces."
    ::= { tmnxSysMgmtInterfaces 2 }

tmnxSysMgmtIfModeLastSwitchTime  OBJECT-TYPE
    SYNTAX      DateAndTime (SIZE (11))
    MAX-ACCESS  read-only
    STATUS      current
    DESCRIPTION
        "The value of tmnxSysMgmtIfModeLastSwitchTime indicates the time when a
         configuration-mode switch was last performed."
    ::= { tmnxSysMgmtInterfaces 3 }

tmnxSysMgmtIfModeSwitchDuration  OBJECT-TYPE
    SYNTAX      Counter32
    UNITS       "milliseconds"
    MAX-ACCESS  read-only
    STATUS      current
    DESCRIPTION
        "The value of tmnxSysMgmtIfModeSwitchDuration indicates the time, in
         milliseconds, that the last configuration-mode switch took to become
         active."
    ::= { tmnxSysMgmtInterfaces 4 }

tmnxSysMgmtIfDstoreLocksTable    OBJECT-TYPE
    SYNTAX      SEQUENCE OF TmnxSysMgmtIfDstoreLocksEntry
    MAX-ACCESS  not-accessible
    STATUS      current
    DESCRIPTION
        "The table tmnxSysMgmtIfDstoreLocksTable contains read-only information
         pertaining to configuration datastores' locks."
    ::= { tmnxSysMgmtInterfaces 5 }

tmnxSysMgmtIfDstoreLocksEntry    OBJECT-TYPE
    SYNTAX      TmnxSysMgmtIfDstoreLocksEntry
    MAX-ACCESS  not-accessible
    STATUS      current
    DESCRIPTION
        "Each row represents a single user session.

         Rows in the table tmnxSysMgmtIfDstoreLocksEntry are automatically
         created by the system when user acquires database connection and
         destroyed when client closes the connection."
    INDEX       { tmnxSysMgmtIfDsLocksSessionId }
    ::= { tmnxSysMgmtIfDstoreLocksTable 1 }

TmnxSysMgmtIfDstoreLocksEntry    ::= SEQUENCE
{
    tmnxSysMgmtIfDsLocksSessionId    Unsigned32,
    tmnxSysMgmtIfDsLocksRmtIpAddress InetAddress,
    tmnxSysMgmtIfDsLocksConsole      TruthValue,
    tmnxSysMgmtIfDsLocksUserName     TNamedItemOrEmpty,
    tmnxSysMgmtIfDsLocksSessionMode  INTEGER,
    tmnxSysMgmtIfDsLocksSessionType  INTEGER,
    tmnxSysMgmtIfDsLocksRegion       TNamedItem,
    tmnxSysMgmtIfDsLocksRunLock      TmnxSysMgmtIfDstoreLockState,
    tmnxSysMgmtIfDsLocksCndLock      TmnxSysMgmtIfDstoreLockState,
    tmnxSysMgmtIfDsLocksIdleTime     Unsigned32,
    tmnxSysMgmtIfDsLocksScratchCnt   Unsigned32,
    tmnxSysMgmtIfDsLocksCronEhs      TruthValue
}

tmnxSysMgmtIfDsLocksSessionId    OBJECT-TYPE
    SYNTAX      Unsigned32
    MAX-ACCESS  read-only
    STATUS      current
    DESCRIPTION
        "The value of the object tmnxSysMgmtIfDsLocksSessionId indicates the
         session ID of user session with open database connection, which can
         block other users from locking specific datastore."
    ::= { tmnxSysMgmtIfDstoreLocksEntry 1 }

tmnxSysMgmtIfDsLocksRmtIpAddress OBJECT-TYPE
    SYNTAX      InetAddress (SIZE (0|4|16))
    MAX-ACCESS  read-only
    STATUS      current
    DESCRIPTION
        "The value of the object tmnxSysMgmtIfDsLocksRmtIpAddress indicates the
         remote IP address of the user session.

         Empty address in case of console connection and
         tmnxSysMgmtIfDsLocksConsole is set to true."
    ::= { tmnxSysMgmtIfDstoreLocksEntry 2 }

tmnxSysMgmtIfDsLocksConsole      OBJECT-TYPE
    SYNTAX      TruthValue
    MAX-ACCESS  read-only
    STATUS      current
    DESCRIPTION
        "The value of tmnxSysMgmtIfDsLocksConsole indicates session session
         origin.

         Value true(1) represents for console connection and false(2) is used
         for Cron/EHS or rest of connections identified by IP address in
         tmnxSysMgmtIfDsLocksRmtIpAddress."
    DEFVAL      { false }
    ::= { tmnxSysMgmtIfDstoreLocksEntry 3 }

tmnxSysMgmtIfDsLocksUserName     OBJECT-TYPE
    SYNTAX      TNamedItemOrEmpty
    MAX-ACCESS  read-only
    STATUS      current
    DESCRIPTION
        "The value of the object tmnxSysMgmtIfDsLocksUserName indicates the
         name of the user who initiated the session."
    ::= { tmnxSysMgmtIfDstoreLocksEntry 4 }

tmnxSysMgmtIfDsLocksSessionMode  OBJECT-TYPE
    SYNTAX      INTEGER {
        global           (1),
        exclusive        (2),
        private          (3),
        privateExclusive (4),
        readOnly         (5)
    }
    MAX-ACCESS  read-only
    STATUS      current
    DESCRIPTION
        "The value of tmnxSysMgmtIfDsLocksSessionMode indicates
         the candidate datastore access session mode:
             global (1)           - write access to the global candidate datastore
                                    can be granted to multiple sessions
             exclusive (2)        - write access to the global candidate datastore
                                    and the running datastore is limited to a single session
             private (3)          - write access to a candidate datastore can be granted
                                    to multiple sessions, each with their own private
                                    candidate datastore
             privateExclusive (4) - write access to the private candidate datastore is granted,
                                    in addition, a single session is granted write access
                                    to the running datastore.
             readOnly (5)         - access to the datastore without write permissions."
    ::= { tmnxSysMgmtIfDstoreLocksEntry 5 }

tmnxSysMgmtIfDsLocksSessionType  OBJECT-TYPE
    SYNTAX      INTEGER {
        classicCli (1),
        grpc       (2),
        mdCli      (3),
        netconf    (4),
        snmp       (5),
        system     (6)
    }
    MAX-ACCESS  read-only
    STATUS      current
    DESCRIPTION
        "The value of tmnxSysMgmtIfDsLocksSessionType indicates the type of
         management interface, which was used to obtain the lock."
    ::= { tmnxSysMgmtIfDstoreLocksEntry 6 }

tmnxSysMgmtIfDsLocksRegion       OBJECT-TYPE
    SYNTAX      TNamedItem
    MAX-ACCESS  read-only
    STATUS      current
    DESCRIPTION
        "The value of the object tmnxSysMgmtIfDsLocksRegion indicates the name
         of the configuration region."
    ::= { tmnxSysMgmtIfDstoreLocksEntry 7 }

tmnxSysMgmtIfDsLocksRunLock      OBJECT-TYPE
    SYNTAX      TmnxSysMgmtIfDstoreLockState
    MAX-ACCESS  read-only
    STATUS      current
    DESCRIPTION
        "The value of tmnxSysMgmtIfDsLocksRunLock indicates running datastore
         lock state"
    ::= { tmnxSysMgmtIfDstoreLocksEntry 8 }

tmnxSysMgmtIfDsLocksCndLock      OBJECT-TYPE
    SYNTAX      TmnxSysMgmtIfDstoreLockState
    MAX-ACCESS  read-only
    STATUS      current
    DESCRIPTION
        "The value of tmnxSysMgmtIfDsLocksCndLock indicates candidate datastore
         lock state"
    ::= { tmnxSysMgmtIfDstoreLocksEntry 9 }

tmnxSysMgmtIfDsLocksIdleTime     OBJECT-TYPE
    SYNTAX      Unsigned32
    UNITS       "seconds"
    MAX-ACCESS  read-only
    STATUS      current
    DESCRIPTION
        "The value of tmnxSysMgmtIfDsLocksIdleTime indicates the idle time of
         user.

         For the CLI sessions the idle time is the period of time after last
         key pressed. For the NETCONF it is the period of time after session
         creation. For the GMI we do not track idle time."
    ::= { tmnxSysMgmtIfDstoreLocksEntry 10 }

tmnxSysMgmtIfDsLocksScratchCnt   OBJECT-TYPE
    SYNTAX      Unsigned32
    MAX-ACCESS  read-only
    STATUS      current
    DESCRIPTION
        "The value of tmnxSysMgmtIfDsLocksScratchCnt indicates the number of
         scratchpads in use for session"
    ::= { tmnxSysMgmtIfDstoreLocksEntry 11 }

tmnxSysMgmtIfDsLocksCronEhs      OBJECT-TYPE
    SYNTAX      TruthValue
    MAX-ACCESS  read-only
    STATUS      current
    DESCRIPTION
        "The value of tmnxSysMgmtIfDsLocksCronEhs indicates whether the session
         is a Cron/EHS session

         Value true(1) represents Cron/EHS session and false(2) is used for
         console or rest of connections identified by IP address in
         tmnxSysMgmtIfDsLocksRmtIpAddress."
    DEFVAL      { false }
    ::= { tmnxSysMgmtIfDstoreLocksEntry 12 }

tmnxSysMgmtIfSchemaPath          OBJECT-TYPE
    SYNTAX      TmnxDisplayStringURL
    MAX-ACCESS  read-write
    STATUS      current
    DESCRIPTION
        "The value of tmnxSysMgmtIfSchemaPath specifies the path to schema
         files used by the system.

         The value of this object defaults to 'cf3:/YANG'."
    DEFVAL      { '6366333a2f59414e47'H }
    ::= { tmnxSysMgmtInterfaces 6 }

tmnxSysMgmtIfWriteSwitchReason   OBJECT-TYPE
    SYNTAX      INTEGER {
        boot       (0),
        manual     (1),
        validation (2)
    }
    MAX-ACCESS  read-only
    STATUS      current
    DESCRIPTION
        "The value of tmnxSysMgmtIfWriteSwitchReason indicates the
         origin cause of the router configuration mode switch.
            boot(0)         - The system booted in the current mode.
            manual (1)      - An operator manually switched to the
                              current mode.
            validation (2)  - Validation failure was detected,
                              causing the mode switch."
    ::= { tmnxSysMgmtInterfaces 7 }

tmnxSysGrpcConnTable             OBJECT-TYPE
    SYNTAX      SEQUENCE OF TmnxSysGrpcConnEntry
    MAX-ACCESS  not-accessible
    STATUS      current
    DESCRIPTION
        "The table tmnxSysGrpcConnTable contains read-only information
         pertaining to gRPC server connections."
    ::= { tmnxSysObjs 44 }

tmnxSysGrpcConnEntry             OBJECT-TYPE
    SYNTAX      TmnxSysGrpcConnEntry
    MAX-ACCESS  not-accessible
    STATUS      current
    DESCRIPTION
        "Each row entry represents a single TCP connection towards gRPC server.

         Rows in the table tmnxSysGrpcConnEntry are automatically created by
         the system when client connect to gRPC server and destroyed when
         client disconnect."
    INDEX       {
        tmnxSysGrpcConnSrcIpAddType,
        tmnxSysGrpcConnSrcIpAddress,
        tmnxSysGrpcConnSrcPort
    }
    ::= { tmnxSysGrpcConnTable 1 }

TmnxSysGrpcConnEntry             ::= SEQUENCE
{
    tmnxSysGrpcConnSrcIpAddType      InetAddressType,
    tmnxSysGrpcConnSrcIpAddress      InetAddress,
    tmnxSysGrpcConnSrcPort           InetPortNumber,
    tmnxSysGrpcConnStartTime         DateAndTime,
    tmnxSysGrpcConnActRpcCnt         CounterBasedGauge64,
    tmnxSysGrpcConnTotRpcCnt         Counter64,
    tmnxSysGrpcConnRxBytes           Counter64,
    tmnxSysGrpcConnTxBytes           Counter64,
    tmnxSysGrpcConnQos               TDSCPNameOrEmpty,
    tmnxSysGrpcConnSrcVRtrId         TmnxVRtrID
}

tmnxSysGrpcConnSrcIpAddType      OBJECT-TYPE
    SYNTAX      InetAddressType
    MAX-ACCESS  not-accessible
    STATUS      current
    DESCRIPTION
        "The value of the object tmnxSysGrpcConnSrcIpAddType indicates the type
         of IP address stored in tmnxSysGrpcConnSrcIpAddress. The value can be
         either 'unknown', 'ipv4' or 'ipv6."
    ::= { tmnxSysGrpcConnEntry 1 }

tmnxSysGrpcConnSrcIpAddress      OBJECT-TYPE
    SYNTAX      InetAddress (SIZE (0|4|16))
    MAX-ACCESS  not-accessible
    STATUS      current
    DESCRIPTION
        "The value of the object tmnxSysGrpcConnSrcIpAddress indicates the
         remote IP address of the gRPC client."
    ::= { tmnxSysGrpcConnEntry 2 }

tmnxSysGrpcConnSrcPort           OBJECT-TYPE
    SYNTAX      InetPortNumber
    MAX-ACCESS  not-accessible
    STATUS      current
    DESCRIPTION
        "The value of the object tmnxSysGrpcConnSrcPort indicates the remote
         port of the gRPC client."
    ::= { tmnxSysGrpcConnEntry 3 }

tmnxSysGrpcConnStartTime         OBJECT-TYPE
    SYNTAX      DateAndTime
    MAX-ACCESS  read-only
    STATUS      current
    DESCRIPTION
        "The value of tmnxSysGrpcConnStartTime indicates the time when
         connection towards gRPC server was established."
    ::= { tmnxSysGrpcConnEntry 4 }

tmnxSysGrpcConnActRpcCnt         OBJECT-TYPE
    SYNTAX      CounterBasedGauge64
    MAX-ACCESS  read-only
    STATUS      current
    DESCRIPTION
        "The value of tmnxSysGrpcConnActRpcCnt indicates the active number of
         RPC on this connection."
    ::= { tmnxSysGrpcConnEntry 5 }

tmnxSysGrpcConnTotRpcCnt         OBJECT-TYPE
    SYNTAX      Counter64
    MAX-ACCESS  read-only
    STATUS      current
    DESCRIPTION
        "The value of tmnxSysGrpcConnTotRpcCnt indicates the total number of
         RPC on this connection since establishment time."
    ::= { tmnxSysGrpcConnEntry 6 }

tmnxSysGrpcConnRxBytes           OBJECT-TYPE
    SYNTAX      Counter64
    UNITS       "bytes"
    MAX-ACCESS  read-only
    STATUS      current
    DESCRIPTION
        "The value of tmnxSysGrpcConnRxBytes indicates the total number of
         bytes received over this connection."
    ::= { tmnxSysGrpcConnEntry 7 }

tmnxSysGrpcConnTxBytes           OBJECT-TYPE
    SYNTAX      Counter64
    UNITS       "bytes"
    MAX-ACCESS  read-only
    STATUS      current
    DESCRIPTION
        "The value of tmnxSysGrpcConnTxBytes indicates the total number of
         bytes sent over this connection."
    ::= { tmnxSysGrpcConnEntry 8 }

tmnxSysGrpcConnQos               OBJECT-TYPE
    SYNTAX      TDSCPNameOrEmpty
    MAX-ACCESS  read-only
    STATUS      current
    DESCRIPTION
        "The value of tmnxSysGrpcConnQos indicates the DSCP value of the
         connection. Only first Subscribe RPC with qos request is accepted on
         connection. DSCP value is reset to sgt-qos default after last
         Subscribe RPC on connection is terminated."
    ::= { tmnxSysGrpcConnEntry 9 }

tmnxSysGrpcConnSrcVRtrId         OBJECT-TYPE
    SYNTAX      TmnxVRtrID
    MAX-ACCESS  read-only
    STATUS      current
    DESCRIPTION
        "The value of the object tmnxSysGrpcConnSrcVRtrId indicates the virtual
         router instance ID of the gRPC client."
    ::= { tmnxSysGrpcConnEntry 10 }

tmnxSysHttpRdr                   OBJECT IDENTIFIER ::= { tmnxSysObjs 45 }

tmnxSysHttpRdrCpmOptimizedMode   OBJECT-TYPE
    SYNTAX      TruthValue
    MAX-ACCESS  read-write
    STATUS      current
    DESCRIPTION
        "The value of tmnxSysHttpRdrCpmOptimizedMode specifies if the CPM uses
         the optimized mode for HTTP redirect messages."
    DEFVAL      { true }
    ::= { tmnxSysHttpRdr 1 }

tmnxSysGrpcRpcTable              OBJECT-TYPE
    SYNTAX      SEQUENCE OF TmnxSysGrpcRpcEntry
    MAX-ACCESS  not-accessible
    STATUS      current
    DESCRIPTION
        "The table tmnxSysGrpcRpcTable contains read-only information
         pertaining to gRPC server RPCs."
    ::= { tmnxSysObjs 46 }

tmnxSysGrpcRpcEntry              OBJECT-TYPE
    SYNTAX      TmnxSysGrpcRpcEntry
    MAX-ACCESS  not-accessible
    STATUS      current
    DESCRIPTION
        "Each row entry represents a single RPC towards gRPC server.

         Rows in the table tmnxSysGrpcRpcEntry are automatically created by the
         system when client send RPC towards gRPC server and destroyed when RPC
         execution is finished or cancelled."
    INDEX       { tmnxSysGrpcRpcId }
    ::= { tmnxSysGrpcRpcTable 1 }

TmnxSysGrpcRpcEntry              ::= SEQUENCE
{
    tmnxSysGrpcRpcId                 Unsigned32,
    tmnxSysGrpcRpcName               TNamedItem,
    tmnxSysGrpcRpcServiceName        TNamedItem,
    tmnxSysGrpcRpcStartTime          DateAndTime,
    tmnxSysGrpcRpcSrcIpAddType       InetAddressType,
    tmnxSysGrpcRpcSrcIpAddress       InetAddress,
    tmnxSysGrpcRpcSrcPort            InetPortNumber,
    tmnxSysGrpcRpcUserName           TNamedItemOrEmpty,
    tmnxSysGrpcRpcSessionId          Unsigned32
}

tmnxSysGrpcRpcId                 OBJECT-TYPE
    SYNTAX      Unsigned32
    MAX-ACCESS  not-accessible
    STATUS      current
    DESCRIPTION
        "The value of the object tmnxSysGrpcRpcId indicates the system
         generated unique RPC ID."
    ::= { tmnxSysGrpcRpcEntry 1 }

tmnxSysGrpcRpcName               OBJECT-TYPE
    SYNTAX      TNamedItem
    MAX-ACCESS  read-only
    STATUS      current
    DESCRIPTION
        "The value of the object tmnxSysGrpcRpcName indicates the name of a
         RPC."
    ::= { tmnxSysGrpcRpcEntry 2 }

tmnxSysGrpcRpcServiceName        OBJECT-TYPE
    SYNTAX      TNamedItem
    MAX-ACCESS  read-only
    STATUS      current
    DESCRIPTION
        "The value of the object tmnxSysGrpcRpcServiceName indicates the name
         of a RPC service."
    ::= { tmnxSysGrpcRpcEntry 3 }

tmnxSysGrpcRpcStartTime          OBJECT-TYPE
    SYNTAX      DateAndTime
    MAX-ACCESS  read-only
    STATUS      current
    DESCRIPTION
        "The value of tmnxSysGrpcRpcStartTime indicates the time of a RPC
         arrival to gRPC server."
    ::= { tmnxSysGrpcRpcEntry 4 }

tmnxSysGrpcRpcSrcIpAddType       OBJECT-TYPE
    SYNTAX      InetAddressType
    MAX-ACCESS  read-only
    STATUS      current
    DESCRIPTION
        "The value of the object tmnxSysGrpcRpcSrcIpAddType indicates the type
         of IP address stored in tmnxSysGrpcRpcSrcIpAddress. The value can be
         either 'unknown', 'ipv4' or 'ipv6."
    ::= { tmnxSysGrpcRpcEntry 5 }

tmnxSysGrpcRpcSrcIpAddress       OBJECT-TYPE
    SYNTAX      InetAddress (SIZE (0|4|16))
    MAX-ACCESS  read-only
    STATUS      current
    DESCRIPTION
        "The value of the object tmnxSysGrpcRpcSrcIpAddress indicates the
         remote IP address of gRPC client who sent a RPC."
    ::= { tmnxSysGrpcRpcEntry 6 }

tmnxSysGrpcRpcSrcPort            OBJECT-TYPE
    SYNTAX      InetPortNumber
    MAX-ACCESS  read-only
    STATUS      current
    DESCRIPTION
        "The value of the object tmnxSysGrpcRpcSrcPort indicates the remote
         port of gRPC client who sent a RPC."
    ::= { tmnxSysGrpcRpcEntry 7 }

tmnxSysGrpcRpcUserName           OBJECT-TYPE
    SYNTAX      TNamedItemOrEmpty
    MAX-ACCESS  read-only
    STATUS      current
    DESCRIPTION
        "The value of the object tmnxSysGrpcRpcUserName indicates the name of a
         system user who initiated a RPC.

         The value might be empty if client did not provide username or if a
         RPC was not yet authenticated."
    ::= { tmnxSysGrpcRpcEntry 8 }

tmnxSysGrpcRpcSessionId          OBJECT-TYPE
    SYNTAX      Unsigned32
    MAX-ACCESS  read-only
    STATUS      current
    DESCRIPTION
        "The value of the object tmnxSysGrpcRpcSessionId indicates the
         session-id of a system user who initiated a RPC.

         The value might be zero if a RPC was not yet authenticated."
    ::= { tmnxSysGrpcRpcEntry 9 }

tmnxSysNetworkElementObjs        OBJECT IDENTIFIER ::= { tmnxSysObjs 47 }

tmnxSysNEProfTableLstChgd        OBJECT-TYPE
    SYNTAX      TimeStamp
    MAX-ACCESS  read-only
    STATUS      current
    DESCRIPTION
        "The value of tmnxSysNEProfTableLstChgd indicates the time, since
         system startup, when tmnxSysNEProfTable last changed configuration.

         A value of zero indicates that no changes were made to this table
         since the system was last initialized."
    ::= { tmnxSysNetworkElementObjs 1 }

tmnxSysNEProfTable               OBJECT-TYPE
    SYNTAX      SEQUENCE OF TmnxSysNEProfEntry
    MAX-ACCESS  not-accessible
    STATUS      current
    DESCRIPTION
        "The tmnxSysNEProfTable contains objects used to configure instances of
         the network element profile, which are used for node discovery.

         Entries in this table are created and deleted via SNMP set operations
         to tmnxSysNEProfRowStatus."
    ::= { tmnxSysNetworkElementObjs 2 }

tmnxSysNEProfEntry               OBJECT-TYPE
    SYNTAX      TmnxSysNEProfEntry
    MAX-ACCESS  not-accessible
    STATUS      current
    DESCRIPTION
        "Each tmnxSysNEProfEntry contains the configuration for one network
         element profile."
    INDEX       { tmnxSysNEProfName }
    ::= { tmnxSysNEProfTable 1 }

TmnxSysNEProfEntry               ::= SEQUENCE
{
    tmnxSysNEProfName                TNamedItem,
    tmnxSysNEProfRowStatus           RowStatus,
    tmnxSysNEProfLastChanged         TimeStamp,
    tmnxSysNEProfNeid                TmnxSysNeid,
    tmnxSysNEProfNeipV4Type          InetAddressType,
    tmnxSysNEProfNeipV4              InetAddress,
    tmnxSysNEProfNeipV6Type          InetAddressType,
    tmnxSysNEProfNeipV6              InetAddress,
    tmnxSysNEProfSystemMac           MacAddress,
    tmnxSysNEProfPlatformType        DisplayString,
    tmnxSysNEProfVendorId            DisplayString
}

tmnxSysNEProfName                OBJECT-TYPE
    SYNTAX      TNamedItem
    MAX-ACCESS  not-accessible
    STATUS      current
    DESCRIPTION
        "The value of tmnxSysNEProfName uniquely specifies one network element
         profile configured on this system."
    ::= { tmnxSysNEProfEntry 1 }

tmnxSysNEProfRowStatus           OBJECT-TYPE
    SYNTAX      RowStatus
    MAX-ACCESS  read-create
    STATUS      current
    DESCRIPTION
        "The value of tmnxSysNEProfRowStatus specifies the status of this row.
         It is used to create and delete row entries in tmnxSysNEProfTable."
    ::= { tmnxSysNEProfEntry 2 }

tmnxSysNEProfLastChanged         OBJECT-TYPE
    SYNTAX      TimeStamp
    MAX-ACCESS  read-only
    STATUS      current
    DESCRIPTION
        "The value of tmnxSysNEProfLastChanged indicates the time, since system
         startup, that the configuration of this row was created or modified."
    ::= { tmnxSysNEProfEntry 3 }

tmnxSysNEProfNeid                OBJECT-TYPE
    SYNTAX      TmnxSysNeid
    MAX-ACCESS  read-create
    STATUS      current
    DESCRIPTION
        "The value of tmnxSysNEProfNeid specifies the Network Element
         Identifier.

         The first 8 high-order bits indicate the subnet ID and and range from
         0x1 to 0xFE. The 16 low-order bits indicate the basic ID and ranges
         from 0x0001 to 0xFFFE."
    DEFVAL      { ''H }
    ::= { tmnxSysNEProfEntry 4 }

tmnxSysNEProfNeipV4Type          OBJECT-TYPE
    SYNTAX      InetAddressType
    MAX-ACCESS  read-create
    STATUS      current
    DESCRIPTION
        "The value of tmnxSysNEProfNeipV4Type specifies the IP address type of
         tmnxSysNEProfNeipV4.

         The value of tmnxSysNEProfNeipV4Type can be either of 'ipv4(1)' or
         'unknown (0)'.

         The value of 'unknown(0)' specifies no NEIP v4 address is configured."
    DEFVAL      { unknown }
    ::= { tmnxSysNEProfEntry 5 }

tmnxSysNEProfNeipV4              OBJECT-TYPE
    SYNTAX      InetAddress (SIZE (0|4))
    MAX-ACCESS  read-create
    STATUS      current
    DESCRIPTION
        "The value of tmnxSysNEProfNeipV4 indicates the IPv4 address  of the
         Network Element."
    DEFVAL      { ''H }
    ::= { tmnxSysNEProfEntry 6 }

tmnxSysNEProfNeipV6Type          OBJECT-TYPE
    SYNTAX      InetAddressType
    MAX-ACCESS  read-create
    STATUS      current
    DESCRIPTION
        "The value of tmnxSysNEProfNeipV6Type specifies the IP address type of
         tmnxSysNEProfNeipV6.

         The value of tmnxSysNEProfNeipV6Type can be either of 'ipv6(2)' or
         'unknown (0)'.

         The value of 'unknown(0)' specifies no NEIP v6 address is configured."
    DEFVAL      { unknown }
    ::= { tmnxSysNEProfEntry 7 }

tmnxSysNEProfNeipV6              OBJECT-TYPE
    SYNTAX      InetAddress (SIZE (0|16))
    MAX-ACCESS  read-create
    STATUS      current
    DESCRIPTION
        "The value of tmnxSysNEProfNeipV6 indicates the IPv6 address of the
         Network Element."
    DEFVAL      { ''H }
    ::= { tmnxSysNEProfEntry 8 }

tmnxSysNEProfSystemMac           OBJECT-TYPE
    SYNTAX      MacAddress
    MAX-ACCESS  read-create
    STATUS      current
    DESCRIPTION
        "The value of tmnxSysNEProfSystemMac specifies the system MAC address
         of the node.

         A value of all zeroes indicates this object is not configured, the
         chassis MAC address will be used."
    DEFVAL      { '000000000000'H }
    ::= { tmnxSysNEProfEntry 9 }

tmnxSysNEProfPlatformType        OBJECT-TYPE
    SYNTAX      DisplayString
    MAX-ACCESS  read-create
    STATUS      current
    DESCRIPTION
        "The value of tmnxSysNEProfPlatformType specifies the product
         identifier.

         An empty string indicates this object is not configured, the chassis
         name and chassis type will be used."
    DEFVAL      { ''H }
    ::= { tmnxSysNEProfEntry 10 }

tmnxSysNEProfVendorId            OBJECT-TYPE
    SYNTAX      DisplayString
    MAX-ACCESS  read-create
    STATUS      current
    DESCRIPTION
        "The value of tmnxSysNEProfVendorId specifies the vendor identifier."
    DEFVAL      { "Nokia" }
    ::= { tmnxSysNEProfEntry 11 }

tmnxSysNEDiscoveryGenerateTraps  OBJECT-TYPE
    SYNTAX      TruthValue
    MAX-ACCESS  read-write
    STATUS      current
    DESCRIPTION
        "The value of tmnxSysNEDiscoveryGenerateTraps specifies whether to
         generate Network Element Discovery notifications or not."
    DEFVAL      { false }
    ::= { tmnxSysNetworkElementObjs 3 }

tmnxSysFwdPathOptsObjs           OBJECT IDENTIFIER ::= { tmnxSysObjs 48 }

tmnxSysFpoDscpTransAdminState    OBJECT-TYPE
    SYNTAX      TmnxAdminState
    MAX-ACCESS  read-write
    STATUS      current
    DESCRIPTION
        "The value of tmnxSysFpoDscpTransAdminState specifies the
         administrative state of the DSCP transparency forwarding path option."
    DEFVAL      { inService }
    ::= { tmnxSysFwdPathOptsObjs 1 }

tmnxSysFpoDscpTransOperState     OBJECT-TYPE
    SYNTAX      TmnxOperState
    MAX-ACCESS  read-only
    STATUS      current
    DESCRIPTION
        "The value of tmnxSysFpoDscpTransOperState indicates the operational
         state of the DSCP transparency forwarding path option."
    ::= { tmnxSysFwdPathOptsObjs 2 }

tmnxSysFpoEntropyLabelAdminState OBJECT-TYPE
    SYNTAX      TmnxAdminState
    MAX-ACCESS  read-write
    STATUS      current
    DESCRIPTION
        "The value of tmnxSysFpoEntropyLabelAdminState specifies the
         administrative state of the entropy label forwarding path option."
    DEFVAL      { outOfService }
    ::= { tmnxSysFwdPathOptsObjs 3 }

tmnxSysFpoEntropyLabelOperState  OBJECT-TYPE
    SYNTAX      TmnxOperState
    MAX-ACCESS  read-only
    STATUS      current
    DESCRIPTION
        "The value of tmnxSysFpoEntropyLabelOperState indicates the operational
         state of the entropy label forwarding path option."
    ::= { tmnxSysFwdPathOptsObjs 4 }

tmnxSysFpoMacFltOutVlanPrioAdmSt OBJECT-TYPE
    SYNTAX      TmnxAdminState
    MAX-ACCESS  read-write
    STATUS      current
    DESCRIPTION
        "The value of tmnxSysFpoMacFltOutVlanPrioAdmSt specifies the
         administrative state of the MAC filter outer VLAN priority forwarding
         path option."
    DEFVAL      { outOfService }
    ::= { tmnxSysFwdPathOptsObjs 5 }

tmnxSysFpoMacFltOutVlanPrioOprSt OBJECT-TYPE
    SYNTAX      TmnxOperState
    MAX-ACCESS  read-only
    STATUS      current
    DESCRIPTION
        "The value of tmnxSysFpoMacFltOutVlanPrioOprSt indicates the
         operational state of the MAC filter outer VLAN priority forwarding
         path option."
    ::= { tmnxSysFwdPathOptsObjs 6 }

tmnxSysFpoVplsEvpnMplsAdminState OBJECT-TYPE
    SYNTAX      TmnxAdminState
    MAX-ACCESS  read-write
    STATUS      current
    DESCRIPTION
        "The value of tmnxSysFpoVplsEvpnMplsAdminState specifies the
         administrative state of the VPLS EVPN MPLS forwarding path option."
    DEFVAL      { inService }
    ::= { tmnxSysFwdPathOptsObjs 7 }

tmnxSysFpoVplsEvpnMplsOperState  OBJECT-TYPE
    SYNTAX      TmnxOperState
    MAX-ACCESS  read-only
    STATUS      current
    DESCRIPTION
        "The value of tmnxSysFpoVplsEvpnMplsOperState indicates the operational
         state of the VPLS EVPN MPLS forwarding path option."
    ::= { tmnxSysFwdPathOptsObjs 8 }

tmnxSysFpoQosFc4ProfAdminState   OBJECT-TYPE
    SYNTAX      TmnxAdminState
    MAX-ACCESS  read-write
    STATUS      current
    DESCRIPTION
        "The value of tmnxSysFpoQosFc4ProfAdminState specifies the
         administrative state of the four color mode forwarding path option."
    DEFVAL      { outOfService }
    ::= { tmnxSysFwdPathOptsObjs 9 }

tmnxSysFpoQosFc4ProfOperState    OBJECT-TYPE
    SYNTAX      TmnxOperState
    MAX-ACCESS  read-only
    STATUS      current
    DESCRIPTION
        "The value of tmnxSysFpoQosFc4ProfOperState indicates the operational
         state of the four color mode forwarding path option."
    ::= { tmnxSysFwdPathOptsObjs 10 }

tmnxSysFpoQosMacCritAdminState   OBJECT-TYPE
    SYNTAX      TmnxAdminState
    MAX-ACCESS  read-write
    STATUS      current
    DESCRIPTION
        "The value of tmnxSysFpoQosMacCritAdminState specifies the
         administrative state of the MAC criteria for forwarding path option."
    DEFVAL      { outOfService }
    ::= { tmnxSysFwdPathOptsObjs 15 }

tmnxSysFpoQosMacCritOperState    OBJECT-TYPE
    SYNTAX      TmnxOperState
    MAX-ACCESS  read-only
    STATUS      current
    DESCRIPTION
        "The value of tmnxSysFpoQosMacCritOperState indicates the operational
         state of the MAC criteria for forwarding path option."
    ::= { tmnxSysFwdPathOptsObjs 16 }

tmnxSysFpoQosIpv6CritAdminState  OBJECT-TYPE
    SYNTAX      TmnxAdminState
    MAX-ACCESS  read-write
    STATUS      current
    DESCRIPTION
        "The value of tmnxSysFpoQosIpv6CritAdminState specifies the
         administrative state of the IPv6 criteria for forwarding path option."
    DEFVAL      { outOfService }
    ::= { tmnxSysFwdPathOptsObjs 17 }

tmnxSysFpoQosIpv6CritOperState   OBJECT-TYPE
    SYNTAX      TmnxOperState
    MAX-ACCESS  read-only
    STATUS      current
    DESCRIPTION
        "The value of tmnxSysFpoQosIpv6CritOperState indicates the operational
         state of the IPv6 criteria for forwarding path option."
    ::= { tmnxSysFwdPathOptsObjs 18 }

tmnxSysFpoQosBumPolAdminState    OBJECT-TYPE
    SYNTAX      TmnxAdminState
    MAX-ACCESS  read-write
    STATUS      current
    DESCRIPTION
        "The value of tmnxSysFpoQosBumPolAdminState specifies the
         administrative state of the BUM policers for forwarding path option."
    DEFVAL      { outOfService }
    ::= { tmnxSysFwdPathOptsObjs 19 }

tmnxSysFpoQosBumPolOperState     OBJECT-TYPE
    SYNTAX      TmnxOperState
    MAX-ACCESS  read-only
    STATUS      current
    DESCRIPTION
        "The value of tmnxSysFpoQosBumPolOperState indicates the operational
         state of the BUM policers for forwarding path option."
    ::= { tmnxSysFwdPathOptsObjs 20 }

tmnxSysConformance               OBJECT IDENTIFIER ::= { tmnxSRConfs 1 }

tmnxSysCompliances               OBJECT IDENTIFIER ::= { tmnxSysConformance 1 }

tmnxSysV4v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerGroup,
            tmnxSysTacPlusServerGroup,
            tmnxSysBofGroup,
            tmnxSysNotificationV4v0Group,
            tmnxPersistenceV4v0Group
        }
    ::= { tmnxSysCompliances 4 }

tmnxSysV5v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerV5v0Group,
            tmnxSysTacPlusServerV5v0Group,
            tmnxSysBofGroup,
            tmnxSysNotificationV5v0Group,
            tmnxPersistenceV5v0Group
        }
    ::= { tmnxSysCompliances 5 }

tmnxSysV6v0Compliance            MODULE-COMPLIANCE
    STATUS      obsolete
    DESCRIPTION
        "The compliance statement for management of general system capabilities
         on Nokia SROS series systems."
    MODULE
        MANDATORY-GROUPS {
            tmnxSysGeneralV3v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group
        }
    ::= { tmnxSysCompliances 6 }

tmnxSysV7v0Compliance            MODULE-COMPLIANCE
    STATUS      obsolete
    DESCRIPTION
        "The compliance statement for management of general system capabilities
         on Nokia SROS series systems."
    MODULE
        MANDATORY-GROUPS {
            tmnxSysGeneralV3v0Group,
            tmnxSysGeneralV7v0Group,
            tmnxSysTimeV4v0Group,
            tmnxSysConfigV3v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSystemCpuMonitorGroup
        }
    ::= { tmnxSysCompliances 7 }

tmnxSysV8v0Compliance            MODULE-COMPLIANCE
    STATUS      obsolete
    DESCRIPTION
        "The compliance statement for management of general system capabilities
         on Nokia SROS series systems."
    MODULE
        MANDATORY-GROUPS {
            tmnxSysGeneralV3v0Group,
            tmnxSysGeneralV7v0Group,
            tmnxSysTimeV4v0Group,
            tmnxSysConfigV8v0Group,
            tmnxSysLoginControlV8v0Group,
            tmnxSysRadiusServerV5v0Group,
            tmnxSysTacPlusServerV5v0Group,
            tmnxSysBofV6v0Group,
            tmnxSysNotificationV6v0Group,
            tmnxPersistenceV6v0Group,
            tmnxSysIpv6MgmtItfV6v0Group,
            tmnxSysLiV6v0Group,
            tmnxSysIcmpVSV6v1Group,
            tmnxSysEthInfoGroup,
            tmnxSystemCpuMonitorGroup
        }
    ::= { tmnxSysCompliances 8 }

tmnxSysV9v0Compliance            MODULE-COMPLIANCE
    STATUS      obsolete
    DESCRIPTION
        "The compliance statement for management of general system capabilities
         on Nokia SROS series systems."
    MODULE
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysNotificationRBGroup
        }
    ::= { tmnxSysCompliances 9 }

tmnxSysBootedBofCompliance       MODULE-COMPLIANCE
    STATUS      current
    DESCRIPTION
        "The compliance statement for currently active (booted) BOF
         capabilities on Nokia SROS series systems."
    MODULE
        MANDATORY-GROUPS {
            tmnxSysBootedBofGroup
        }
    ::= { tmnxSysCompliances 10 }

tmnxSysV10v0Compliance           MODULE-COMPLIANCE
    STATUS      obsolete
    DESCRIPTION
        "The compliance statement for management of general system capabilities
         on Nokia SROS series systems."
    MODULE
        MANDATORY-GROUPS {
            tmnxPersistenceV9v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup
        }
    ::= { tmnxSysCompliances 11 }

tmnxSysV11v0Compliance           MODULE-COMPLIANCE
    STATUS      obsolete
    DESCRIPTION
        "The compliance statement for management of general system capabilities
         on Nokia SROS series systems."
    MODULE
        MANDATORY-GROUPS {
            tmnxPersistenceV11v0Group,
            tmnxSysBofV6v0Group,
            tmnxSysConfigV8v0Group,
            tmnxSysEthInfoGroup,
            tmnxSysGeneralV3v0Group,
            tmnxSysGeneralV7v0Group,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNotificationV6v0Group,
            tmnxSysNotificationV9v0Group,
            tmnxSysNotificationV10v0Group,
            tmnxSysRadiusServerV5v0Group,
            tmnxSysRollbackV9v0Group,
            tmnxSysTacPlusServerV5v0Group,
            tmnxSysTimeV4v0Group,
            tmnxSystemCpuMonitorGroup,
            tmnxSysCertGroup,
            tmnxSysRollbackRescueGroup,
            tmnxSysNotificationRBGroup,
            tmnxSysGroupingSystemGroup,
            tmnxSysCandidateCfgGroup,
            tmnxSysNetconfV11v0Group,
            tmnxSysStrmV11v0R4Group
        }
    ::= { tmnxSysCompliances 12 }

tmnxSysV12v0Compliance           MODULE-COMPLIANCE
    STATUS      obsolete
    DESCRIPTION
        "The compliance statement for management of general system capabilities
         on Nokia SROS series systems."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group
        }
    ::= { tmnxSysCompliances 13 }

tmnxSysV13v0Compliance           MODULE-COMPLIANCE
    STATUS      obsolete
    DESCRIPTION
        "The compliance statement for management of general system capabilities
         on Nokia SROS series systems."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group
        }
    ::= { tmnxSysCompliances 14 }

tmnxSysV14v0Compliance           MODULE-COMPLIANCE
    STATUS      current
    DESCRIPTION
        "The compliance statement for management of general system capabilities
         on Nokia SROS series systems in release 14.0."
    MODULE
        MANDATORY-GROUPS {
            tmnxPersistenceV12v0Group,
            tmnxSysBofV6v0Group,
            tmnxSysCandidateCfgGroup,
            tmnxSysCardResourceGroup,
            tmnxSysCertGroup,
            tmnxSysConfigV8v0Group,
            tmnxSysDNSSecNotifV12v0Group,
            tmnxSysDNSSecV12v0Group,
            tmnxSysEthInfoGroup,
            tmnxSysGeneralV3v0Group,
            tmnxSysGeneralV7v0Group,
            tmnxSysGroupingSystemGroup,
            tmnxSysIcmpVSV6v1Group,
            tmnxSysIpv6MgmtItfV6v0Group,
            tmnxSysLiFilterGroup,
            tmnxSysLiV6v0Group,
            tmnxSysLoginControlSecGroup,
            tmnxSysLoginControlV8v0Group,
            tmnxSysLoginControlV9v0Group,
            tmnxSysNetconfV11v0Group,
            tmnxSysNotificationRBGroup,
            tmnxSysNotificationV10v0Group,
            tmnxSysNotificationV12v0Group,
            tmnxSysNotificationV6v0Group,
            tmnxSysNotificationV9v0Group,
            tmnxSysRadiusServerV5v0Group,
            tmnxSysRollbackRescueGroup,
            tmnxSysRollbackV9v0Group,
            tmnxSysDhcpGroup,
            tmnxSysStrmV11v0R4Group,
            tmnxSysTacPlusServerV5v0Group,
            tmnxSysTimeV4v0Group,
            tmnxSystemCpuMonitorGroup,
            tmnxSysXmppV12v4Group,
            tmnxSysBofV12v0Group,
            tmnxSysLicenseV12v0Group,
            tmnxSysFibV13v0Group,
            tmnxSysNetconfV13v0Group,
            tmnxSysSnmpSrcAccesLstV13v0Group,
            tmnxSysMgmtProtocolV13v0Group,
            tmnxSysFileTransProfV13v0Group,
            tmnxSysEhsV13v0Group,
            tmnxSysBofV13v0Group,
            tmnxSysLicenseV13v0Group,
            tmnxSysLicenseNotifV13v0Group,
            tmnxSysSwReposV13v0Group,
            tmnxSysBofV14v0Group,
            tmnxSysNotificationV14v0Group,
            tmnxPersistenceV14v0Group,
            tmnxSysEhsParameterGroup,
            tmnxSysLicenseApplicationGroup,
            tmnxSysNotifyObjsV14v0Group,
            tmnxSysTimeV14v0Group
        }
    ::= { tmnxSysCompliances 15 }

tmnxSysV15v0Compliance           MODULE-COMPLIANCE
    STATUS      current
    DESCRIPTION
        "The compliance statement for management of general system capabilities
         on Nokia SROS series systems in release 15.0."
    MODULE
        MANDATORY-GROUPS {
            tmnxSysLoginControlV15v0Group,
            tmnxSysGrpcV15v0Group,
            tmnxSysXmppMgmtGroup,
            tmnxSysLicenseApp48HrsGroup
        }
    ::= { tmnxSysCompliances 16 }

tmnxSysV15v1Compliance           MODULE-COMPLIANCE
    STATUS      current
    DESCRIPTION
        "The compliance statement for management of general system capabilities
         on Nokia SROS series systems in release 15.1."
    MODULE
        MANDATORY-GROUPS {
            tmnxSysNetconfV15v1Group,
            tmnxSysMgmtProtocolV15v1Group,
            tmnxSysConfigSaveCtrlV15v1Group,
            tmnxSysMgmtIfMdCliGroup,
            tmnxSysMgmtIfYangModulesGroup,
            tmnxSysFileTransProfV15v1Group,
            tmnxSysBofV15v1Group
        }
    ::= { tmnxSysCompliances 17 }

tmnxSysV16v0Compliance           MODULE-COMPLIANCE
    STATUS      current
    DESCRIPTION
        "The compliance statement for management of general system capabilities
         on Nokia SROS series systems in release 16.0."
    MODULE
        MANDATORY-GROUPS {
            tmnxSysHttpRdrV16v0Group,
            tmnxSysLicenseNotifV16v0Group,
            tmnxSysMgmtIfDsLocksV16v0Group,
            tmnxSysLicensingV16v0Group,
            tmnxSysMgmtInterfaceV16v0Group,
            tmnxSysMgmtIfNotifyObjsGroup,
            tmnxSysNetworkElementV16v0Group
        }
    ::= { tmnxSysCompliances 18 }

tmnxSysV19v0Compliance           MODULE-COMPLIANCE
    STATUS      current
    DESCRIPTION
        "The compliance statement for management of general system capabilities
         on Nokia SROS series systems in release 19."
    MODULE
        MANDATORY-GROUPS {
            tmnxSysLicNotifyObjsV19v0Group,
            tmnxSysLicenseNotifV19v0Group,
            tmnxSysResInfoV19v0Group,
            tmnxSysBofV19v0Group,
            tmnxSysNetworkElementV19v0Group,
            tmnxSysLicensingV19v0Group,
            tmnxSysNetconfV19v0Group,
            tmnxSysEhsV19v0Group,
            tmnxSysBootConfFmtNotifyObjsGrp,
            tmnxSysFwdPathOptsV19v0Group,
            tmnxSysBootConfFmtNotifyGrp,
            tmnxSysMgmtIfMdCliCmdAccntGroup,
            tmnxSysResItCamV19v0Group,
            tmnxSysFpCamAllocV19v0Group
        }
    ::= { tmnxSysCompliances 19 }

tmnxSysV20v0Compliance           MODULE-COMPLIANCE
    STATUS      current
    DESCRIPTION
        "The compliance statement for management of general system capabilities
         on Nokia SROS series systems in release 20."
    MODULE
        MANDATORY-GROUPS {
            tmnxSysNotificationV20v0Group
        }
    ::= { tmnxSysCompliances 20 }

tmnxSysGroups                    OBJECT IDENTIFIER ::= { tmnxSysConformance 2 }

tmnxSysRadiusServerGroup         OBJECT-GROUP
    OBJECTS     {
        radiusOperStatus,
        radiusServerAddress,
        radiusServerOperStatus
    }
    STATUS      obsolete
    DESCRIPTION
        "The group of objects supporting management of RADIUS servers on Nokia
         SROS series systems."
    ::= { tmnxSysGroups 4 }

tmnxSysTacPlusServerGroup        OBJECT-GROUP
    OBJECTS     {
        tacplusOperStatus,
        tacplusServerAddress,
        tacplusServerOperStatus
    }
    STATUS      obsolete
    DESCRIPTION
        "The group of objects supporting management of TACACS+ servers on Nokia
         SROS series systems."
    ::= { tmnxSysGroups 5 }

tmnxSysBofGroup                  OBJECT-GROUP
    OBJECTS     {
        sbiActiveIpAddr,
        sbiActiveIpMask,
        sbiStandbyIpAddr,
        sbiStandbyIpMask,
        sbiPrimaryImage,
        sbiSecondaryImage,
        sbiTertiaryImage,
        sbiPrimaryConfigFile,
        sbiSecondaryConfigFile,
        sbiTertiaryConfigFile,
        sbiPersist,
        sbiConsoleSpeed,
        sbiAutoNegotiate,
        sbiSpeed,
        sbiDuplex,
        sbiPrimaryDns,
        sbiSecondaryDns,
        sbiTertiaryDns,
        sbiDnsDomain,
        sbiWait,
        sbiStaticRouteNextHop,
        sbiStaticRouteRowStatus
    }
    STATUS      obsolete
    DESCRIPTION
        "The group of objects supporting management of the Boot Options File
         (BOF) on Nokia SROS series systems."
    ::= { tmnxSysGroups 8 }

tmnxSysConfigV3v0Group           OBJECT-GROUP
    OBJECTS     {
        ssiSaveConfig,
        ssiSyncMode,
        ssiSyncForce,
        ssiSyncStatus,
        ssiSyncConfigLastTime,
        ssiSyncBootEnvLastTime,
        ssiConfigMaxBackupRevisions,
        ssiSaveConfigResult,
        ssiSaveBof,
        ssiSaveBofResult,
        ssiSaveConfigDest,
        ssiSaveConfigDetail,
        ssiRedFailoverTime,
        ssiRedFailoverReason,
        sbiConfigStatus,
        sbiPersistStatus,
        sbiPersistIndex,
        sbiSnmpdAdminStatus,
        sbiSnmpdOperStatus,
        sbiSnmpdMaxPktSize,
        sbiSnmpdPortNum,
        sbiBootConfigOKScript,
        sbiConfigOKScriptStatus,
        sbiBootConfigFailScript,
        sbiConfigFailScriptStatus,
        sbiRedSwitchoverScript,
        sbiRedSwitchoverScriptStatus,
        slcFtpInboundMaxSessions,
        slcTelnetInboundMaxSessions,
        slcTelnetOutboundMaxSessions,
        slcPreLoginMessage,
        slcPreLoginMessageInclName,
        slcMessageOfTheDay,
        slcMessageOfTheDayType,
        slcLoginBanner,
        sysLACPSystemPriority,
        slcLoginExponentialBackOff
    }
    STATUS      obsolete
    DESCRIPTION
        "The group of objects supporting management of boot-up configuration
         and synchronization of active and standby systems on Nokia SROS series
         systems."
    ::= { tmnxSysGroups 12 }

tmnxSysGeneralV3v0Group          OBJECT-GROUP
    OBJECTS     {
        sgiCpuUsage,
        sgiMemoryUsed,
        sgiMemoryAvailable,
        sgiMemoryPoolAllocated,
        sgiSwMajorVersion,
        sgiSwMinorVersion,
        sgiSwVersionModifier
    }
    STATUS      current
    DESCRIPTION
        "The group of objects supporting management of general system
         capabilities on Nokia SROS series systems, 3.0 Release."
    ::= { tmnxSysGroups 15 }

tmnxSysObsoleteGroup             OBJECT-GROUP
    OBJECTS     {
        stiSummerZoneStartDate,
        stiSummerZoneEndDate,
        tacplusServerAddress,
        radiusServerAddress
    }
    STATUS      obsolete
    DESCRIPTION
        "The group of objects in TIMETRA-SYSTEM-MIB which are obsoleted."
    ::= { tmnxSysGroups 17 }

tmnxPersistenceV4v0Group         OBJECT-GROUP
    OBJECTS     {
        spiDhcpL2PersistenceFileLocation,
        spiDhcpL2PersistenceDescription,
        spiDhcpL3PersistenceFileLocation,
        spiDhcpL3PersistenceDescription,
        spiSubMgmtPersistenceFileLocation,
        spiSubMgmtPersistenceDescription
    }
    STATUS      obsolete
    DESCRIPTION
        "The group of objects supporting management of persistency across
         system reboot on Nokia SROS series systems."
    ::= { tmnxSysGroups 18 }

tmnxSysTimeV4v0Group             OBJECT-GROUP
    OBJECTS     {
        stiDateAndTime,
        stiActiveZone,
        stiHoursOffset,
        stiMinutesOffset,
        stiZoneType,
        stiSummerZoneRowStatus,
        stiSummerZoneOffset,
        stiSummerZoneStartDay,
        stiSummerZoneStartWeek,
        stiSummerZoneStartMonth,
        stiSummerZoneStartHour,
        stiSummerZoneStartMinute,
        stiSummerZoneEndDay,
        stiSummerZoneEndWeek,
        stiSummerZoneEndMonth,
        stiSummerZoneEndHour,
        stiSummerZoneEndMinute,
        sntpState,
        sntpServerRowStatus,
        sntpServerVersion,
        sntpServerPreference,
        sntpServerInterval,
        sntpAdminState,
        sntpOperStatus
    }
    STATUS      current
    DESCRIPTION
        "The group of objects supporting management of time on Nokia SROS
         series systems, 4.0 Release."
    ::= { tmnxSysGroups 19 }

tmnxSysNotifyObjsR4r0Group       OBJECT-GROUP
    OBJECTS     {
        tmnxNotifyRow,
        tmnxNotifyRowAdminState,
        tmnxNotifyRowOperState,
        tmnxMemoryModule,
        tmnxModuleMallocSize,
        tmnxDroppedTrapID,
        tmnxTrapDroppedReasonCode,
        tmnxTrapDroppedEntryID,
        tmnxNotifyEntryOID,
        tmnxSnmpdErrorMsg,
        tmnxSysTimeSetBy
    }
    STATUS      obsolete
    DESCRIPTION
        "The group of objects supporting notifications for general system
         capabilities on Nokia SROS series systems."
    ::= { tmnxSysGroups 20 }

tmnxSysNotificationV4v0Group     NOTIFICATION-GROUP
    NOTIFICATIONS {
        stiDateAndTimeChanged,
        ssiSaveConfigSucceeded,
        ssiSaveConfigFailed,
        sbiBootConfig,
        sbiBootSnmpd,
        radiusServerOperStatusChange,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusServerOperStatusChange,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet
    }
    STATUS      obsolete
    DESCRIPTION
        "The group of notifications supporting the general system capabilities
         on Nokia SROS series systems."
    ::= { tmnxSysGroups 21 }

tmnxSysNotifyObjsV5v0Group       OBJECT-GROUP
    OBJECTS     {
        tmnxPersistencyClient,
        tmnxPersistencyFileLocator,
        tmnxPersistencyNotifyMsg,
        tmnxPersistenceAffectedCpm,
        tmnxNotifyRow,
        tmnxNotifyRowAdminState,
        tmnxNotifyRowOperState,
        tmnxMemoryModule,
        tmnxModuleMallocSize,
        tmnxDroppedTrapID,
        tmnxTrapDroppedReasonCode,
        tmnxTrapDroppedEntryID,
        tmnxNotifyEntryOID,
        tmnxSnmpdErrorMsg,
        tmnxSysTimeSetBy,
        tmnxFtpFailureMsg,
        tmnxFtpFailureDestAddressType,
        tmnxFtpFailureDestAddress
    }
    STATUS      current
    DESCRIPTION
        "The group of objects supporting notifications for general system
         capabilities on Nokia SROS series systems."
    ::= { tmnxSysGroups 22 }

tmnxSysNotificationV5v0Group     NOTIFICATION-GROUP
    NOTIFICATIONS {
        stiDateAndTimeChanged,
        ssiSaveConfigSucceeded,
        ssiSaveConfigFailed,
        sbiBootConfig,
        sbiBootSnmpd,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet,
        tmnxFtpClientFailure,
        tacplusInetSrvrOperStatusChange,
        radiusInetServerOperStatusChange,
        persistencyEventReport
    }
    STATUS      obsolete
    DESCRIPTION
        "The group of notifications supporting the general system capabilities
         on Nokia SROS series systems."
    ::= { tmnxSysGroups 23 }

tmnxSysObsoleteNotificationV5v0Group NOTIFICATION-GROUP
    NOTIFICATIONS {
        tacplusServerOperStatusChange,
        radiusServerOperStatusChange
    }
    STATUS      current
    DESCRIPTION
        "The group of notification objects in TIMETRA-SYSTEM-MIB which are
         obsoleted."
    ::= { tmnxSysGroups 24 }

tmnxSysTacPlusServerV5v0Group    OBJECT-GROUP
    OBJECTS     {
        tacplusOperStatus,
        tacplusServerOperStatus,
        tacPlusServerInetAddressType,
        tacPlusServerInetAddress
    }
    STATUS      current
    DESCRIPTION
        "The group of objects supporting management of TACACS+ servers on Nokia
         SROS series systems."
    ::= { tmnxSysGroups 25 }

tmnxSysRadiusServerV5v0Group     OBJECT-GROUP
    OBJECTS     {
        radiusOperStatus,
        radiusServerOperStatus,
        radiusServerInetAddressType,
        radiusServerInetAddress
    }
    STATUS      current
    DESCRIPTION
        "The group of objects supporting management of RADIUS servers on Nokia
         SROS series systems."
    ::= { tmnxSysGroups 26 }

tmnxSysObsoleteV5v0Group         OBJECT-GROUP
    OBJECTS     {
        stiSummerZoneStartDate,
        stiSummerZoneEndDate,
        tacplusServerAddress,
        radiusServerAddress,
        spiDhcpL2PersistenceFileLocation,
        spiDhcpL2PersistenceDescription,
        spiDhcpL3PersistenceFileLocation,
        spiDhcpL3PersistenceDescription
    }
    STATUS      current
    DESCRIPTION
        "The group of objects in TIMETRA-SYSTEM-MIB which are obsoleted."
    ::= { tmnxSysGroups 27 }

tmnxPersistenceV5v0Group         OBJECT-GROUP
    OBJECTS     {
        spiSubMgmtPersistenceFileLocation,
        spiSubMgmtPersistenceDescription
    }
    STATUS      obsolete
    DESCRIPTION
        "The group of objects supporting management of persistency across
         system reboot on Nokia SROS series systems."
    ::= { tmnxSysGroups 28 }

tmnxSysIpv6MgmtItfV6v0Group      OBJECT-GROUP
    OBJECTS     {
        sbiActiveIPv6Addr,
        sbiActiveIPv6PfxLen,
        sbiStandbyIPv6Addr,
        sbiStandbyIPv6PfxLen,
        sbiPrimaryDnsIPv6Addr,
        sbiSecondaryDnsIPv6Addr,
        sbiTertiaryDnsIPv6Addr,
        sbiStaticRouteIPv6NextHop,
        sbiStaticRouteIPv6RowStatus,
        sysDNSInfoLastChanged,
        sysDNSAddressResolvePref
    }
    STATUS      current
    DESCRIPTION
        "The group of objects supporting ipv6 management interface on Nokia
         SROS series systems."
    ::= { tmnxSysGroups 29 }

tmnxPersistenceV6v0Group         OBJECT-GROUP
    OBJECTS     {
        spiSubMgmtPersistenceFileLocation,
        spiSubMgmtPersistenceDescription,
        spiDhcpSrvPersistenceFileLoc,
        spiDhcpSrvPersistenceDescr
    }
    STATUS      obsolete
    DESCRIPTION
        "The group of objects supporting management of persistency across
         system reboot on Nokia SROS series systems."
    ::= { tmnxSysGroups 30 }

tmnxSysBofV6v0Group              OBJECT-GROUP
    OBJECTS     {
        sbiActiveIpAddr,
        sbiActiveIpMask,
        sbiStandbyIpAddr,
        sbiStandbyIpMask,
        sbiPrimaryImage,
        sbiSecondaryImage,
        sbiTertiaryImage,
        sbiPrimaryConfigFile,
        sbiSecondaryConfigFile,
        sbiTertiaryConfigFile,
        sbiPersist,
        sbiConsoleSpeed,
        sbiAutoNegotiate,
        sbiSpeed,
        sbiDuplex,
        sbiPrimaryDns,
        sbiSecondaryDns,
        sbiTertiaryDns,
        sbiDnsDomain,
        sbiWait,
        sbiStaticRouteNextHop,
        sbiStaticRouteRowStatus,
        sbiLiSeparate,
        sbiLiLocalSave
    }
    STATUS      current
    DESCRIPTION
        "The group of objects supporting management of the Boot Options File
         (BOF) on Nokia SROS series systems."
    ::= { tmnxSysGroups 31 }

tmnxSysNotificationV6v0Group     NOTIFICATION-GROUP
    NOTIFICATIONS {
        stiDateAndTimeChanged,
        ssiSaveConfigSucceeded,
        ssiSaveConfigFailed,
        sbiBootConfig,
        sbiBootSnmpd,
        sbiBootConfigFailFileError,
        sbiBootConfigOKFileError,
        sbiBootLiConfig,
        radiusOperStatusChange,
        tmnxConfigModify,
        tmnxConfigCreate,
        tmnxConfigDelete,
        tmnxStateChange,
        tmnxModuleMallocFailed,
        tmnxTrapDropped,
        ssiSyncConfigOK,
        ssiSyncConfigFailed,
        ssiSyncBootEnvOK,
        ssiSyncBootEnvFailed,
        sntpTimeDiffExceedsThreshold,
        tacplusOperStatusChange,
        tmnxSnmpdError,
        tmnxSsiMismatch,
        tmnxSnmpdStateChange,
        ssiRedStandbySyncing,
        ssiRedStandbyReady,
        ssiRedStandbySyncLost,
        ssiRedSwitchover,
        ssiRedCpmActive,
        ssiRedSingleCpm,
        persistencyClosedAlarmRaised,
        persistencyClosedAlarmCleared,
        tmnxSntpOperChange,
        tmnxSysTimeSet,
        tmnxFtpClientFailure,
        tacplusInetSrvrOperStatusChange,
        radiusInetServerOperStatusChange,
        persistencyEventReport
    }
    STATUS      current
    DESCRIPTION
        "The group of notifications supporting the general system capabilities
         on Nokia SROS series systems."
    ::= { tmnxSysGroups 32 }

tmnxSysLiV6v0Group               OBJECT-GROUP
    OBJECTS     {
        sliConfigStatus,
        sliSaveConfig,
        sliSaveConfigResult,
        sliConfigLastModified,
        sliConfigLastSaved
    }
    STATUS      current
    DESCRIPTION
        "The group of objects supporting management of Lawful Intercept
         configuration on Nokia SROS series systems."
    ::= { tmnxSysGroups 33 }

tmnxSysNotifyObjsV6v0Group       OBJECT-GROUP
    OBJECTS     {
        tmnxNotifyObjectName,
        tmnxSyncFailureReason
    }
    STATUS      current
    DESCRIPTION
        "The group of objects added in 6.0 release to support system
         notifications."
    ::= { tmnxSysGroups 34 }

tmnxSysGeneralV7v0Group          OBJECT-GROUP
    OBJECTS     {
        sgiSnmpInGetBulks,
        sgiKbMemoryUsed,
        sgiKbMemoryAvailable,
        sgiKbMemoryPoolAllocated
    }
    STATUS      current
    DESCRIPTION
        "The group of objects supporting management of general system
         capabilities on Nokia SROS series systems added in 7.0 Release."
    ::= { tmnxSysGroups 35 }

tmnxSysIcmpVSV6v1Group           OBJECT-GROUP
    OBJECTS     {
        sysIcmpVSEnhancement
    }
    STATUS      current
    DESCRIPTION
        "The group of objects supporting management of ICMP vendor specific
         enhancement capabilities on Nokia SROS series systems."
    ::= { tmnxSysGroups 36 }

tmnxSysConfigV8v0Group           OBJECT-GROUP
    OBJECTS     {
        ssiSaveConfig,
        ssiSyncMode,
        ssiSyncForce,
        ssiSyncStatus,
        ssiSyncConfigLastTime,
        ssiSyncBootEnvLastTime,
        ssiConfigMaxBackupRevisions,
        ssiSaveConfigResult,
        ssiSaveBof,
        ssiSaveBofResult,
        ssiSaveConfigDest,
        ssiSaveConfigDetail,
        ssiRedFailoverTime,
        ssiRedFailoverReason,
        sbiConfigStatus,
        sbiPersistStatus,
        sbiPersistIndex,
        sbiSnmpdAdminStatus,
        sbiSnmpdOperStatus,
        sbiSnmpdMaxPktSize,
        sbiSnmpdPortNum,
        sbiBootConfigOKScript,
        sbiConfigOKScriptStatus,
        sbiBootConfigFailScript,
        sbiConfigFailScriptStatus,
        sbiRedSwitchoverScript,
        sbiRedSwitchoverScriptStatus,
        sysLACPSystemPriority
    }
    STATUS      current
    DESCRIPTION
        "The group of objects supporting management of boot-up configuration
         and synchronization of active and standby systems on Nokia SROS series
         systems."
    ::= { tmnxSysGroups 37 }

tmnxSysLoginControlV8v0Group     OBJECT-GROUP
    OBJECTS     {
        slcFtpInboundMaxSessions,
        slcTelnetInboundMaxSessions,
        slcTelnetOutboundMaxSessions,
        slcPreLoginMessage,
        slcPreLoginMessageInclName,
        slcMessageOfTheDay,
        slcMessageOfTheDayType,
        slcLoginBanner,
        slcLoginExponentialBackOff,
        slcTelnetGracefulShutdown,
        slcSSHGracefulShutdown
    }
    STATUS      current
    DESCRIPTION
        "The group of objects supporting management of login control on Nokia
         SROS series systems."
    ::= { tmnxSysGroups 38 }

tmnxSysEthInfoGroup              OBJECT-GROUP
    OBJECTS     {
        sysNewQinqUntaggedSap
    }
    STATUS      current
    DESCRIPTION
        "The group of objects supporting management of Ethernet Info on Nokia
         SROS series systems."
    ::= { tmnxSysGroups 39 }

tmnxPersistenceV9v0Group         OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr
    }
    STATUS      obsolete
    DESCRIPTION
        "The group of objects supporting management of persistency across
         system reboot on Nokia SROS series systems release 9.0."
    ::= { tmnxSysGroups 40 }

tmnxSysLoginControlSecGroup      OBJECT-GROUP
    OBJECTS     {
        slcTelnetMinTTLValue,
        slcSSHMinTTLValue
    }
    STATUS      current
    DESCRIPTION
        "The group of objects supporting management of login control on Nokia
         SROS series systems."
    ::= { tmnxSysGroups 41 }

tmnxSysLiFilterGroup             OBJECT-GROUP
    OBJECTS     {
        sliFilterLock
    }
    STATUS      current
    DESCRIPTION
        "The group of objects supporting management of Lawful Intercept
         configuration on Nokia SROS series systems."
    ::= { tmnxSysGroups 42 }

tmnxSysNotificationV9v0Group     NOTIFICATION-GROUP
    NOTIFICATIONS {
        persistenceRestoreProblem,
        tmnxSysRollbackStarted,
        tmnxSysRollbackStatusChange,
        tmnxSysRollbackSaveStatusChange,
        tmnxSysRollbackFileDeleteStatus,
        ssiSyncRollbackOK,
        ssiSyncRollbackFailed,
        ssiSyncCertOK,
        ssiSyncCertFailed
    }
    STATUS      current
    DESCRIPTION
        "The group of notifications supporting the general system capabilities
         added in release 9.0 of SROS."
    ::= { tmnxSysGroups 43 }

tmnxSysRollbackV9v0Group         OBJECT-GROUP
    OBJECTS     {
        tmnxSysRollbackIndex,
        tmnxSysRollbackStart,
        tmnxSysRollbackResult,
        tmnxSysRollbackSave,
        tmnxSysRollbackSaveResult,
        tmnxSysRollbackLocation,
        tmnxSysRollbackRevertIndex,
        tmnxSysRollbackRevertEndTime,
        tmnxSysRollbackTableLastChanged,
        tmnxSysRollbackFileCreationTime,
        tmnxSysRollbackFileComment,
        tmnxSysRollbackFileUserName,
        tmnxSysRollbackSavedTime,
        ssiSyncRollbackLastTime,
        tmnxSysRollbackRevertStartTime,
        tmnxSysRollbackRevertUserName,
        tmnxSysRollbackRevertFilename,
        tmnxSysRollbackSaveComment,
        tmnxSysRollbackAbortRevert,
        tmnxSysRollbackFileVersion,
        tmnxSysRollbackFileDelete,
        tmnxSysRollbackFileDeleteResult,
        ssiSyncRollbackMode,
        ssiSyncRollbackForce,
        ssiSyncRollbackStatus
    }
    STATUS      current
    DESCRIPTION
        "The group of objects supporting management of the Rollback Files on
         Nokia SROS series systems."
    ::= { tmnxSysGroups 44 }

tmnxSysLoginControlV9v0Group     OBJECT-GROUP
    OBJECTS     {
        slcSSHInboundMaxSessions,
        slcSSHOutboundMaxSessions
    }
    STATUS      current
    DESCRIPTION
        "The group of objects supporting management of login control on Nokia
         SROS series systems, added in release 9.0."
    ::= { tmnxSysGroups 45 }

tmnxSystemCpuMonitorGroup        OBJECT-GROUP
    OBJECTS     {
        tmnxSysCpuMonCpuIdle,
        tmnxSysCpuMonBusyCoreUtil,
        tmnxSysCpuMonBusyGroupName,
        tmnxSysCpuMonBusyGroupUtil
    }
    STATUS      current
    DESCRIPTION
        "The group of objects, added in release 7.0, used for monitoring system
         CPU utilization on Nokia SROS series systems."
    ::= { tmnxSysGroups 46 }

tmnxSysCertGroup                 OBJECT-GROUP
    OBJECTS     {
        ssiSyncCertForce,
        ssiSyncCertLastTime,
        ssiSyncCertMode,
        ssiSyncCertStatus
    }
    STATUS      current
    DESCRIPTION
        "The group of objects supporting management of the synchronization of
         certificate Files on Nokia SROS series systems."
    ::= { tmnxSysGroups 47 }

tmnxSysBootedBofGroup            OBJECT-GROUP
    OBJECTS     {
        sbbiLiSeparate,
        sbbiLiLocalSave
    }
    STATUS      current
    DESCRIPTION
        "The group of objects giving the value of the currently active (booted)
         Boot Options File (BOF) parameters on Nokia SROS series systems."
    ::= { tmnxSysGroups 48 }

tmnxSysRollbackRescueGroup       OBJECT-GROUP
    OBJECTS     {
        tmnxSysRollbackRescueLocation,
        tmnxSysRollbackRescueSave,
        tmnxSysRollbackRescueRevert,
        tmnxSysRollbackRescueDelete,
        tmnxSysRollbackRescueSaveRes,
        tmnxSysRollbackRescueRevertRes,
        tmnxSysRollbackRescueDeleteRes,
        tmnxSysRollbackRescueSavedTime,
        tmnxSysRollbackRescueRevStTime,
        tmnxSysRollbackRescueRevEdTime,
        tmnxSysRollbackRescueRevUser,
        tmnxSysRollbackRescueSaveComment,
        tmnxSysRollbackRescueAbortRevert,
        tmnxSysRollbackRescueFileExists,
        tmnxSysRollbackMaxLocalFiles,
        tmnxSysRollbackMaxRemoteFiles
    }
    STATUS      current
    DESCRIPTION
        "The group of objects supporting management of the Rollback Rescue file
         on Nokia SROS series systems."
    ::= { tmnxSysGroups 49 }

tmnxSysNotificationV10v0Group    NOTIFICATION-GROUP
    NOTIFICATIONS {
        persistencyFileSysThresRaised,
        persistencyFileSysThresCleared,
        tmnxSysExecStarted,
        tmnxSysExecFinished
    }
    STATUS      current
    DESCRIPTION
        "The group of notifications supporting the general system capabilities
         added in release 10.0 of SROS."
    ::= { tmnxSysGroups 50 }

tmnxSysNotifyObjsV10v0Group      OBJECT-GROUP
    OBJECTS     {
        tmnxSysRollbackFileType,
        tmnxSysExecScript,
        tmnxSysExecResult
    }
    STATUS      current
    DESCRIPTION
        "The group of accessible-for-notify objects supporting notifications on
         Nokia SROS series systems added in SROS release 10.0."
    ::= { tmnxSysGroups 51 }

tmnxSysNotificationRBGroup       NOTIFICATION-GROUP
    NOTIFICATIONS {
        tmnxSysRollbackSaveStarted,
        tmnxSysRollbackDeleteStarted,
        tmnxSysNvsysFileError
    }
    STATUS      current
    DESCRIPTION
        "The group of notifications supporting the general system capabilities
         added in Nokia SROS series systems."
    ::= { tmnxSysGroups 52 }

tmnxSysNotifyObjsGenGroup        OBJECT-GROUP
    OBJECTS     {
        tmnxSysFileErrorType
    }
    STATUS      current
    DESCRIPTION
        "The group of accessible-for-notify objects supporting notifications on
         Nokia SROS series systems added in SROS."
    ::= { tmnxSysGroups 53 }

tmnxSysGroupingSystemGroup       OBJECT-GROUP
    OBJECTS     {
        sgiSystemGroupID,
        sgiSystemSubGroupID
    }
    STATUS      current
    DESCRIPTION
        "The group of objects supporting management of the grouping systems on
         Nokia SROS series systems."
    ::= { tmnxSysGroups 54 }

tmnxSysCandidateCfgGroup         OBJECT-GROUP
    OBJECTS     {
        tmnxSysCandidateCfgState,
        tmnxSysCandidateCfgEditors,
        tmnxSysCandidateCfgCommitState,
        tmnxSysCandidateCfgCommitTime,
        tmnxSysCandidateCfgRevertTime,
        tmnxSysCandidateCfgChckptCreated,
        tmnxSysCandidateCfgExclusiveUsr,
        tmnxSysCandidateCfgUser
    }
    STATUS      current
    DESCRIPTION
        "The group of objects supporting the candidate config on Nokia SROS
         series system added in SROS release 11.0."
    ::= { tmnxSysGroups 55 }

tmnxPersistenceV11v0Group        OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr,
        spiAncpPersistenceFileLoc,
        spiAncpPersistenceDescr
    }
    STATUS      obsolete
    DESCRIPTION
        "The group of objects supporting management of persistency across
         system reboot on Nokia SROS series systems release 11.0."
    ::= { tmnxSysGroups 56 }

tmnxSysNetconfV11v0Group         OBJECT-GROUP
    OBJECTS     {
        tmnxSysNetconfAdminStatus,
        tmnxSysNetconfOperStatus,
        tmnxSysNetconfRequests,
        tmnxSysNetconfGetRequests,
        tmnxSysNetconfGetConfigRequests,
        tmnxSysNetconfEditConfigRequests,
        tmnxSysNetconfCloseRequests,
        tmnxSysNetconfKillRequests,
        tmnxSysNetconfResponses,
        tmnxSysNetconfErrorResponses
    }
    STATUS      current
    DESCRIPTION
        "The group of objects supporting management of the NETCONF on Nokia
         SROS series system added in SROS release 11.0."
    ::= { tmnxSysGroups 57 }

tmnxSysStrmV11v0R4Group          OBJECT-GROUP
    OBJECTS     {
        tmnxSysStrmAdminStatus,
        tmnxSysStrmDumpSnmpRequests,
        tmnxSysStrmGetManyRequests,
        tmnxSysStrmResponses
    }
    STATUS      current
    DESCRIPTION
        "The group of objects supporting management of the SAM streaming on
         Nokia SROS series system added in SROS release 11.0 R4."
    ::= { tmnxSysGroups 58 }

tmnxSysNotifyObjsV11v0Group      OBJECT-GROUP
    OBJECTS     {
        tmnxTrapDroppedCount
    }
    STATUS      current
    DESCRIPTION
        "The group of objects supporting notifications for general system
         capabilities, added in Nokia SROS release 11.0."
    ::= { tmnxSysGroups 59 }

tmnxSysV12v0Groups               OBJECT IDENTIFIER ::= { tmnxSysGroups 60 }

tmnxPersistenceV12v0Group        OBJECT-GROUP
    OBJECTS     {
        spiSubMgmtPersistenceFileLocation,
        spiSubMgmtPersistenceDescription,
        spiDhcpSrvPersistenceFileLoc,
        spiDhcpSrvPersistenceDescr,
        spiNatFwdPersistenceFileLoc,
        spiNatFwdPersistenceDescr,
        spiAAPersistenceFileLoc,
        spiAAPersistenceDescr,
        spiAncpPersistenceFileLoc,
        spiAncpPersistenceDescr,
        spiPythonPersistenceFileLoc,
        spiPythonPersistenceDescr
    }
    STATUS      current
    DESCRIPTION
        "The group of objects supporting management of persistency across
         system reboot on Nokia SROS series systems release 12.0."
    ::= { tmnxSysV12v0Groups 1 }

tmnxSysDNSSecV12v0Group          OBJECT-GROUP
    OBJECTS     {
        sysDNSSecAdValidation,
        sysDNSSecRespCtrl
    }
    STATUS      current
    DESCRIPTION
        "The group of objects supporting Domain Name System Security Extensions
         on Nokia SROS series systems in release 12.0."
    ::= { tmnxSysV12v0Groups 2 }

tmnxSysDNSSecNotifV12v0Group     NOTIFICATION-GROUP
    NOTIFICATIONS {
        sysDNSSecFailedAuthentication
    }
    STATUS      current
    DESCRIPTION
        "The group of notifications supporting Domain Name System Security
         Extension capabilities added in release 12.0 of SROS."
    ::= { tmnxSysV12v0Groups 3 }

tmnxSysNotificationV12v0Group    NOTIFICATION-GROUP
    NOTIFICATIONS {
        tmnxConfigConflict,
        tmnxSysLicenseInvalid,
        tmnxSysLicenseExpiresSoon,
        tmnxSysVsdServerAvailable,
        tmnxSysVsdServerUnavailable,
        tmnxSysXmppServerFunctional,
        tmnxSysXmppServerNotFunctional
    }
    STATUS      current
    DESCRIPTION
        "The group of notifications supporting the general system capabilities
         added in release 12.0 of SROS."
    ::= { tmnxSysV12v0Groups 4 }

tmnxSysXmppV12v4Group            OBJECT-GROUP
    OBJECTS     {
        tmnxSysVsdSystemId,
        tmnxSysVsdGwPubSubIsSubscrd,
        tmnxSysVsdGwPubSubNodeName,
        tmnxSysVsdGwPubSubLstSubscrdTime,
        tmnxSysVsdGwLastAuditTxTime,
        tmnxSysXmppServFQDN,
        tmnxSysXmppServRowStatus,
        tmnxSysXmppServUserName,
        tmnxSysXmppServPassword,
        tmnxSysXmppServLastChanged,
        tmnxSysXmppServUptime,
        tmnxSysXmppServIQSent,
        tmnxSysXmppServIQRcvd,
        tmnxSysXmppServIQError,
        tmnxSysXmppServIQTimedOut,
        tmnxSysXmppServIQAckRcvd,
        tmnxSysXmppServIQMinRtt,
        tmnxSysXmppServIQMaxRtt,
        tmnxSysXmppServVsdUpdatesRcvd,
        tmnxSysXmppServUpdatesRcvd,
        tmnxSysXmppServMsgSent,
        tmnxSysXmppServMsgRcvd,
        tmnxSysXmppServMsgAckRcvd,
        tmnxSysXmppServMsgError,
        tmnxSysXmppServMsgTimedOut,
        tmnxSysXmppServMsgMinRtt,
        tmnxSysXmppServMsgMaxRtt,
        tmnxSysXmppServSubSent,
        tmnxSysXmppServUnSubSent,
        tmnxSysXmppServState,
        tmnxSysXmppServAdminState,
        tmnxSysVsdServUptime,
        tmnxSysVsdServUserName,
        tmnxSysVsdServerStatus,
        tmnxSysVsdServMsgSent,
        tmnxSysVsdServMsgRcvd,
        tmnxSysVsdServMsgAckRcvd,
        tmnxSysVsdServMsgError,
        tmnxSysVsdServMsgTimedOut,
        tmnxSysVsdServMsgMinRtt,
        tmnxSysVsdServMsgMaxRtt,
        tmnxSysXmppServOperUserName,
        tmnxSysXmppServAuthType,
        tmnxSysXmppServConnMode
    }
    STATUS      current
    DESCRIPTION
        "The group of objects supporting XMPP server information on Nokia SROS
         series systems in release 12.0 R4."
    ::= { tmnxSysV12v0Groups 5 }

tmnxSysCardResourceGroup         OBJECT-GROUP
    OBJECTS     {
        tmnxCardCpuResMonCpuIdle,
        tmnxCardCpuResMonBusyCoreUtil,
        tmnxCardCpuResMonBusyGroupName,
        tmnxCardCpuResMonBusyGroupUtil,
        tmnxCardMemResMemoryUsed,
        tmnxCardMemResMemoryAvailable,
        tmnxCardMemResPoolsAllocated
    }
    STATUS      current
    DESCRIPTION
        "The group of objects supporting the resource monitoring of cards in
         the system on Nokia SROS series systems in release 12.0."
    ::= { tmnxSysV12v0Groups 6 }

tmnxSysNotifyObjsV12v0Group      OBJECT-GROUP
    OBJECTS     {
        tmnxSysDNSSecDomainName,
        tmnxSysNotifVsdServerName,
        tmnxSysNotifXmppServerName,
        tmnxSysLicenseErrorReason,
        tmnxSysLicenseTimeLeft
    }
    STATUS      current
    DESCRIPTION
        "The group of objects supporting notifications for general system
         capabilities, added in Nokia SROS release 12.0."
    ::= { tmnxSysV12v0Groups 7 }

tmnxSysBofV12v0Group             OBJECT-GROUP
    OBJECTS     {
        sbiLicenseFile
    }
    STATUS      current
    DESCRIPTION
        "The group of additional objects supporting bof configuration on Nokia
         SROS series systems in release 12.0."
    ::= { tmnxSysV12v0Groups 8 }

tmnxSysLicenseV12v0Group         OBJECT-GROUP
    OBJECTS     {
        tmnxSysLicenseStatus,
        tmnxSysLicenseName,
        tmnxSysLicenseUuid,
        tmnxSysLicenseDescription,
        tmnxSysLicenseProduct,
        tmnxSysLicenseSwVersion,
        tmnxSysLicenseIssueDateAndTime,
        tmnxSysLicenseStartDateAndTime,
        tmnxSysLicenseEndDateAndTime
    }
    STATUS      current
    DESCRIPTION
        "The group of objects supporting license information on Nokia SROS
         series systems in release 12.0."
    ::= { tmnxSysV12v0Groups 9 }

tmnxSysDhcpGroup                 OBJECT-GROUP
    OBJECTS     {
        tmnxSysDhcp6AdvNoaddrsGlobal
    }
    STATUS      current
    DESCRIPTION
        "The group of objects supporting the configuration of DHCP at the
         system level."
    ::= { tmnxSysGroups 61 }

tmnxSysFibV13v0Group             OBJECT-GROUP
    OBJECTS     {
        tmnxSysFibSelective
    }
    STATUS      current
    DESCRIPTION
        "The group of objects supporting the configuration of FIB at the system
         level."
    ::= { tmnxSysGroups 62 }

tmnxSysNetconfV13v0Group         OBJECT-GROUP
    OBJECTS     {
        tmnxSysNetconfCopyConfigRequests,
        tmnxSysNetconfDelConfigRequests,
        tmnxSysNetconfValidateRequests
    }
    STATUS      current
    DESCRIPTION
        "The group of objects supporting management of the NETCONF on Nokia
         SROS series system added in SROS release 13.0."
    ::= { tmnxSysGroups 63 }

tmnxSysSnmpSrcAccesLstV13v0Group OBJECT-GROUP
    OBJECTS     {
        tmnxSysSnmpSrcAccessTblLstChgd,
        tmnxSysSnmpSrcAccessLstRowStatus,
        tmnxSysSnmpSrcAccessLstLastChg,
        tmnxSysSnmpCommunityPktDropped
    }
    STATUS      current
    DESCRIPTION
        "The group of objects supporting the configuration of source access
         list on Nokia SROS series system added in SROS release 13.0."
    ::= { tmnxSysGroups 64 }

tmnxSysMgmtProtocolV13v0Group    OBJECT-GROUP
    OBJECTS     {
        tmnxSysMgmtProtocolTblLstChng,
        tmnxSysMgmtProtLastChange,
        tmnxSysMgmtAllowImmediateChange
    }
    STATUS      current
    DESCRIPTION
        "The group of objects supporting the configuration of network
         management protocols on Nokia SROS series system added in SROS release
         13.0."
    ::= { tmnxSysGroups 65 }

tmnxSysFileTransProfV13v0Group   OBJECT-GROUP
    OBJECTS     {
        tmnxSysFileTransProfTableLstChgd,
        tmnxSysFileTransProfRowStatus,
        tmnxSysFileTransProfLastChanged,
        tmnxSysFileTransProfRtrId,
        tmnxSysFileTransProfSvcId,
        tmnxSysFileTransProfSrcAddrV4T,
        tmnxSysFileTransProfSrcAddrV4,
        tmnxSysFileTransProfSrcAddrV6T,
        tmnxSysFileTransProfSrcAddrV6,
        tmnxSysFileTransProfTimeout,
        tmnxSysFileTransProfRetry,
        tmnxSysFileTransProfRedirection
    }
    STATUS      current
    DESCRIPTION
        "The group of objects supporting the configuration of file transmission
         profiles on Nokia SROS series system added in SROS release 13.0."
    ::= { tmnxSysGroups 66 }

tmnxSysEhsV13v0Group             OBJECT-GROUP
    OBJECTS     {
        tmnxSmLaunchExtAuthType,
        tmnxSmRunExtAuthType,
        tmnxSmRunExtUserName
    }
    STATUS      current
    DESCRIPTION
        "The group of objects supporting the extension of tables in
         DISMAN-SCRIPT-MIB to support the Event Handling System (EHS) feature
         added in Nokia SROS release 13.0"
    ::= { tmnxSysGroups 67 }

tmnxSysLicenseV13v0Group         OBJECT-GROUP
    OBJECTS     {
        tmnxSysLicenseVChassisType,
        tmnxSysLicenseMaxNumCPMs,
        tmnxSysLicenseMaxNumIOMs,
        tmnxSysCpmCardLicStatus,
        tmnxSysCpmCardLicName,
        tmnxSysCpmCardLicUuid,
        tmnxSysCpmCardLicDescription,
        tmnxSysCpmCardLicProduct,
        tmnxSysCpmCardLicSwVersion,
        tmnxSysCpmCardLicIssueDateTime,
        tmnxSysCpmCardLicStartDateTime,
        tmnxSysCpmCardLicEndDateTime,
        tmnxSysCpmCardLicVChassisType,
        tmnxSysCpmCardLicMaxNumCPMs,
        tmnxSysCpmCardLicMaxNumIOMs,
        tmnxSysCpmCardLicFeatDescription
    }
    STATUS      current
    DESCRIPTION
        "The group of additional objects supporting license information on
         Nokia SROS series systems in release 13.0."
    ::= { tmnxSysGroups 68 }

tmnxSysLicenseNotifV13v0Group    NOTIFICATION-GROUP
    NOTIFICATIONS {
        tmnxSysLicenseValid
    }
    STATUS      current
    DESCRIPTION
        "The group of additional notifications supporting license information
         on Nokia SROS series systems in release 13.0."
    ::= { tmnxSysGroups 69 }

tmnxSysSwReposV13v0Group         OBJECT-GROUP
    OBJECTS     {
        tmnxSysSwReposTableLastChanged,
        tmnxSysSwReposRowStatus,
        tmnxSysSwReposLastChanged,
        tmnxSysSwReposDescription,
        tmnxSysSwReposPrimaryLocation,
        tmnxSysSwReposSecondaryLocation,
        tmnxSysSwReposTertiaryLocation
    }
    STATUS      current
    DESCRIPTION
        "The group of objects maintaining configuration for system software
         repositories on Nokia SROS series systems in Release 13.0."
    ::= { tmnxSysGroups 70 }

tmnxSysBofV13v0Group             OBJECT-GROUP
    OBJECTS     {
        sbiFips1402Level1,
        sbiEssSystemType
    }
    STATUS      current
    DESCRIPTION
        "The group of additional objects supporting bof configuration on Nokia
         SROS series systems in release 13.0."
    ::= { tmnxSysGroups 71 }

tmnxSysV14v0Groups               OBJECT IDENTIFIER ::= { tmnxSysGroups 72 }

tmnxSysBofV14v0Group             OBJECT-GROUP
    OBJECTS     {
        sbiSystemBaseMacAddress
    }
    STATUS      current
    DESCRIPTION
        "The group of additional objects supporting bof configuration on Nokia
         SROS series systems in release 14.0."
    ::= { tmnxSysV14v0Groups 1 }

tmnxSysNotificationV14v0Group    NOTIFICATION-GROUP
    NOTIFICATIONS {
        tmnxSysBaseMacAddressNotSet,
        tmnxSmLaunchStartFailed,
        tmnxEhsHandlerInvoked,
        tmnxEhsDroppedByMinDelay,
        tmnxSysAppStats24HrsAvailable,
        tmnxSysAppStatsWeekAvailable
    }
    STATUS      current
    DESCRIPTION
        "The group of additional notifications supporting the general system
         capabilities on Nokia SROS series systems in release 14.0."
    ::= { tmnxSysV14v0Groups 2 }

tmnxPersistenceV14v0Group        OBJECT-GROUP
    OBJECTS     {
        tmnxDhcpLeaseTimeModeThreshold
    }
    STATUS      current
    DESCRIPTION
        "The group of objects supporting management of persistency across
         system reboot added to Nokia SROS series systems release 14.0."
    ::= { tmnxSysV14v0Groups 3 }

tmnxSysNetconfV14v0Group         OBJECT-GROUP
    OBJECTS     {
        tmnxSysNetconfFailedEditCfgReqs,
        tmnxSysNetconfFailedLockReqs,
        sgiSnmpFailedSets,
        tmnxSysNetconfLockRequests,
        tmnxSysNetconfUnlockRequests,
        tmnxSysNetconfCommitRequests,
        tmnxSysNetconfDiscardRequests,
        tmnxSysNetconfCapCandidateCfg,
        tmnxSysNetconfCapRunningCfg,
        tmnxSysNetconfYangBaseR13,
        tmnxSysNetconfYangNokia
    }
    STATUS      obsolete
    DESCRIPTION
        "The group of objects supporting management of the NETCONF on Nokia
         SROS series system added in SROS release 14.0."
    ::= { tmnxSysV14v0Groups 4 }

tmnxSysEhsParameterGroup         OBJECT-GROUP
    OBJECTS     {
        tmnxSmRunEventArgName,
        tmnxSmRunEventArgValue
    }
    STATUS      current
    DESCRIPTION
        "The group of objects extending the support of the DISMAN-SCRIPT-MIB
         for the Event Handling System (EHS) feature added in Nokia SROS
         release 14.0"
    ::= { tmnxSysV14v0Groups 5 }

tmnxSysLicenseApplicationGroup   OBJECT-GROUP
    OBJECTS     {
        tmnxSysAppStats24HrsName,
        tmnxSysAppStats24HrsValue,
        tmnxSysAppStats24HrsTime,
        tmnxSysAppStatsWeekName,
        tmnxSysAppStatsWeekAverage,
        tmnxSysAppStatsWeekPeak,
        tmnxSysAppStatsWeekTime,
        tmnxSysAppStatsPeakName,
        tmnxSysAppStatsPeakValue,
        tmnxSysAppStatsPeakTime
    }
    STATUS      current
    DESCRIPTION
        "The group of additional objects supporting license information about a
         virtual machine implementation of an application on Nokia SROS series
         systems."
    ::= { tmnxSysV14v0Groups 6 }

tmnxSysNotifyObjsV14v0Group      OBJECT-GROUP
    OBJECTS     {
        tmnxSysLicenseErrorAction,
        tmnxSysNotifAppStatsTime,
        tmnxSysNotifAppStatsApplication,
        tmnxSysNotifAppStatsType
    }
    STATUS      current
    DESCRIPTION
        "The group of objects supporting notifications for general system
         capabilities, added in Nokia SROS release 14.0."
    ::= { tmnxSysV14v0Groups 7 }

tmnxSysTimeV14v0Group            OBJECT-GROUP
    OBJECTS     {
        stiPreferLocalTime
    }
    STATUS      current
    DESCRIPTION
        "The group of objects enhancing time output on Nokia SROS series
         systems for 14.0 Release."
    ::= { tmnxSysV14v0Groups 8 }

tmnxSysLoginControlV15v0Group    OBJECT-GROUP
    OBJECTS     {
        slcIdleTimeout,
        slcLoginScriptGlobal,
        slcLoginScriptPerUserDirectory,
        slcLoginScriptPerUserFilename
    }
    STATUS      current
    DESCRIPTION
        "The group of objects enhancing system login control on Nokia SROS
         series systems for 15.0 Release."
    ::= { tmnxSysGroups 73 }

tmnxSysGrpcV15v0Group            OBJECT-GROUP
    OBJECTS     {
        tmnxSysGrpcAdminState,
        tmnxSysGrpcOperState,
        tmnxSysGrpcTlsServerProfile,
        tmnxSysGrpcMaxMsgSize,
        tmnxSysGrpcGnmiVersion,
        tmnxSysGrpcAllowUnsecure,
        tmnxSysGrpcGnmiAdminState,
        tmnxSysGrpcTcpKaAdminState,
        tmnxSysGrpcTcpKaIdle,
        tmnxSysGrpcTcpKaInterval,
        tmnxSysGrpcTcpKaCount,
        tmnxSysGrpcRibApiAdminState,
        tmnxSysGrpcRibApiPurgeTimeout,
        tmnxSysGrpcRibApiVersion,
        tmnxSysGrpcGnoiCertMgmtAdmnState,
        tmnxSysGrpcGnoiCertMgmtVersion,
        tmnxSysGrpcConnStartTime,
        tmnxSysGrpcConnActRpcCnt,
        tmnxSysGrpcConnTotRpcCnt,
        tmnxSysGrpcConnRxBytes,
        tmnxSysGrpcConnTxBytes,
        tmnxSysGrpcConnQos,
        tmnxSysGrpcConnSrcVRtrId,
        tmnxSysGrpcRpcName,
        tmnxSysGrpcRpcServiceName,
        tmnxSysGrpcRpcStartTime,
        tmnxSysGrpcRpcSrcIpAddType,
        tmnxSysGrpcRpcSrcIpAddress,
        tmnxSysGrpcRpcSrcPort,
        tmnxSysGrpcRpcUserName,
        tmnxSysGrpcRpcSessionId
    }
    STATUS      current
    DESCRIPTION
        "The group of objects supporting gRPC server on Nokia SROS series
         systems for 15.0 Release."
    ::= { tmnxSysGroups 74 }

tmnxSysXmppMgmtGroup             OBJECT-GROUP
    OBJECTS     {
        tmnxSysXmppServServiceId,
        tmnxSysXmppServRouterId
    }
    STATUS      current
    DESCRIPTION
        "The group of objects supporting management of XMPP server on Nokia
         SROS series systems for 15.0 Release."
    ::= { tmnxSysGroups 75 }

tmnxSysV15v0Groups               OBJECT IDENTIFIER ::= { tmnxSysGroups 76 }

tmnxSysLicenseApp48HrsGroup      OBJECT-GROUP
    OBJECTS     {
        tmnxSysAppStats48HrsName,
        tmnxSysAppStats48HrsValue,
        tmnxSysAppStats48HrsTime
    }
    STATUS      current
    DESCRIPTION
        "The group of additional objects supporting license information about a
         virtual machine implementation of an application on Nokia SROS series
         systems."
    ::= { tmnxSysV15v0Groups 3 }

tmnxSysV15v1Groups               OBJECT IDENTIFIER ::= { tmnxSysGroups 77 }

tmnxSysNetconfV15v1Group         OBJECT-GROUP
    OBJECTS     {
        tmnxSysNetconfFailedEditCfgReqs,
        tmnxSysNetconfFailedLockReqs,
        sgiSnmpFailedSets,
        tmnxSysNetconfLockRequests,
        tmnxSysNetconfUnlockRequests,
        tmnxSysNetconfCommitRequests,
        tmnxSysNetconfDiscardRequests,
        tmnxSysNetconfCapCandidateCfg,
        tmnxSysNetconfCapRunningCfg,
        tmnxSysNetconfCreateSubRequests
    }
    STATUS      current
    DESCRIPTION
        "The group of objects supporting management of the NETCONF on Nokia
         SROS series system added in SROS release 15.1."
    ::= { tmnxSysV15v1Groups 1 }

tmnxSysMgmtProtocolV15v1Group    OBJECT-GROUP
    OBJECTS     {
        tmnxSysMgmtCliEngine1,
        tmnxSysMgmtCliEngine2
    }
    STATUS      current
    DESCRIPTION
        "The group of objects supporting the configuration of network
         management protocols on Nokia SROS series system added in SROS release
         15.1."
    ::= { tmnxSysV15v1Groups 2 }

tmnxSysConfigSaveCtrlV15v1Group  OBJECT-GROUP
    OBJECTS     {
        tmnxSysMgmtIfMDCliAutoCfgSave,
        tmnxSysNetconfAutoCfgSave,
        tmnxSysGrpcAutoCfgSave
    }
    STATUS      current
    DESCRIPTION
        "The group of objects supporting the configuration of configuration
         save options on Nokia SROS series system added in SROS release 15.1."
    ::= { tmnxSysV15v1Groups 3 }

tmnxSysMgmtIfMdCliGroup          OBJECT-GROUP
    OBJECTS     {
        tmnxSysMgmtIfMDEnvComplEnter,
        tmnxSysMgmtIfMDEnvComplSpace,
        tmnxSysMgmtIfMDEnvComplTab,
        tmnxSysMgmtIfMDEnvConsLength,
        tmnxSysMgmtIfMDEnvConsWidth,
        tmnxSysMgmtIfMDEnvMore,
        tmnxSysMgmtIfMDEnvPromptCtx,
        tmnxSysMgmtIfMDEnvPromptNewline,
        tmnxSysMgmtIfMDEnvPromptTime,
        tmnxSysMgmtIfMDEnvPromptIndic,
        tmnxSysMgmtIfMDEnvTimeDisplay,
        tmnxSysMgmtIfMDEnvMsgCliSvrt,
        tmnxSysMgmtIfMDEnvProIndAdminSt,
        tmnxSysMgmtIfMDEnvProIndType,
        tmnxSysMgmtIfMDEnvProIndDelay,
        tmnxSysMgmtIfWriteMode,
        tmnxSysMgmtIfWriteOperMode,
        tmnxSysMgmtIfModeLastSwitchTime,
        tmnxSysMgmtIfModeSwitchDuration,
        tmnxSysMgmtIfMDEnvTimeFormat
    }
    STATUS      current
    DESCRIPTION
        "The group of objects supporting the configuration MD cli on Nokia SROS
         series system added in SROS release 15.1."
    ::= { tmnxSysV15v1Groups 4 }

tmnxSysMgmtIfYangModulesGroup    OBJECT-GROUP
    OBJECTS     {
        tmnxSysMgmtIfYangBaseR13,
        tmnxSysMgmtIfYangNokia,
        tmnxSysMgmtIfYangOpenConfig,
        tmnxSysMgmtIfYangNokiaCombined
    }
    STATUS      current
    DESCRIPTION
        "The group of objects supporting the configuration of YANG modules on
         Nokia SROS series system added in SROS release 15.1."
    ::= { tmnxSysV15v1Groups 5 }

tmnxSysNetconfV15v1ObsoleteGroup OBJECT-GROUP
    OBJECTS     {
        tmnxSysNetconfYangBaseR13,
        tmnxSysNetconfYangNokia
    }
    STATUS      current
    DESCRIPTION
        "The group of objects supporting management of the NETCONF on Nokia
         SROS series system which are obsoleted"
    ::= { tmnxSysV15v1Groups 6 }

tmnxSysFileTransProfV15v1Group   OBJECT-GROUP
    OBJECTS     {
        tmnxSysFileTransProfSvcName
    }
    STATUS      current
    DESCRIPTION
        "The group of objects supporting the configuration of file transmission
         profile on Nokia SROS series system added in SROS release 15.1."
    ::= { tmnxSysV15v1Groups 7 }

tmnxSysBofV15v1Group             OBJECT-GROUP
    OBJECTS     {
        sbiSystemProfile
    }
    STATUS      current
    DESCRIPTION
        "The group of objects supporting the configuration of BOF on Nokia SROS
         series system add in SROS release 15.1."
    ::= { tmnxSysV15v1Groups 8 }

tmnxSysV16v0Groups               OBJECT IDENTIFIER ::= { tmnxSysGroups 78 }

tmnxSysHttpRdrV16v0Group         OBJECT-GROUP
    OBJECTS     {
        tmnxSysHttpRdrCpmOptimizedMode
    }
    STATUS      current
    DESCRIPTION
        "The group of objects supporting HTTP redirect on Nokia SROS series
         systems for the 16.0 Release."
    ::= { tmnxSysV16v0Groups 1 }

tmnxSysLicenseNotifV16v0Group    NOTIFICATION-GROUP
    NOTIFICATIONS {
        tmnxSysLicenseActivated,
        tmnxSysStandbyLicensingError,
        tmnxSysStandbyLicensingReady,
        tmnxSysMgmtIfModeChangeStart,
        tmnxSysMgmtIfModeChangeComplete,
        tmnxSysMgmtIfModeChangeFailure
    }
    STATUS      current
    DESCRIPTION
        "The group of additional notifications supporting license information
         on Nokia SROS series systems in release 16.0."
    ::= { tmnxSysV16v0Groups 2 }

tmnxSysMgmtIfDsLocksV16v0Group   OBJECT-GROUP
    OBJECTS     {
        tmnxSysMgmtIfDsLocksSessionId,
        tmnxSysMgmtIfDsLocksRmtIpAddress,
        tmnxSysMgmtIfDsLocksConsole,
        tmnxSysMgmtIfDsLocksUserName,
        tmnxSysMgmtIfDsLocksSessionMode,
        tmnxSysMgmtIfDsLocksSessionType,
        tmnxSysMgmtIfDsLocksRegion,
        tmnxSysMgmtIfDsLocksRunLock,
        tmnxSysMgmtIfDsLocksCndLock,
        tmnxSysMgmtIfDsLocksIdleTime,
        tmnxSysMgmtIfDsLocksScratchCnt,
        tmnxSysMgmtIfDsLocksCronEhs
    }
    STATUS      current
    DESCRIPTION
        "The group of objects supporting the configuration datastore locks on
         Nokia SROS series system added in SROS release 16.0."
    ::= { tmnxSysV16v0Groups 3 }

tmnxSysLicensingV16v0Group       OBJECT-GROUP
    OBJECTS     {
        tmnxSysAppLicenseDescription,
        tmnxSysAppLicenseType,
        tmnxSysAppLicensePoolSize,
        tmnxSysAppLicenseAllocated,
        tmnxSysAppLicensePresent,
        tmnxSysAppLicenseState,
        tmnxSysAvailLicenseName,
        tmnxSysAvailLicenseUuid,
        tmnxSysAvailLicenseDescription,
        tmnxSysAvailLicenseSwVersion,
        tmnxSysAvailLicIssueDateTime,
        tmnxSysAvailLicStartDateTime,
        tmnxSysAvailLicEndDateTime,
        sbiAllowBootLicenseViolations
    }
    STATUS      current
    DESCRIPTION
        "The group of objects supporting application licensing on Nokia SROS
         series system added in SROS release 16.0."
    ::= { tmnxSysV16v0Groups 4 }

tmnxSysMgmtInterfaceV16v0Group   OBJECT-GROUP
    OBJECTS     {
        tmnxSysMgmtIfSchemaPath,
        tmnxSysMgmtIfWriteSwitchReason
    }
    STATUS      current
    DESCRIPTION
        "The group of objects supporting configuration of management interface
         on Nokia SROS series system added in SROS release 16.0."
    ::= { tmnxSysV16v0Groups 5 }

tmnxSysMgmtIfNotifyObjsGroup     OBJECT-GROUP
    OBJECTS     {
        tmnxNotifySysMgmtIfOriginalMode
    }
    STATUS      current
    DESCRIPTION
        "The group of notification objects supporting configuration of
         management interface on Nokia SROS series system added in SROS release
         16.0."
    ::= { tmnxSysV16v0Groups 6 }

tmnxSysNetworkElementV16v0Group  OBJECT-GROUP
    OBJECTS     {
        tmnxSysNEProfTableLstChgd,
        tmnxSysNEProfRowStatus,
        tmnxSysNEProfLastChanged,
        tmnxSysNEProfNeid,
        tmnxSysNEProfNeipV4Type,
        tmnxSysNEProfNeipV4,
        tmnxSysNEProfNeipV6Type,
        tmnxSysNEProfNeipV6,
        tmnxSysNEProfSystemMac,
        tmnxSysNEProfPlatformType,
        tmnxSysNEProfVendorId,
        tmnxSysNEDiscoveryGenerateTraps
    }
    STATUS      current
    DESCRIPTION
        "The group of objects supporting Network Element info on Nokia SROS
         series system added in SROS release 16.0."
    ::= { tmnxSysV16v0Groups 7 }

tmnxSysV19v0Groups               OBJECT IDENTIFIER ::= { tmnxSysGroups 79 }

tmnxSysLicNotifyObjsV19v0Group   OBJECT-GROUP
    OBJECTS     {
        tmnxSysLicensingNotifyGroup,
        tmnxSysLicensedNotifyAppName
    }
    STATUS      current
    DESCRIPTION
        "The group of objects supporting notifications for licensing
         capabilities, added in Nokia SROS release 19."
    ::= { tmnxSysV19v0Groups 1 }

tmnxSysLicenseNotifV19v0Group    NOTIFICATION-GROUP
    NOTIFICATIONS {
        tmnxSysAppLicenseInsufficient,
        tmnxSysLicenseUpdateRequired
    }
    STATUS      current
    DESCRIPTION
        "The group of additional notifications supporting license information
         on Nokia SROS series systems in release 19."
    ::= { tmnxSysV19v0Groups 2 }

tmnxSysResInfoV19v0Group         OBJECT-GROUP
    OBJECTS     {
        tmnxSysResEcmpProfRowStatus,
        tmnxSysResEcmpProfType,
        tmnxSysResEcmpProfLinksPerGrp,
        tmnxSysResEcmpProfNumGrps
    }
    STATUS      current
    DESCRIPTION
        "The group of objects supporting system resource info on Nokia SROS
         series system added in SROS release 19."
    ::= { tmnxSysV19v0Groups 3 }

tmnxSysBofV19v0Group             OBJECT-GROUP
    OBJECTS     {
        sbiAutoBoot,
        sbiAutoBootClientId,
        sbiAutoBootClientIdType,
        sbiAutoBootUsingMgmt,
        sbiAutoBootUsingInband,
        sbiAutoBootInbandVlan,
        sbiAutoBootUsingIpv4,
        sbiAutoBootUsingIpv6,
        sbiAutoBootIncludeUserClass,
        sbiAutoIpv4Dhcp,
        sbiAutoIpv4DhcpClientIdType,
        sbiAutoIpv4DhcpClientId,
        sbiAutoIpv4DhcpOptUserClass,
        sbiAutoIpv4DhcpTimeout,
        sbiAutoIpv6Dhcp,
        sbiAutoIpv6DhcpClientIdType,
        sbiAutoIpv6DhcpClientIdDuidType,
        sbiAutoIpv6DhcpClientIdDuid,
        sbiAutoIpv6DhcpOptUserClass,
        sbiAutoIpv6DhcpTimeout,
        sbiStandbyAIpAddr,
        sbiStandbyAIpMask,
        sbiStandbyAIPv6Addr,
        sbiStandbyAIPv6PfxLen,
        sbiStandbyBIpAddr,
        sbiStandbyBIpMask,
        sbiStandbyBIPv6Addr,
        sbiStandbyBIPv6PfxLen,
        sbiStandbyCIpAddr,
        sbiStandbyCIpMask,
        sbiStandbyCIPv6Addr,
        sbiStandbyCIPv6PfxLen,
        sbiStandbyDIpAddr,
        sbiStandbyDIpMask,
        sbiStandbyDIPv6Addr,
        sbiStandbyDIPv6PfxLen,
        sbiMgmtIfIpMtu
    }
    STATUS      current
    DESCRIPTION
        "The group of objects supporting BOF options info on Nokia SROS series
         system added in SROS release 19."
    ::= { tmnxSysV19v0Groups 4 }

tmnxSysNetworkElementV19v0Group  OBJECT-GROUP
    OBJECTS     {
        tmnxSysNEProfTableLstChgd,
        tmnxSysNEProfRowStatus,
        tmnxSysNEProfLastChanged,
        tmnxSysNEProfNeid,
        tmnxSysNEProfNeipV4Type,
        tmnxSysNEProfNeipV4,
        tmnxSysNEProfNeipV6Type,
        tmnxSysNEProfNeipV6,
        tmnxSysNEProfSystemMac,
        tmnxSysNEProfPlatformType,
        tmnxSysNEProfVendorId,
        tmnxSysNEDiscoveryGenerateTraps
    }
    STATUS      current
    DESCRIPTION
        "The group of objects supporting Network Element info on Nokia SROS
         series system added in SROS release 19."
    ::= { tmnxSysV19v0Groups 5 }

tmnxSysLicensingV19v0Group       OBJECT-GROUP
    OBJECTS     {
        tmnxSysAvailLicenseProduct,
        tmnxSysLicensingState,
        tmnxSysLicensingRebootPending,
        tmnxSysLicensingProduct,
        tmnxSysLicensingUuid
    }
    STATUS      current
    DESCRIPTION
        "The group of objects supporting Licensing info on Nokia SROS series
         system added in SROS release 19."
    ::= { tmnxSysV19v0Groups 6 }

tmnxSysNetconfV19v0Group         OBJECT-GROUP
    OBJECTS     {
        tmnxSysNetconfPort
    }
    STATUS      current
    DESCRIPTION
        "The group of objects supporting management of the NETCONF on Nokia
         SROS series system added in SROS release 19.0."
    ::= { tmnxSysV19v0Groups 7 }

tmnxSysEhsV19v0Group             OBJECT-GROUP
    OBJECTS     {
        tmnxSmLaunchExtLockOverride
    }
    STATUS      current
    DESCRIPTION
        "The group of objects supporting the extension of tables in
         DISMAN-SCRIPT-MIB to support the Event Handling System (EHS) feature
         added in Nokia SROS release 19.0"
    ::= { tmnxSysV19v0Groups 8 }

tmnxSysBootConfFmtNotifyObjsGrp  OBJECT-GROUP
    OBJECTS     {
        tmnxPrimaryConfigFileFormatType,
        tmnxLiConfigFileFormatType
    }
    STATUS      current
    DESCRIPTION
        "The group of notification objects supporting configuration of
         management interface on Nokia SROS series system added in SROS release
         19."
    ::= { tmnxSysV19v0Groups 9 }

tmnxSysBootConfFmtNotifyGrp      NOTIFICATION-GROUP
    NOTIFICATIONS {
        tmnxSysMgmtIfLiIncorrectFormat,
        tmnxSysMgmtIfLiCfgNotEncrypted
    }
    STATUS      current
    DESCRIPTION
        "The group of notification objects supporting configuration of
         management interface on Nokia SROS series system added in SROS release
         19."
    ::= { tmnxSysV19v0Groups 10 }

tmnxSysFwdPathOptsV19v0Group     OBJECT-GROUP
    OBJECTS     {
        tmnxSysFpoDscpTransAdminState,
        tmnxSysFpoDscpTransOperState,
        tmnxSysFpoEntropyLabelAdminState,
        tmnxSysFpoEntropyLabelOperState,
        tmnxSysFpoMacFltOutVlanPrioAdmSt,
        tmnxSysFpoMacFltOutVlanPrioOprSt,
        tmnxSysFpoVplsEvpnMplsAdminState,
        tmnxSysFpoVplsEvpnMplsOperState,
        tmnxSysFpoQosFc4ProfAdminState,
        tmnxSysFpoQosFc4ProfOperState,
        tmnxSysFpoQosMacCritAdminState,
        tmnxSysFpoQosMacCritOperState,
        tmnxSysFpoQosIpv6CritAdminState,
        tmnxSysFpoQosIpv6CritOperState,
        tmnxSysFpoQosBumPolAdminState,
        tmnxSysFpoQosBumPolOperState
    }
    STATUS      current
    DESCRIPTION
        "The group of objects supporting management of system forwarding path
         options on Nokia SROS series system added in SROS release 19."
    ::= { tmnxSysV19v0Groups 11 }

tmnxSysMgmtIfMdCliCmdAccntGroup  OBJECT-GROUP
    OBJECTS     {
        tmnxSysMgmtIfMDCliCmdAccntLoad
    }
    STATUS      current
    DESCRIPTION
        "The group of objects supporting the configuration of remote accounting
         behavior during MD-CLI load and rollback operations on Nokia SROS
         series system added in SROS release 19.10."
    ::= { tmnxSysV19v0Groups 12 }

tmnxSysResItCamV19v0Group        OBJECT-GROUP
    OBJECTS     {
        tmnxSysResItCamBankV6Multicast
    }
    STATUS      current
    DESCRIPTION
        "The group of objects supporting system internal TCAM resource info on
         Nokia SROS series system added in SROS release 19.10"
    ::= { tmnxSysV19v0Groups 13 }

tmnxSysFpCamAllocV19v0Group      OBJECT-GROUP
    OBJECTS     {
        tmnxSysFpCamAllocAdmnV6Multicast,
        tmnxSysFpCamAllocOperV6Multicast
    }
    STATUS      current
    DESCRIPTION
        "The group of objects supporting system internal TCAM resource info on
         Nokia SROS series system added in SROS release 19.10"
    ::= { tmnxSysV19v0Groups 14 }

tmnxSysV20v0Groups               OBJECT IDENTIFIER ::= { tmnxSysGroups 80 }

tmnxSysNotificationV20v0Group    NOTIFICATION-GROUP
    NOTIFICATIONS {
        tmnxEqOperStateChange
    }
    STATUS      current
    DESCRIPTION
        "The group of notifications supporting the general system capabilities
         on Nokia SROS series systems added in SROS release 20."
    ::= { tmnxSysV20v0Groups 1 }

tmnxSysMGGroups                  OBJECT IDENTIFIER ::= { tmnxSysConformance 3 }

tmnxSysMGCompliances             OBJECT IDENTIFIER ::= { tmnxSysConformance 4 }

tmnxSysDCCompliance              OBJECT IDENTIFIER ::= { tmnxSysConformance 5 }

tmnxSysDCGroups                  OBJECT IDENTIFIER ::= { tmnxSysConformance 6 }

tmnxSysNspProxyCompliances       OBJECT IDENTIFIER ::= { tmnxSysConformance 7 }

tmnxSysNspProxyGroups            OBJECT IDENTIFIER ::= { tmnxSysConformance 8 }

tmnxSysMIBNotifyPrefix           OBJECT IDENTIFIER ::= { tmnxSRNotifyPrefix 1 }

tmnxSysNotifications             OBJECT IDENTIFIER ::= { tmnxSysMIBNotifyPrefix 0 }

stiDateAndTimeChanged            NOTIFICATION-TYPE
    OBJECTS     {
        stiDateAndTime
    }
    STATUS      current
    DESCRIPTION
        "The date and time changed  event is generated when the time on the
         system is modified either by explicit setting or automatic update in
         case of SNTP."
    ::= { tmnxSysNotifications 1 }

ssiSaveConfigSucceeded           NOTIFICATION-TYPE
    STATUS      current
    DESCRIPTION
        "The save config succeeded event is generated when the saving of
         configuration finishes without errors."
    ::= { tmnxSysNotifications 2 }

ssiSaveConfigFailed              NOTIFICATION-TYPE
    STATUS      current
    DESCRIPTION
        "The save config failed event is generated when the saving of
         configuration is stopped due to errors."
    ::= { tmnxSysNotifications 3 }

sbiBootConfig                    NOTIFICATION-TYPE
    OBJECTS     {
        sbiConfigStatus,
        sbiPersistStatus,
        sbiPersistIndex
    }
    STATUS      current
    DESCRIPTION
        "The sbiBootConfig notification is generated upon completion of the
         configuration phase following a system reboot."
    ::= { tmnxSysNotifications 4 }

sbiBootSnmpd                     NOTIFICATION-TYPE
    OBJECTS     {
        sbiPersistIndex,
        sbiSnmpdAdminStatus,
        sbiSnmpdOperStatus
    }
    STATUS      current
    DESCRIPTION
        "The sbiBootSnmpd notification is generated upon completion of the SNMP
         daemon initialization following a system reboot. Some system
         configuration and initialization errors may result in the SNMP daemon
         being suspended."
    ::= { tmnxSysNotifications 5 }

radiusServerOperStatusChange     NOTIFICATION-TYPE
    OBJECTS     {
        radiusServerAddress,
        radiusServerOperStatus
    }
    STATUS      obsolete
    DESCRIPTION
        "The radiusServerOperStatusChange notification is generated when the
         operational status of a RADIUS server has transitioned either from
         'up' to 'down' or from 'down' to 'up'.

         This object was made obsolete in the 5.0 release."
    ::= { tmnxSysNotifications 6 }

radiusOperStatusChange           NOTIFICATION-TYPE
    OBJECTS     {
        radiusOperStatus
    }
    STATUS      current
    DESCRIPTION
        "The radiusOperStatusChange notification is generated when the
         radiusOperStatus has transitioned either from 'up' to 'down' or from
         'down' to 'up'"
    ::= { tmnxSysNotifications 7 }

tmnxConfigModify                 NOTIFICATION-TYPE
    OBJECTS     {
        tmnxNotifyRow,
        tmnxNotifyEntryOID,
        tmnxNotifyObjectName
    }
    STATUS      current
    DESCRIPTION
        "A tmnxConfigModify notification is generated when a configuration
         attribute associated with a row entry in a MIB table is modified. It
         can be used by the NMS to trigger maintenance polls of the
         configuration information."
    ::= { tmnxSysNotifications 8 }

tmnxConfigCreate                 NOTIFICATION-TYPE
    OBJECTS     {
        tmnxNotifyRow,
        tmnxNotifyEntryOID,
        tmnxNotifyObjectName
    }
    STATUS      current
    DESCRIPTION
        "A tmnxConfigCreate notification is generated when a new row entry is
         created in one of the MIB tables. It can be used by the NMS to trigger
         maintenance polls of the configuration information."
    ::= { tmnxSysNotifications 9 }

tmnxConfigDelete                 NOTIFICATION-TYPE
    OBJECTS     {
        tmnxNotifyRow,
        tmnxNotifyEntryOID,
        tmnxNotifyObjectName
    }
    STATUS      current
    DESCRIPTION
        "A tmnxConfigDelete notification is generated when an existing row
         entry in one of the MIB tables is deleted. It can be used by the NMS
         to trigger maintenance polls of the configuration information."
    ::= { tmnxSysNotifications 10 }

tmnxStateChange                  NOTIFICATION-TYPE
    OBJECTS     {
        tmnxNotifyRow,
        tmnxNotifyRowAdminState,
        tmnxNotifyRowOperState,
        tmnxNotifyEntryOID,
        tmnxNotifyObjectName
    }
    STATUS      current
    DESCRIPTION
        "A tmnxStateChange notification is generated when there is a change in
         either the administrative or operational state of a MIB table entry."
    ::= { tmnxSysNotifications 11 }

tmnxModuleMallocFailed           NOTIFICATION-TYPE
    OBJECTS     {
        tmnxMemoryModule,
        tmnxModuleMallocSize
    }
    STATUS      current
    DESCRIPTION
        "A tmnxModuleMallocFailed notification is generated when a request to
         allocate memory from a particular module fails because the memory
         module is short on memory and cannot support the size that was
         requested."
    ::= { tmnxSysNotifications 12 }

tmnxTrapDropped                  NOTIFICATION-TYPE
    OBJECTS     {
        tmnxDroppedTrapID,
        tmnxTrapDroppedReasonCode,
        tmnxTrapDroppedEntryID,
        tmnxTrapDroppedCount
    }
    STATUS      current
    DESCRIPTION
        "A tmnxTrapDropped notification is generated when a trap is dropped for
         the reason specified by the reason code. The tmnxTrapDroppedEntryID
         identifies the table entry associated with the dropped trap.

         A nonzero value of the object tmnxTrapDroppedCount indicates the
         number of traps dropped for the current flow of traps, identified by
         the values of tmnxDroppedTrapID, tmnxTrapDroppedReasonCode and
         tmnxTrapDroppedEntryID."
    ::= { tmnxSysNotifications 13 }

ssiSyncConfigOK                  NOTIFICATION-TYPE
    STATUS      current
    DESCRIPTION
        "The ssiSyncConfigOK event is generated when the synchronization of
         configuration files between the primary and secondary CPMs finishes
         without errors."
    ::= { tmnxSysNotifications 14 }

ssiSyncConfigFailed              NOTIFICATION-TYPE
    OBJECTS     {
        tmnxSyncFailureReason
    }
    STATUS      current
    DESCRIPTION
        "The ssiSyncConfigFailed event is generated when the synchronization of
         configuration files between the primary and secondary CPMs is stopped
         due to errors. The tmnxSyncFailureReason will state reason for
         failure."
    ::= { tmnxSysNotifications 15 }

ssiSyncBootEnvOK                 NOTIFICATION-TYPE
    STATUS      current
    DESCRIPTION
        "The ssiSyncBootEnvOK event is generated when the synchronization of
         boot environment files between the primary and secondary CPMs finishes
         without errors."
    ::= { tmnxSysNotifications 16 }

ssiSyncBootEnvFailed             NOTIFICATION-TYPE
    OBJECTS     {
        tmnxSyncFailureReason
    }
    STATUS      current
    DESCRIPTION
        "The ssiSyncBootEnvFailed event is generated when the synchronization
         of boot environment files between the primary and secondary CPMs is
         stopped due to errors. The tmnxSyncFailureReason will state reason for
         failure."
    ::= { tmnxSysNotifications 17 }

sntpTimeDiffExceedsThreshold     NOTIFICATION-TYPE
    OBJECTS     {
        sntpAdminState
    }
    STATUS      current
    DESCRIPTION
        "The sntpTimeDiffExceedsThreshold event is generated when the time
         differential between the system and the SNTP server is more than 10
         seconds. In this case the system clock is not automatically adjusted."
    ::= { tmnxSysNotifications 18 }

tacplusServerOperStatusChange    NOTIFICATION-TYPE
    OBJECTS     {
        tacplusServerAddress,
        tacplusServerOperStatus
    }
    STATUS      obsolete
    DESCRIPTION
        "The tacplusServerOperStatusChange notification is generated when the
         operational status of a TACACS+ server has transitioned either from
         'up' to 'down' or from 'down' to 'up'.

         This object was made obsolete in the 5.0 release."
    ::= { tmnxSysNotifications 19 }

tacplusOperStatusChange          NOTIFICATION-TYPE
    OBJECTS     {
        tacplusOperStatus
    }
    STATUS      current
    DESCRIPTION
        "The tacplusOperStatusChange notification is generated when the
         tacplusOperStatus has transitioned either from 'up' to 'down' or from
         'down' to 'up'"
    ::= { tmnxSysNotifications 20 }

tmnxSnmpdError                   NOTIFICATION-TYPE
    OBJECTS     {
        tmnxSnmpdErrorMsg
    }
    STATUS      current
    DESCRIPTION
        "The tmnxSnmpdError notification is generated when the SNMP daemon
         detects an error condition."
    ::= { tmnxSysNotifications 21 }

tmnxSsiMismatch                  NOTIFICATION-TYPE
    OBJECTS     {
        ssiSyncMode,
        sbiPersist
    }
    STATUS      current
    DESCRIPTION
        "The tmnxSsiMismatch notification is generated by a system with
         redundant CPM cards after the processing of the bootup
         configuration has completed when ssiSyncMode has a  value of 'none'
         and sbiPersist has a value of 'true'.  This can result in SNMP
         indexes having different values following a system failover."
    ::= { tmnxSysNotifications 22 }

tmnxSnmpdStateChange             NOTIFICATION-TYPE
    OBJECTS     {
        sbiSnmpdAdminStatus,
        sbiSnmpdOperStatus
    }
    STATUS      current
    DESCRIPTION
        "The tmnxSnmpdStateChange notification is generated whenever there is a
         change in either the administrative or operational state of the SNMP
         agent."
    ::= { tmnxSysNotifications 23 }

ssiRedStandbySyncing             NOTIFICATION-TYPE
    OBJECTS     {
        tmnxChassisNotifyHwIndex,
        tmnxHwID,
        tmnxHwClass
    }
    STATUS      current
    DESCRIPTION
        "The ssiRedStandbySyncing notification is generated when
         synchronization of redundancy information onto the standby
         CPM is started.  tmnxChassisNotifyHwIndex identifies the
         standby CPM."
    ::= { tmnxSysNotifications 24 }

ssiRedStandbyReady               NOTIFICATION-TYPE
    OBJECTS     {
        tmnxChassisNotifyHwIndex,
        tmnxHwID,
        tmnxHwClass
    }
    STATUS      current
    DESCRIPTION
        "The ssiRedStandbyReady notification is generated when the
         synchronization of redundancy information onto the standby CPM
         has completed.  The standby CPM is now ready to take over
         control of the system if the active CPM fails or a manual
         switchover command is issued.  tmnxChassisNotifyHwIndex
         identifies the standby CPM."
    ::= { tmnxSysNotifications 25 }

ssiRedStandbySyncLost            NOTIFICATION-TYPE
    OBJECTS     {
        tmnxChassisNotifyHwIndex,
        tmnxHwID,
        tmnxHwClass
    }
    STATUS      current
    DESCRIPTION
        "The ssiRedStandbySyncLost notification is generated when the active
         CPM looses communication with the standby CPM.
         tmnxChassisNotifyHwIndex identifies the lost standby CPM."
    ::= { tmnxSysNotifications 26 }

ssiRedSwitchover                 NOTIFICATION-TYPE
    OBJECTS     {
        tmnxChassisNotifyHwIndex,
        tmnxHwID,
        tmnxHwClass,
        ssiRedFailoverTime,
        ssiRedFailoverReason
    }
    STATUS      current
    DESCRIPTION
        "The ssiRedSwitchover notification is generated when the standby
         CPM detects that the active CPM has failed and the standby prepares
         to take over as the new active CPM.  tmnxChassisNotifyHwIndex
         identifies the new active CPM."
    ::= { tmnxSysNotifications 27 }

ssiRedCpmActive                  NOTIFICATION-TYPE
    OBJECTS     {
        tmnxChassisNotifyHwIndex,
        tmnxHwID,
        tmnxHwClass
    }
    STATUS      current
    DESCRIPTION
        "The ssiRedCpmActive notification is generated following a
         redundancy switchover when the new active CPM has completed
         its audit and is ready to accept management commands via CLI
         or SNMP SET requests.  tmnxChassisNotifyHwIndex identifies
         the new active CPM."
    ::= { tmnxSysNotifications 28 }

ssiRedSingleCpm                  NOTIFICATION-TYPE
    OBJECTS     {
        tmnxChassisNotifyHwIndex,
        tmnxHwID,
        tmnxHwClass
    }
    STATUS      current
    DESCRIPTION
        "The ssiRedSingleCpm notification is generated by a system with
         a chassis with two CPM slots when the active CPM cannot detect a
         standby CPM in the chassis.  When the operating state of
         TIMETRA-CHASSIS-MIB::tmnxCpmCardRedundant for the active CPM card
         transitions to a value of 'singleton (1)', this notification is
         generated.  tmnxChassisNotifyHwIndex identifies the singleton CPM.

         When the active CPM later detects a standby CPM in the chassis, the
         ssiRedStandbySyncing event will be generated followed by a
         ssiRedStandbyReady event to indicate clearing of the CPM singleton
         state.  The value of tmnxCpmCardRedundant will then transition to
         'redundantActive (2)'."
    ::= { tmnxSysNotifications 29 }

persistencyClosedAlarmRaised     NOTIFICATION-TYPE
    OBJECTS     {
        tmnxPersistenceAffectedCpm,
        tmnxPersistencyClient,
        tmnxPersistencyFileLocator,
        tmnxPersistencyNotifyMsg
    }
    STATUS      current
    DESCRIPTION
        "The persistencyClosedAlarmRaised notification is generated when the
         system is unable to store persistency data (e.g. because the device is
         inaccessible, or full)."
    ::= { tmnxSysNotifications 30 }

persistencyClosedAlarmCleared    NOTIFICATION-TYPE
    OBJECTS     {
        tmnxPersistenceAffectedCpm,
        tmnxPersistencyClient,
        tmnxPersistencyFileLocator,
        tmnxPersistencyNotifyMsg
    }
    STATUS      current
    DESCRIPTION
        "The persistencyClosedAlarmCleared notification is generated when the
         output device used to store the persistence data is available for use
         again."
    ::= { tmnxSysNotifications 31 }

tmnxSntpOperChange               NOTIFICATION-TYPE
    OBJECTS     {
        sntpOperStatus
    }
    STATUS      current
    DESCRIPTION
        "The tmnxSntpOperChange notification is generated whenever there is a
         change in the operational state of SNTP."
    ::= { tmnxSysNotifications 32 }

tmnxSysTimeSet                   NOTIFICATION-TYPE
    OBJECTS     {
        stiDateAndTime,
        tmnxSysTimeSetBy
    }
    STATUS      current
    DESCRIPTION
        "The tmnxSysTimeSet notification is generated whenever system time is
         set by NTP, SNTP, SNMP, Real Time Clock(RTC) or if it was set
         manually."
    ::= { tmnxSysNotifications 33 }

tmnxFtpClientFailure             NOTIFICATION-TYPE
    OBJECTS     {
        tmnxFtpFailureMsg,
        tmnxFtpFailureDestAddressType,
        tmnxFtpFailureDestAddress
    }
    STATUS      current
    DESCRIPTION
        "The tmnxFtpClientFailure notification is generated when a file
         transfer operation initiated by the FTP client fails."
    ::= { tmnxSysNotifications 34 }

tacplusInetSrvrOperStatusChange  NOTIFICATION-TYPE
    OBJECTS     {
        tacPlusServerInetAddressType,
        tacPlusServerInetAddress,
        tacplusServerOperStatus
    }
    STATUS      current
    DESCRIPTION
        "The tacplusInetSrvrOperStatusChange notification is generated when the
         operational status of a TACACS+ server has transitioned either from
         'up' to 'down' or from 'down' to 'up'."
    ::= { tmnxSysNotifications 35 }

radiusInetServerOperStatusChange NOTIFICATION-TYPE
    OBJECTS     {
        radiusServerInetAddressType,
        radiusServerInetAddress,
        radiusServerOperStatus
    }
    STATUS      current
    DESCRIPTION
        "The radiusInetServerOperStatusChange notification is generated when
         the operational status of a Radius server has transitioned either from
         'up' to 'down' or from 'down' to 'up'."
    ::= { tmnxSysNotifications 36 }

persistencyEventReport           NOTIFICATION-TYPE
    OBJECTS     {
        tmnxPersistencyNotifyMsg
    }
    STATUS      current
    DESCRIPTION
        "The persistencyEventReport notification is generated when a
         client-specific persistence event occurs (e.g. the start and
         completion of a recover action after system startup)."
    ::= { tmnxSysNotifications 37 }

sbiBootConfigFailFileError       NOTIFICATION-TYPE
    OBJECTS     {
        sbiBootConfigFailScript
    }
    STATUS      current
    DESCRIPTION
        "The sbiBootConfigFailFileError notification is generated when
         sbiBootConfigFailScript file cannot be accessed."
    ::= { tmnxSysNotifications 38 }

sbiBootConfigOKFileError         NOTIFICATION-TYPE
    OBJECTS     {
        sbiBootConfigOKScript
    }
    STATUS      current
    DESCRIPTION
        "The sbiBootConfigOKFileError notification is generated when
         sbiBootConfigOKScript file cannot be accessed."
    ::= { tmnxSysNotifications 39 }

sbiBootLiConfig                  NOTIFICATION-TYPE
    OBJECTS     {
        sliConfigStatus,
        sbiLiSeparate,
        sbiLiLocalSave
    }
    STATUS      current
    DESCRIPTION
        "The sbiBootLiConfig notification is generated upon completion of
         the Lawful Intercept (LI) configuration phase following a system
         reboot.  This notification is generated periodically, about once
         an hour.

         This event is generated only from the LI context."
    ::= { tmnxSysNotifications 40 }

persistenceRestoreProblem        NOTIFICATION-TYPE
    OBJECTS     {
        tmnxPersistencyClient,
        tmnxPersistencyNotifyMsg
    }
    STATUS      current
    DESCRIPTION
        "The persistenceRestoreProblem notification is generated when an error
         is detected while processing a persistence record."
    ::= { tmnxSysNotifications 41 }

tmnxSysRollbackStarted           NOTIFICATION-TYPE
    OBJECTS     {
        tmnxSysRollbackIndex,
        tmnxSysRollbackFileType,
        tmnxLogExecRollbackOpIndex
    }
    STATUS      current
    DESCRIPTION
        "[CAUSE] The tmnxSysRollbackStarted notification is generated when the
         user initiates a revert of the rollback checkpoint file specified by
         tmnxSysRollbackIndex and tmnxSysRollbackFileType. The value of
         tmnxLogExecRollbackOpIndex indicates the row entry in the
         TIMETRA-LOG-MIB::tmnxLogExecRollbackOpTable for this rollback revert
         operation.

         [EFFECT] The specified file is executed and system configuration may
         change.

         [RECOVERY] There is no recovery required for this notification."
    ::= { tmnxSysNotifications 42 }

tmnxSysRollbackStatusChange      NOTIFICATION-TYPE
    OBJECTS     {
        tmnxSysRollbackIndex,
        tmnxSysRollbackResult,
        tmnxSysRollbackFileType,
        tmnxLogExecRollbackOpIndex
    }
    STATUS      current
    DESCRIPTION
        "[CAUSE] The tmnxSysRollbackStatusChange notification is
         generated upon the completion of a rollback revert as specified
         by tmnxSysRollbackIndex and tmnxSysRollbackFileType.  The value
         of tmnxLogExecRollbackOpIndex indicates the row entry in the
         TIMETRA-LOG-MIB::tmnxLogExecRollbackOpTable for this rollback
         revert operation.

         [EFFECT] The result is indicated by the value of
         tmnxSysRollbackResult.

         [RECOVERY] When the value of tmnxSysRollbackResult is none, inProgress
         or success no recovery is required. When the value is failed, the user
         should try to determine the reason for the failure. The user can
         attempt a recovery by reverting back to a known good checkpoint. The
         user may reboot the system with the bof pointing to a saved
         configuration file."
    ::= { tmnxSysNotifications 43 }

tmnxSysRollbackSaveStatusChange  NOTIFICATION-TYPE
    OBJECTS     {
        tmnxSysRollbackSaveResult,
        tmnxSysRollbackFileType
    }
    STATUS      current
    DESCRIPTION
        "[CAUSE] The tmnxSysRollbackSaveStatusChange notification is generated
         upon the completion of a rollback save as specified by
         tmnxSysRollbackFileType.

         [EFFECT] The result is indicated by value of
         tmnxSysRollbackSaveResult.

         [RECOVERY] When the value of tmnxSysRollbackSaveResult is none,
         inProgress or success no recovery is required. When the value is
         failed, the user should try to determine the reason for the failure.
         The user can attempt a recovery by attempting the rollback save again."
    ::= { tmnxSysNotifications 44 }

tmnxSysRollbackFileDeleteStatus  NOTIFICATION-TYPE
    OBJECTS     {
        tmnxSysRollbackIndex,
        tmnxSysRollbackFileDeleteResult,
        tmnxSysRollbackFileType
    }
    STATUS      current
    DESCRIPTION
        "[CAUSE] The tmnxSysRollbackFileDeleteStatus notification is generated
         upon the completion of a rollback file delete as specified by
         tmnxSysRollbackIndex and tmnxSysRollbackFileType.

         [EFFECT] The result is indicated by the value of
         tmnxSysRollbackFileDeleteResult.

         [RECOVERY] When the value of tmnxSysRollbackFileDeleteResult is none,
         inProgress or success no recovery is required. When the value is
         failed, the user should try to determine the reason for the failure.
         The user can attempt a recovery by deleting the file again."
    ::= { tmnxSysNotifications 45 }

ssiSyncRollbackOK                NOTIFICATION-TYPE
    STATUS      current
    DESCRIPTION
        "[CAUSE]  The ssiSyncRollbackOK event is generated when the
         synchronization of rollback files between the primary
         and secondary CPMs finishes without errors.

         [EFFECT] Rollback files are synchronized.

         [RECOVERY] No recovery is necessary."
    ::= { tmnxSysNotifications 46 }

ssiSyncRollbackFailed            NOTIFICATION-TYPE
    OBJECTS     {
        tmnxSyncFailureReason
    }
    STATUS      current
    DESCRIPTION
        "[CAUSE] The ssiSyncRollbackFailed event is generated when the
         synchronization of rollback files between the primary and secondary
         CPMs is stopped due to errors. The tmnxSyncFailureReason will state
         the reason for the failure.

         [EFFECT] Rollback files are not synchronized.

         [RECOVERY] The user should try to determine the cause of the failure
         and can attempt synchronizing the files again."
    ::= { tmnxSysNotifications 47 }

ssiSyncCertOK                    NOTIFICATION-TYPE
    STATUS      current
    DESCRIPTION
        "[CAUSE]  The ssiSyncCertOK event is generated when the
         synchronization of certificate files between the primary
         and secondary CPMs finishes without errors.

         [EFFECT] Certificate files are synchronized.

         [RECOVERY] No recovery is necessary."
    ::= { tmnxSysNotifications 48 }

ssiSyncCertFailed                NOTIFICATION-TYPE
    OBJECTS     {
        tmnxSyncFailureReason
    }
    STATUS      current
    DESCRIPTION
        "[CAUSE] The ssiSyncCertFailed event is generated when the
         synchronization of certificate files between the primary and secondary
         CPMs is stopped due to errors. The tmnxSyncFailureReason will state
         the reason for the failure.

         [EFFECT] Certificate files are not synchronized.

         [RECOVERY] The user should try to determine the cause of the failure
         and can attempt synchronizing the files again."
    ::= { tmnxSysNotifications 49 }

persistencyFileSysThresRaised    NOTIFICATION-TYPE
    OBJECTS     {
        tmnxPersistenceAffectedCpm,
        tmnxPersistencyClient,
        tmnxPersistencyFileLocator,
        tmnxPersistencyNotifyMsg
    }
    STATUS      current
    DESCRIPTION
        "The persistencyFileSysThresRaised notification is generated when the
         filesystem reaches 90 percent occupation."
    ::= { tmnxSysNotifications 50 }

persistencyFileSysThresCleared   NOTIFICATION-TYPE
    OBJECTS     {
        tmnxPersistenceAffectedCpm,
        tmnxPersistencyClient,
        tmnxPersistencyFileLocator,
        tmnxPersistencyNotifyMsg
    }
    STATUS      current
    DESCRIPTION
        "The persistencyFileSysThresCleared notification is generated when the
         filesystem drops below 90 percent occupation."
    ::= { tmnxSysNotifications 51 }

tmnxSysExecStarted               NOTIFICATION-TYPE
    OBJECTS     {
        tmnxSysExecScript,
        tmnxLogExecRollbackOpIndex,
        tmnxLogExecRollbackOpType
    }
    STATUS      current
    DESCRIPTION
        "[CAUSE] The tmnxSysExecStarted notification is generated when the user
         initiates a CLI 'exec' operation to process a file of SROS CLI
         commands or processing of 'vsd' configuration messages have been
         initiated.

         The value of tmnxSysExecScript indicates the command file when the
         value of tmnxLogExecRollbackOpType is 'exec' or an empty string when
         the value of tmnxLogExecRollbackOpType is 'vsd'. The value of
         tmnxLogExecRollbackOpIndex indicates the row entry in
         TIMETRA-LOG-MIB::tmnxLogExecRollbackOpTable for this CLI 'exec' or
         'vsd' operation.

         [EFFECT] All change notifications generated after the generation of
         this notification and before the tmnxSysExecFinished will be logged in
         the TIMETRA-LOG-MIB::tmnxLogExecRollbackEventEntry. Once the
         tmnxSysExecFinished notification is triggered, a Network Management
         System (NMS) is able to walk the aforementioned log table to retrieve
         the list of all objects that have been modified during this
         transaction.

         [RECOVERY] There is no recovery required for this notification."
    ::= { tmnxSysNotifications 52 }

tmnxSysExecFinished              NOTIFICATION-TYPE
    OBJECTS     {
        tmnxSysExecScript,
        tmnxSysExecResult,
        tmnxLogExecRollbackOpIndex,
        tmnxLogExecRollbackOpType
    }
    STATUS      current
    DESCRIPTION
        "[CAUSE] The tmnxSysExecFinished notification is generated upon the
         completion of the execution of a CLI command file or execution of vsd
         configuration messages is completed.

         The value of tmnxSysExecScript indicates the command file when the
         value of tmnxLogExecRollbackOpType is 'exec' or an empty string when
         the value of tmnxLogExecRollbackOpType is 'vsd'. The value of
         tmnxLogExecRollbackOpIndex indicates the row entry in
         TIMETRA-LOG-MIB::tmnxLogExecRollbackOpTable for this CLI 'exec' or
         'vsd' operation.

         [EFFECT] The effect is that the entry for the specified
         tmnxLogExecRollbackOpIndex won't be updated, and no further
         notifications will be added to the specified index in the logger.

         [RECOVERY] When the value of tmnxSysExecResult is 'none' or 'success',
         no recovery is required.

         When the value is 'fail', the system may be left in an inconsistent
         state and the user should try to determine the reason for the failure.
         The user can attempt a recovery by manually entering CLI commands to
         reverse the failed configuration.  The user can attempt a recovery by
         performing a rollback revert to a known good checkpoint. The user can
         attempt a recovery by rebooting the system with the bof pointing to a
         saved configuration file."
    ::= { tmnxSysNotifications 53 }

tmnxSysRollbackSaveStarted       NOTIFICATION-TYPE
    OBJECTS     {
        tmnxSysRollbackFileType
    }
    STATUS      current
    DESCRIPTION
        "[CAUSE] The tmnxSysRollbackSaveStarted notification is generated when
         the user initiates a rollback save as specified by
         tmnxSysRollbackFileType.

         [EFFECT] The specified configuration file is saved.

         [RECOVERY] There is no recovery required for this notification."
    ::= { tmnxSysNotifications 54 }

tmnxSysRollbackDeleteStarted     NOTIFICATION-TYPE
    OBJECTS     {
        tmnxSysRollbackIndex,
        tmnxSysRollbackFileType
    }
    STATUS      current
    DESCRIPTION
        "[CAUSE] The tmnxSysRollbackDeleteStarted notification is generated
         when the user initiates a rollback delete as specified by
         tmnxSysRollbackIndex and tmnxSysRollbackFileType.

         [EFFECT] The specified configuration file is deleted.

         [RECOVERY] There is no recovery required for this notification."
    ::= { tmnxSysNotifications 55 }

tmnxSysNvsysFileError            NOTIFICATION-TYPE
    OBJECTS     {
        tmnxSysFileErrorType
    }
    STATUS      current
    DESCRIPTION
        "[CAUSE] The tmnxSysNvsysFileError notification is generated when there
         is a failure in accessing the nvsys file as specified by
         tmnxSysFileErrorType.

         [EFFECT] The specified nvsys file operation is unsuccessful.

         [RECOVERY] The user should investigate why the failure occurred. A
         failure can indicate a problem with the compact flash."
    ::= { tmnxSysNotifications 56 }

sysDNSSecFailedAuthentication    NOTIFICATION-TYPE
    OBJECTS     {
        sysDNSSecRespCtrl,
        tmnxSysDNSSecDomainName
    }
    STATUS      current
    DESCRIPTION
        "[CAUSE] The sysDNSSecFailedAuthentication notification is generated
         when a DNS response PDU is received with an unset AD-bit and
         sysDNSSecAdValidation is set to 'true (1)'.

         [EFFECT] This notification is informational only. The message will
         vary depending on the state of sysDNSSecRespCtrl.

         [RECOVERY] There is no recovery required for this notification."
    ::= { tmnxSysNotifications 57 }

tmnxConfigConflict               NOTIFICATION-TYPE
    OBJECTS     {
        tmnxNotifyRow,
        tmnxNotifyEntryOID,
        tmnxNotifyObjectName
    }
    STATUS      current
    DESCRIPTION
        "A tmnxConfigConflict notification is generated when a configuration
         attribute associated with a row entry in a MIB table is in conflict
         with another attribute.

         It can be used by the NMS to trigger maintenance polls of the
         configuration information."
    ::= { tmnxSysNotifications 58 }

tmnxSysLicenseInvalid            NOTIFICATION-TYPE
    OBJECTS     {
        tmnxHwClass,
        tmnxSysLicenseErrorReason,
        tmnxSysLicenseTimeLeft,
        tmnxSysLicenseErrorAction
    }
    STATUS      current
    DESCRIPTION
        "[CAUSE] The tmnxSysLicenseInvalid notification is generated when the
         license becomes invalid for the reason specified in
         tmnxSysLicenseErrorReason.

         [EFFECT] The CPM or system will reboot at the end of the time
         remaining, as specified by tmnxSysLicenseTimeLeft and
         tmnxSysLicenseErrorAction.

         [RECOVERY] Configure a valid license file location and file name,
         given the value of tmnxSysLicenseErrorReason."
    ::= { tmnxSysNotifications 59 }

tmnxSysLicenseExpiresSoon        NOTIFICATION-TYPE
    OBJECTS     {
        tmnxHwClass,
        tmnxSysLicenseTimeLeft
    }
    STATUS      current
    DESCRIPTION
        "[CAUSE] The tmnxSysLicenseExpiresSoon notification is generated when
         the license is due to expire soon.

         [EFFECT] The system will reboot at the end of the time remaining, as
         specified by tmnxSysLicenseTimeLeft.

         [RECOVERY] Configure a valid license file location and file name."
    ::= { tmnxSysNotifications 60 }

tmnxSysVsdServerAvailable        NOTIFICATION-TYPE
    OBJECTS     {
        tmnxSysNotifVsdServerName
    }
    STATUS      current
    DESCRIPTION
        "[CAUSE] The tmnxSysVsdServerAvailable notification is generated when
         system discover a new VSD server.

         [EFFECT] System will use this information to establish communication
         with new VSD server as needed.

         [RECOVERY] None needed."
    ::= { tmnxSysNotifications 63 }

tmnxSysVsdServerUnavailable      NOTIFICATION-TYPE
    OBJECTS     {
        tmnxSysNotifVsdServerName
    }
    STATUS      current
    DESCRIPTION
        "[CAUSE] The tmnxSysVsdServerAvailable notification is generated when
         system loses connection to VSD.

         [EFFECT] System will use this information and stop communication with
         this VSD server as needed.

         [RECOVERY] None needed."
    ::= { tmnxSysNotifications 64 }

tmnxSysXmppServerFunctional      NOTIFICATION-TYPE
    OBJECTS     {
        tmnxSysNotifXmppServerName
    }
    STATUS      current
    DESCRIPTION
        "[CAUSE] The tmnxSysXmppServerFunctional notification is generated when
         system discover a new XMPP server.

         [EFFECT] System will use this information to establish communication
         with new XMPP server as needed.

         [RECOVERY] None needed."
    ::= { tmnxSysNotifications 65 }

tmnxSysXmppServerNotFunctional   NOTIFICATION-TYPE
    OBJECTS     {
        tmnxSysNotifXmppServerName
    }
    STATUS      current
    DESCRIPTION
        "[CAUSE] The tmnxSysXmppServerNotFunctional notification is generated
         when system can not communicate with XMPP server.

         [EFFECT] Communication with XMPP server will stop.

         [RECOVERY] Check to see why XMPP server has stopped communicating."
    ::= { tmnxSysNotifications 66 }

tmnxSysLicenseValid              NOTIFICATION-TYPE
    OBJECTS     {
        tmnxHwClass
    }
    STATUS      current
    DESCRIPTION
        "[CAUSE] The tmnxSysLicenseValid notification is generated once after
         the system boots up and the license is determined by the system to be
         valid.

         [EFFECT] The system is running with the license specified in
         tmnxSysLicenseName.

         [RECOVERY] No recovery."
    ::= { tmnxSysNotifications 67 }

tmnxSysBaseMacAddressNotSet      NOTIFICATION-TYPE
    OBJECTS     {
        tmnxChassisBaseMacAddress
    }
    STATUS      current
    DESCRIPTION
        "[CAUSE] The tmnxSysBaseMacAddressNotSet notification is generated once
         after the system boots up and the value of sbiSystemBaseMacAddress is
         all zeroes.

         [EFFECT] The system software is using the base MAC address specified
         in tmnxChassisBaseMacAddress which may not be unique.

         [RECOVERY] Configure sbiSystemBaseMacAddress to a value other than all
         zeroes."
    ::= { tmnxSysNotifications 68 }

tmnxSmLaunchStartFailed          NOTIFICATION-TYPE
    OBJECTS     {
        tmnxEhsHEntryScriptPlcyOwner,
        tmnxEhsHEntryScriptPlcyName,
        smLaunchScriptOwner,
        smLaunchScriptName,
        smLaunchError,
        tmnxSmLaunchExtAuthType,
        tmnxSmRunExtAuthType,
        tmnxSmRunExtUserName
    }
    STATUS      current
    DESCRIPTION
        "[CAUSE] The tmnxSmLaunchStartFailed notification is generated when the
         launch start fails because of one of the following reasons:
            1. The values of smLaunchScriptOwner and smLaunchScriptName don't
            have an existing entry in the smScriptTable.
            2. The value of smScriptOperStatus is not 'enabled'.
            3. The smScriptSource value is NULL.
            4. The value of smLaunchOperStatus object in smLaunchTable is not
            'enabled'.
            5. The check to see if the run Index is already in use fails.
            6. The number of currently executing scripts invoked from this
            smLaunchTable entry is greater than smLaunchMaxRunning.

          [EFFECT] The result is indicated by incrementing the value of
            tmnxEhsHEntryStatsErrLaunch.
          [RECOVERY] No recovery is necessary."
    ::= { tmnxSysNotifications 69 }

tmnxEhsHandlerInvoked            NOTIFICATION-TYPE
    OBJECTS     {
        tmnxEhsHandlerDescription,
        tmnxSmRunExtAuthType,
        tmnxSmRunExtUserName
    }
    STATUS      current
    DESCRIPTION
        "[CAUSE] The tmnxEhsHandlerInvoked notification is generated when the
         following checks pass: 1. A check to see if a event trigger is present
         for a particular log event based on the log event application-id and
         event-id/event name. 2. Evaluation of the log filter associated with
         the trigger-entry.

         [EFFECT] This may create a run entry to execute scripts.

         [RECOVERY] No recovery is necessary."
    ::= { tmnxSysNotifications 70 }

tmnxEhsDroppedByMinDelay         NOTIFICATION-TYPE
    OBJECTS     {
        tmnxEhsHEntryScriptPlcyOwner,
        tmnxEhsHEntryScriptPlcyName,
        smLaunchScriptOwner,
        smLaunchScriptName,
        tmnxEhsHEntryMinDelay,
        tmnxEhsHEntryMinDelayInterval,
        tmnxSmRunExtAuthType,
        tmnxSmRunExtUserName
    }
    STATUS      current
    DESCRIPTION
        "[CAUSE] The tmnxEhsDroppedByMinDelay is generated when two consecutive
         executions of script policy specified by the same event handler entry
         occurs within the time period specified by tmnxEhsHEntryMinDelay.

         [EFFECT] The value of tmnxEhsHEntryStatsErrMinDelay gets incremented.

         [RECOVERY] No recovery is necessary."
    ::= { tmnxSysNotifications 71 }

tmnxSysAppStats24HrsAvailable    NOTIFICATION-TYPE
    OBJECTS     {
        tmnxSysNotifAppStatsTime,
        tmnxSysNotifAppStatsApplication,
        tmnxSysNotifAppStatsType
    }
    STATUS      current
    DESCRIPTION
        "[CAUSE] The system generates the tmnxSysAppStats24HrsAvailable
         notification when new rows are available in the
         tmnxSysAppStats24HrsTable.

         The value of tmnxSysNotifAppStatsTime indicates the time the system
         collected the values in the new rows.

         A non-zero value of tmnxSysNotifAppStatsApplication indicates the
         application; a zero value of tmnxSysNotifAppStatsApplication indicates
         that new values are available for all active applications.

         A non-zero value of tmnxSysNotifAppStatsType indicates the type of
         statistics; a zero value of tmnxSysNotifAppStatsType indicates that
         new values are available for all active types.

         [EFFECT] None.

         [RECOVERY] No recovery is necessary."
    ::= { tmnxSysNotifications 72 }

tmnxSysAppStatsWeekAvailable     NOTIFICATION-TYPE
    OBJECTS     {
        tmnxSysNotifAppStatsTime
    }
    STATUS      current
    DESCRIPTION
        "[CAUSE] The system generates the tmnxSysAppStatsWeekAvailable
         notification when new rows are available in the
         tmnxSysAppStatsWeekTable.

         The value of tmnxSysNotifAppStatsTime indicates the time the system
         collected the values in the new rows.

         [EFFECT] None.

         [RECOVERY] No recovery is necessary."
    ::= { tmnxSysNotifications 73 }

tmnxSysLicenseActivated          NOTIFICATION-TYPE
    OBJECTS     {
        tmnxHwClass
    }
    STATUS      current
    DESCRIPTION
        "[CAUSE] The tmnxSysLicenseActivated notification is generated each
         time a license is activated by the system.

         [EFFECT] The system is running with the license specified in
         tmnxSysLicenseName.

         [RECOVERY] No recovery."
    ::= { tmnxSysNotifications 75 }

tmnxSysStandbyLicensingError     NOTIFICATION-TYPE
    OBJECTS     {
        tmnxHwClass,
        tmnxSysLicenseErrorReason
    }
    STATUS      current
    DESCRIPTION
        "[CAUSE] The tmnxSysStandbyLicensingError notification is generated
         when a licensing issue has been detected by the standby. The reason is
         specified in tmnxSysLicenseErrorReason.

         [EFFECT] The Standby CPM may not synchronized and may be put into a
         failed state depending on the failure.

         [RECOVERY] Ensure a valid license file location and file name,
         given the value of tmnxSysLicenseErrorReason.  Reset the Standby CPM or activate
         a valid license."
    ::= { tmnxSysNotifications 76 }

tmnxSysStandbyLicensingReady     NOTIFICATION-TYPE
    OBJECTS     {
        tmnxHwClass
    }
    STATUS      current
    DESCRIPTION
        "[CAUSE] The tmnxSysStandbyLicensingReady notification is generated
         when a licensing has been successfully activated by the standby.

         [EFFECT] Any licensing errors detected by the Standby CPM are cleared.

         [RECOVERY] None."
    ::= { tmnxSysNotifications 77 }

tmnxSysMgmtIfModeChangeStart     NOTIFICATION-TYPE
    OBJECTS     {
        tmnxNotifySysMgmtIfOriginalMode,
        tmnxSysMgmtIfWriteMode,
        tmnxSysMgmtIfWriteSwitchReason
    }
    STATUS      current
    DESCRIPTION
        "[CAUSE] The tmnxSysMgmtIfModeChangeStart notification is generated
         when a management interface configuration mode change request is sent.

         [EFFECT] Switching modes between any configuration mode will lock the
         configuration datastores from operator input until the mode switch has
         completed.

         [RECOVERY] None."
    ::= { tmnxSysNotifications 78 }

tmnxSysMgmtIfModeChangeComplete  NOTIFICATION-TYPE
    OBJECTS     {
        tmnxSysMgmtIfWriteMode
    }
    STATUS      current
    DESCRIPTION
        "[CAUSE] The tmnxSysMgmtIfModeChangeComplete notification is generated
         when a management interface configuration mode change request is
         complete.

         [EFFECT] Switching modes between any configuration mode will lock the
         configuration datastores from operator input until the mode switch has
         completed. Once this event is triggered the configuration datastores
         are unlocked for operator input.

         [RECOVERY] None."
    ::= { tmnxSysNotifications 79 }

tmnxSysMgmtIfModeChangeFailure   NOTIFICATION-TYPE
    OBJECTS     {
        tmnxSysMgmtIfWriteMode
    }
    STATUS      current
    DESCRIPTION
        "[CAUSE] The tmnxSysMgmtIfModeChangeFailure notification is generated
         when a management interface configuration mode change request fails to
         complete.

         [EFFECT] Switching modes between any configuration mode will lock the
         configuration datastores from operator input until the mode switch has
         completed. When this event is triggered the mode change is declared
         unsuccessful; the effective configuration mode will be indicated in
         this notification. The configuration datastores are unlocked for
         operator input.

         [RECOVERY] None."
    ::= { tmnxSysNotifications 80 }

tmnxSysAppLicenseInsufficient    NOTIFICATION-TYPE
    OBJECTS     {
        tmnxSysLicensingNotifyGroup,
        tmnxSysLicensedNotifyAppName,
        tmnxSysAppLicenseState,
        tmnxSysLicenseErrorReason
    }
    STATUS      current
    DESCRIPTION
        "[CAUSE] The tmnxSysAppLicenseInsufficient notification is generated periodically
         when licensing for an application is detected to be insufficient.  The details
         of the error is specified in tmnxSysLicenseErrorReason.
         This notification cannot be suppressed.

         [EFFECT] Notification generated periodically while the application
         remains in this condition.

         [RECOVERY] Activate a system license containing sufficient license
         entitlements for this application."
    ::= { tmnxSysNotifications 81 }

tmnxSysMgmtIfLiIncorrectFormat   NOTIFICATION-TYPE
    OBJECTS     {
        tmnxPrimaryConfigFileFormatType,
        tmnxLiConfigFileFormatType
    }
    STATUS      current
    DESCRIPTION
        "[CAUSE] The tmnxSysMgmtIfLiIncorrectFormat notification is generated
         when a format (classic or model-driven) of the Lawful Intercept (LI)
         configuration file does not match primary configuration file format.

         [EFFECT] The Lawful Intercept (LI) configuration file is not loaded
         during the boot.

         [RECOVERY] Reboot with the correct Lawful Intercept (LI) configuration
         file"
    ::= { tmnxSysNotifications 82 }

tmnxSysMgmtIfLiCfgNotEncrypted   NOTIFICATION-TYPE
    STATUS      current
    DESCRIPTION
        "[CAUSE] The tmnxSysMgmtIfLiCfgNotEncrypted notification is generated
         when the Lawful Intercept (LI) configuration file is not encrypted.

         [EFFECT] The Lawful Intercept (LI) configuration file is not loaded
         during the boot.

         [RECOVERY] Reboot with the correct Lawful Intercept (LI) configuration
         file"
    ::= { tmnxSysNotifications 83 }

tmnxSysLicenseUpdateRequired     NOTIFICATION-TYPE
    OBJECTS     {
        tmnxHwClass
    }
    STATUS      current
    DESCRIPTION
        "[CAUSE] The tmnxSysLicenseUpdateRequired notification is generated once after
         the system boots up and the license is determined by the system to be  valid, but
         requires to be updated to the correct software version.

         [EFFECT] The system will use the license until it is updated.

         [RECOVERY] Update and activate the updated license."
    ::= { tmnxSysNotifications 84 }

tmnxEqOperStateChange            NOTIFICATION-TYPE
    OBJECTS     {
        tmnxNotifyRow,
        tmnxNotifyRowOperState,
        tmnxNotifyEntryOID,
        tmnxNotifyObjectName
    }
    STATUS      current
    DESCRIPTION
        "[CAUSE] The tmnxEqOperStateChange notification is generated when a
         change occurred in the operational state on the piece of hardware.

         [EFFECT] If the state has changed to out of service, then all ports
         and services associated with the module change to out of service and
         traffic is impacted.

         [RECOVERY] Investigation is required to determine the cause of the
         change."
    ::= { tmnxSysNotifications 85 }

tmnxSysMGNotifications           OBJECT IDENTIFIER ::= { tmnxSysMIBNotifyPrefix 1 }

END
