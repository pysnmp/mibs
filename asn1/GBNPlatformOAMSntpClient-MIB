GBNPlatformOAMSntpClient-MIB DEFINITIONS ::= BEGIN

    IMPORTS
        MODULE-IDENTITY, OBJECT-TYPE,
        Counter32, Gauge32,
        Unsigned32, Integer32,
        IpAddress                               FROM SNMPv2-SMI
        
        RowStatus, TruthValue, 
        DisplayString, MacAddress               FROM SNMPv2-TC
        
        MODULE-COMPLIANCE, OBJECT-GROUP         FROM SNMPv2-CONF
        
        gbnPlatformOAM                          FROM GBNPlatformOAM-MIB;
 
   
    gbnPlatformOAMSntpClient  MODULE-IDENTITY
        LAST-UPDATED    "0107152004Z"  -- July 15, 2004
        ORGANIZATION    "admin Systems, Inc."
        CONTACT-INFO    "admin Systems, Inc.
                         E-mail: support@admin.com.cn"

        DESCRIPTION     "SNTP mib definition."

        REVISION        "0107152004Z"  -- July 15, 2004
        DESCRIPTION     "Initial MIB creation."

        ::= { gbnPlatformOAM 8 }

------------------------------------------------------------------------------
------------------------------------------------------------------------------     
--  sntpClientGeneral:
------------------------------------------------------------------------------

    sntpClientGeneral         OBJECT IDENTIFIER ::= { gbnPlatformOAMSntpClient 1 }  
    
    sntpClientMode OBJECT-TYPE
       SYNTAX  INTEGER  {
                        unicast (1),
                        anycast(2),
                        broadcast(4),
                        multicast(8) }
        MAX-ACCESS  read-write
        STATUS  current
        DESCRIPTION
            "SNTP"
        DEFVAL  { broadcast }            
        ::= { sntpClientGeneral 1 }  
        
    sntpClientPollInterval OBJECT-TYPE
        SYNTAX INTEGER( 64..1024 )
        MAX-ACCESS  read-write
        STATUS  current
        DESCRIPTION
            ""
        DEFVAL  { 1000 }                 
        ::= { sntpClientGeneral 2 }              
       
    sntpClientRetransInterval OBJECT-TYPE
        SYNTAX INTEGER( 1..30 )
        MAX-ACCESS  read-write
        STATUS  current
        DESCRIPTION
            ""
        DEFVAL  { 5 }                 
        ::= { sntpClientGeneral 3 }  
        
    sntpClientRetransTimes OBJECT-TYPE
        SYNTAX INTEGER( 0..10 )
        MAX-ACCESS  read-write
        STATUS  current
        DESCRIPTION
            ""
        DEFVAL  { 0 }            
        ::= { sntpClientGeneral 4 }       
        
    sntpClientServer OBJECT-TYPE
        SYNTAX IpAddress
        MAX-ACCESS  read-write
        STATUS  current
        DESCRIPTION
            ""
        ::= { sntpClientGeneral 5 }  
        
    sntpClientSynthFlag OBJECT-TYPE
        SYNTAX TruthValue
        MAX-ACCESS  read-only
        STATUS  current
        DESCRIPTION
            ""
        ::= { sntpClientGeneral 6 }               
        
    sntpClientState OBJECT-TYPE
        SYNTAX INTEGER
        MAX-ACCESS  read-only
        STATUS  current
        DESCRIPTION
            ""
        ::= { sntpClientGeneral 7 }  
        
    sntpClientLastSynthTime OBJECT-TYPE
        SYNTAX Integer32
        MAX-ACCESS  read-only
        STATUS  current
        DESCRIPTION
            ""
        ::= { sntpClientGeneral 8 }               
        
    sntpClientLastSynthErrno OBJECT-TYPE
        SYNTAX INTEGER
        MAX-ACCESS  read-only
        STATUS  current
        DESCRIPTION
            ""
        ::= { sntpClientGeneral 9 }      
        
    sntpClientAdminStatus OBJECT-TYPE
        SYNTAX INTEGER{
                     enable(1),
                     disable(2)
                     }
        MAX-ACCESS  read-write
        STATUS  current
        DESCRIPTION
            ""
        ::= { sntpClientGeneral 10 }    
        
    sntpClientBcastDelay OBJECT-TYPE
        SYNTAX INTEGER ( 1..9999 )    
        MAX-ACCESS  read-write
        STATUS  current
        DESCRIPTION
            "()"
        ::= { sntpClientGeneral 11 }  
        
     sntpClientMcastTtl OBJECT-TYPE
        SYNTAX INTEGER ( 1..255 )    
        MAX-ACCESS  read-write
        STATUS  current
        DESCRIPTION
            "TTL"
        ::= { sntpClientGeneral 12 }  
    
      sntpClientAuthFlag OBJECT-TYPE
        SYNTAX TruthValue    
        MAX-ACCESS  read-write
        STATUS  current
        DESCRIPTION
            "authentication enable flag"  
             --TRUEFALSE--
        ::= { sntpClientGeneral 13 }   
        
      sntpClientUniKeyID OBJECT-TYPE
        SYNTAX Unsigned32    
        MAX-ACCESS  read-write
        STATUS  current
        DESCRIPTION
            "in client/server mode, client send request with this keyID"  
             --/keyID--
        ::= { sntpClientGeneral 14 }         
   
      sntpClientAnyKeyID OBJECT-TYPE
        SYNTAX Unsigned32    
        MAX-ACCESS  read-write
        STATUS  current
        DESCRIPTION
            "in anycast mode, client send request with this keyID"  
             --keyID--
        ::= { sntpClientGeneral 15 }                   
      sntpClientServerBackup OBJECT-TYPE
        SYNTAX IpAddress
        MAX-ACCESS  read-write
        STATUS  current
        DESCRIPTION
            "server backup"
        ::= { sntpClientGeneral 16 }  
    
------------------------------------------------------------------------------     
--  sntpValidSrcTable:
------------------------------------------------------------------------------
    
  sntpClientValidServerTable OBJECT-TYPE
        SYNTAX   SEQUENCE OF SntpClientValidServerEntry
        MAX-ACCESS   not-accessible
        STATUS   current
        DESCRIPTION
           "SNTP
            "
       ::= { gbnPlatformOAMSntpClient 2 }

    sntpClientValidServerEntry OBJECT-TYPE
        SYNTAX   SntpClientValidServerEntry
        MAX-ACCESS   not-accessible
        STATUS   current
        DESCRIPTION
           "."
       INDEX { sntpClientValidServerNet, sntpClientValidServerMask }
       ::= { sntpClientValidServerTable 1 } 
         
    SntpClientValidServerEntry ::=
	    SEQUENCE {
	        sntpClientValidServerNet
	            IpAddress,
	        sntpClientValidServerMask
	            IpAddress,
	        sntpClientValidServerRowStatus
	            RowStatus        	            
	        }   
	        
    sntpClientValidServerNet OBJECT-TYPE
        SYNTAX   IpAddress
        MAX-ACCESS   read-only
        STATUS   current
        DESCRIPTION
           ""
        ::= { sntpClientValidServerEntry 1 } 
        
    sntpClientValidServerMask OBJECT-TYPE
        SYNTAX   IpAddress
        MAX-ACCESS   read-only
        STATUS   current
        DESCRIPTION
           ""
        ::= { sntpClientValidServerEntry 2 }         
                                                
    sntpClientValidServerRowStatus OBJECT-TYPE
        SYNTAX   RowStatus
        MAX-ACCESS   read-write
        STATUS   current
        DESCRIPTION
           ""
        ::= { sntpClientValidServerEntry 3 }   
        
------------------------------------------------------------------------------     
--  sntpAuthKeyTable:
------------------------------------------------------------------------------
    
  sntpAuthKeyTable OBJECT-TYPE
        SYNTAX   SEQUENCE OF SntpAuthKeyEntry
        MAX-ACCESS   not-accessible
        STATUS   current
        DESCRIPTION
           "keys userd for SNTP authentication"  
           --SNTP--
       ::= { gbnPlatformOAMSntpClient 3 }

    sntpAuthKeyEntry OBJECT-TYPE
        SYNTAX   SntpAuthKeyEntry
        MAX-ACCESS   not-accessible
        STATUS   current
        DESCRIPTION
           "define a key item."   
       INDEX { sntpAuthKeyId }
       ::= { sntpAuthKeyTable 1 } 
         
    SntpAuthKeyEntry ::=
	    SEQUENCE {
	        sntpAuthKeyId
	            Unsigned32,
	        sntpAuthKeyValue
	            DisplayString (SIZE (1..16)),  
	        sntpAuthKeyTrustFlag
	            TruthValue,
	        sntpAuthKeyRowStatus
	            RowStatus        	            
	        }   
	        
    sntpAuthKeyId OBJECT-TYPE
        SYNTAX   Unsigned32  ( 1..4294967295 )  
        MAX-ACCESS   read-only
        STATUS   current
        DESCRIPTION
           "key number" 
           --key ID--
        ::= { sntpAuthKeyEntry 1 } 
        
    sntpAuthKeyValue OBJECT-TYPE
        SYNTAX   DisplayString (SIZE (1..16))
        MAX-ACCESS   read-write
        STATUS   current
        DESCRIPTION
           "key value"    
           --16--
        ::= { sntpAuthKeyEntry 2 }    
        
    sntpAuthKeyTrustFlag OBJECT-TYPE
        SYNTAX   TruthValue
        MAX-ACCESS   read-write
        STATUS   current
        DESCRIPTION
           "whether the key is trusted" 
        ::= { sntpAuthKeyEntry 3 }   
                                                
    sntpAuthKeyRowStatus OBJECT-TYPE
        SYNTAX   RowStatus
        MAX-ACCESS   read-write
        STATUS   current
        DESCRIPTION
           "row status"
        ::= { sntpAuthKeyEntry 4 }                                                                             
                               
   END
