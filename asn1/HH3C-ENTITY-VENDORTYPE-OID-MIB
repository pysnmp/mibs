-- =================================================================
-- Copyright (c) 2004-2021 New H3C Tech. Co., Ltd.  All rights reserved.
--
-- Description: The definition of Entity Vendortype OID
-- Reference:
-- Version: V4.89
-- History:
-- V1.0 2004.05.13  Created by lvzhenfeng, modified by gaolong.
-- V1.1 2004.05.22  Adjusted by gaolong and lvzhenfeng.
--   1. Adjust module name to hh3cEntityVendorTypeOID and its location is set to { hh3c 3 }.
--   2. Rename module name prefix from hh3cevtModule to hh3cevtModuleRt_
--   and hh3cevtModuleSw_ for routers and switches seperately.
--   3. Add hh3cevtSubModuleRouter and hh3cevtSubModuleSwitch under hh3cevtModule.
--   4. Split port type into two groups, one for routers, another for switches.
-- V1.11 2004-06-17 add hh3cevtHotSwapFan node by limeng for garibaldi
-- V1.12 2004-07-19 add hh3cevtModuleSwitchType {117-138}
-- V1.13 2004-07-29 add hh3cevtPortSwitchType {50-58}
-- V1.14 2004-08-12 add hh3cevtModuleSw_LSA1FP8U(hh3cevtModuleSwitchType 139)
-- V1.15 2004-08-25 change enumeration name
--                     from hh3cevtModuleSw_LS81SFCA(120) to hh3cevtModuleSw_LS81SRPG0(120),
--                     from hh3cevtModuleSw_LS81SFCB(121) to hh3cevtModuleSw_LS81SRPG1(121),
--                     from hh3cevtModuleSw_LS81SFCC(122) to hh3cevtModuleSw_LS81SRPG2(122),
--                     from hh3cevtModuleSw_LS81SFCD(123) to hh3cevtModuleSw_LS81SRPG3(123).
--                  modify comments for these enumerations as well.
-- V1.2  2004-08-26 add sub identifier of hh3cevtPortSwitchType from 59 to 71.
-- V1.21 2004-09-08 add sub identifier of hh3cevtModuleSwitchType from 140 to 148.
-- V1.3  2004-09-14 add subidentifier under hh3cevtModuleSwitchType from 149 to 157 by wangyahui
--                  add subidentifier under hh3cevtModuleSwitchType from 158 to 159 by kangyinan
--                  add subidentifier under hh3cevtModuleSwitchType from 72 to 93 by wangyahui
--                  add subidentifier under hh3cevtModuleSwitchType from 94 to 96 by kangyinan
--                  add type description for hh3cevtModuleSw_SP4, hh3cevtModuleSw_UP1, hh3cevtModuleSw_XP4 by kangyinan
-- V2.0  2004-10-12 updated by gaolong
--                  Change all underscore('_') characters to hyphen characters('-') because underscore character is not allowed in MIB module.
--                  Remove some adjacent hyphens
-- V2.1  2004-10-19 add subidentifier under hh3cevtModuleSwitchType from 160 to 162 by kangyinan
--                  add subidentifier under hh3cevtPortSwitchType 97 by kangyinan
-- V2.2  2004-09-18 add sub identifier for hh3cevtModuleRouterType from 111 to 117 by taotao
-- V2.3  2004-11-18 add sub identifier 2 under hh3cevtFan by liyutao
-- V2.4  2004-11-23 add subidentifier under hh3cevtModuleSwitchType from 163 to 166 by zhangchengmei
-- V2.5  2004-12-04 add subidentifier 118 under hh3cevtModuleRouterType by lizhiyong
-- V2.6  2004-12-23 add sub identifier 4 to 7 under hh3cevtPowerSupply by Zhangjianfeng
--                  add sub identifier 167 to 169 under hh3cevtModuleSwitchType by Zhangjianfeng
-- V2.7  2004-12-26 add subidentifier 170 under hh3cevtModuleSwitchType by wangyahui
-- v2.8  2004-12-23 add subidentifier under hh3cevtModuleSwitchType from 171 to 172 and
--                  add sub identifier 98 to 99 under hh3cevtPortSwitchType by liyue
-- V2.9  2004-12-26 add sub identifier 173 under hh3cevtModuleSwitchType by Zhangjianfeng
--                  add sub identifier 100 for 24G cascade port under hh3cevtPort by Zhangjianfeng
-- V3.0  2004-01-07 add subidentifier 174 and 175 under hh3cevtModuleSwitchType by wangyahui
-- V3.1  2005-01-31 add subidentifier 176 under hh3cevtModuleSwitchType by wangyahui
-- V3.2  2005-02-26 add subidentifier 177 under hh3cevtModuleSwitchType by zhangchengmei
--                  add subidentifier 101 to 137 under hh3cevtPortSwitchType by zhangchengmei
--                  add subidentifier 178 under hh3cevtModuleSwitchType by zhouqiang
--                  add subidentifier 138 under hh3cevtPortSwitchType by zhouqiang
--                  add subidentifier 179 to 180 under hh3cevtModuleSwitchType by wangyahui
--                  remove trailing spaces
-- V3.3  2005-03-22 add subidentifier 181 to 187 under hh3cevtModuleSwitchType by zhangchengmei
-- V3.4  2004-12-29 add subidentifier 119 to 120 under hh3cevtModuleRouterType by lizhiyong
-- V3.5  2005-04-12 add subidentifier 141 to 144 under hh3cevtModuleRouterType by yinxiaoyu
--                  add subidentifier 30 to 33 under hh3cevtPortRouterType by yinxiaoyu
-- V3.6  2005-04-07 add subidentifier 121 to 140 under hh3cevtModuleRouterType by taotao
--                  change the name of subidentifier 118 under hh3cevtModuleRouterType by taotao
--                  adjust file format
-- V3.7  2005-05-10 add subidentifier 188 to 216 under hh3cevtModuleSwitchType by zhangchengmei
-- V3.8  2005-06-12 add subidentifier 145 to 149 under hh3cevtModuleRouterType,
--                  add subidentifier 34 under hh3cevtPortRouterType by wanghanlin
-- V3.9  2005-06-22 add subidentifier 150 under hh3cevtModuleRouterType by yinxiaoyu
-- V4.0  2005-07-18 add subidentifier 217 to 219 under hh3cevtModuleSwitchType by yangliming
--                  add subidentifier 139 to 142 under hh3cevtPortSwitchType by wangyahui
-- V4.01 2005-07-29 add subidentifier 220 to 225 under hh3cevtModuleSwitchType by wangyahui
-- V4.02 2005-07-21 change the name of subidentifier 183 under hh3cevtModuleSwitchType,
--                  add subidentifier 226 to 227 under hh3cevtModuleSwitchType by zhangchengmei
--       2005-08-29 add subidentifier 143 under hh3cevtPortSwitchType by qianxiaoyu
--                  add subidentifier 151 to 161 under hh3cevtModuleRouterType by taotao
--                  add subidentifier 35 to 41 under hh3cevtPortRouterType by taotao
-- V4.03 2005-09-07 add hh3cevtCPU and hh3cevtGeneralCPU by taotao
--                  add subidentifier 162 to 163 under hh3cevtModuleRouterType by taotao
--                  adjust file format by gaolong
-- V4.04 2005-09-13 add subidentifier 228 to 253 under hh3cevtModuleSwitchType by zhangchengmei
--       2005-09-13 add subidentifier 257 to 268 under hh3cevtModuleSwitchType by zhangchengmei
-- V4.05 2005-11-04 add subidentifier 144 to 149 under hh3cevtPortSwitchType by zhangchengmei
--                  add subidentifier 150 under hh3cevtPortSwitchType by huangyuetao
--                  add subidentifier 269 to 271 under hh3cevtModuleSwitchType by yangxiaopeng
--                  add subidentifier 272 under hh3cevtModuleSwitchType by qianxiaoyu
--                  add subidentifier 164 to 165 under hh3cevtModuleRouterType by xuejiayong
-- V4.06 2005-11-24 add subidentifier 500 to 501 under hh3cevtModuleSwitchType by wangyahui
-- V4.07 2005-11-28 add subidentifier 300 to 316 under hh3cevtModuleSwitchType by zhangchengmei
-- V4.08 2005-12-09 add subidentifier 220 to 223 under hh3cevtModuleRouterType by taotao
-- V4.09 2005-12-30 add subidentifier 151 to 170 under hh3cevtPortSwitchType by zhangchengmei
-- V4.10 2006-01-04 add subidentifier 701 under hh3cevtModuleSwitchType by qianxiaoyu
-- V4.11 2006-02-12 add subidentifier 200 to 219 under hh3cevtModuleRouterType by liutinghai
--                  add subidentifier 702 under hh3cevtModuleSwitchType by chenxiaohui
--                  add subidentifier 600 under hh3cevtModuleRouterType by qujin
--                  add subidentifier 317 under hh3cevtModuleSwitchType by zhangchengmei
-- V4.12 2006-02-24 add subidentifier 703 under hh3cevtModuleSwitchType by chijuntao
--                  add subidentifier 224 to 228 under hh3cevtModuleRouterType by taotao
-- V4.13 2006-02-27 add subidentifier 171 to 174 under hh3cevtPortSwitchType by wangshunli
--                  add subidentifier 318 to 336 under hh3cevtModuleSwitchType by zhaiyingying
-- V4.14 2006-03-14 add subidentifier 175 under hh3cevtPortSwitchType by wangyahui
--                  add subidentifier 502 to 504 under hh3cevtModuleSwitchType by wangyahui
-- V4.15 2006-04-03 add subidentifier 176 under hh3cevtPortSwitchType by wangyahui
-- V4.16 2006-04-26 add subidentifier 229 to 233 under hh3cevtModuleRouterType by taotao
-- V4.17 2006-04-21 add subidentifier 337 to 340 under hh3cevtModuleSwitchType by zhaiyingying
-- V4.18 2006-06-05 add subidentifier 704 to 705 under hh3cevtModuleSwitchType by zhangxianguo
--                  add subidentifier 505 to 506 under hh3cevtModuleSwitchType by zhangjianfeng
--                  add subidentifier 341 to 349 under hh3cevtModuleSwitchType by zhaiyingying
--                  add subidentifier 177 to 178 under hh3cevtPortSwitchType by zhangjianfeng
--                  add subidentifier 179 to 180 under hh3cevtPortSwitchType by zhangxianguo
-- V4.19 2006-08-23 add subidentifier 507 to 509 under hh3cevtModuleSwitchType by wangyahui
--                  modify object name of subidentifier 502 and 503 under hh3cevtModuleSwitchType by wangyahui
--                  add subidentifier 234 to 235 under hh3cevtModuleRouterType by liutinghai
--                  add subidentifier 350 to 357 under hh3cevtModuleSwitchType by zhaiyingying
-- V4.20 2006-09-26 add subidentifier 510 to 514 under hh3cevtModuleSwitchType by wangyahui
--                  add subidentifier 601 to 603 under hh3cevtModuleRouterType by zhoujianming
--                  add subidentifier 236 to 239 under hh3cevtModuleRouterType by qikai
--                  add subidentifier 240 to 241 under hh3cevtModuleRouterType by liutinghai
--                  add subidentifier 800 to 801 under hh3cevtModuleSwitchType by luoguixing
-- V4.21 2006-10-26 add subidentifier 358 to 370 under hh3cevtModuleSwitchType by zhaiyingying
--                  add subidentifier 183 under hh3cevtPortSwitchType by zhaiyingying
--                  add subidentifier 515 to 526 under hh3cevtModuleSwitchType by wangyahui
--                  add subidentifier 181 to 182 under hh3cevtPortSwitchType by wangyahui
-- V4.22 2006-11-02 add subidentifier 527 to 536 under hh3cevtModuleSwitchType by wangyahui
--                  modify description of 511 to 513 under hh3cevtModuleSwitchType by wangyahui
--       2006-11-10 add subidentifier 371 to 378 under hh3cevtModuleSwitchType by shuxiongtao
--       2006-11-08 add subidentifier 184 to 185 under hh3cevtPortSwitchType by zhaiyingying
-- V4.23 2006-12-04 add subidentifier 242 to 243 under hh3cevtModuleRouterType by liutinghai
-- V4.24 2006-01-24 add subidentifier 244 to 245 under hh3cevtModuleRouterType by liutinghai
-- V4.25 2007-03-19 add subidentifier 537 under hh3cevtModuleSwitchType by wangyahui
-- V4.26 2007-04-12 add subidentifier 538 to 542 under hh3cevtModuleSwitchType by wangyahui
-- V4.27 2007-04-25 add subidentifier 706 under hh3cevtModuleSwitchType by zhangzongyi
--                  add subidentifier 379 to 380 under hh3cevtModuleSwitchType by zhaiyingying
--                  add subidentifier 246 to 250 under hh3cevtModuleRouterType by liutinghai
--                  add subidentifier 42 under hh3cevtPortRouterType by liutinghai
-- V4.28 2007-05-28 add subidentifier 707 under hh3cevtModuleSwitchType by ligaoxu
--                  add subidentifier 381 to 392 under hh3cevtModuleSwitchType by shuxiongtao
--                  modify name of subidentifier 371 and 374 under hh3cevtModuleSwitchType by shuxiongtao
--                  add subidentifier 251 to 253 under hh3cevtModuleRouterType by qikai
--                  add subidentifier 254 to 255 under hh3cevtModuleRouterType by liutinghai
--                  add subidentifier 186 under hh3cevtPortSwitchType by jinzhaoqiong
-- V4.29 2007-07-09 add subidentifier 543 to 551 under hh3cevtModuleSwitchType by zhangjianfeng
--                  add subidentifier 552 to 554 under hh3cevtModuleSwitchType by wangyahui
-- V4.30 2007-07-26 add subidentifier 400 under hh3cevtModuleRouterType by xuejiayong
--                  add subidentifier 708 under hh3cevtModuleSwitchType by xiuyihong
--                  add subidentifier 256 to 258 under hh3cevtModuleRouterType by qikai
--                  add subidentifier 259 to 263 under hh3cevtModuleRouterType by liutinghai
--                  add subidentifier 3 to 5 under hh3cevtOther by gaolong
-- V4.31 2007-08-27 add subidentifier 187 to 188 under hh3cevtPortSwitchType by ruanhan
--                  add subidentifier 802 to 804 under hh3cevtModuleSwitchType by luoguixing
--                  add subidentifier 393 to 397 under hh3cevtModuleSwitchType by shuxiongtao
-- V4.32 2007-09-25 add subidentifier 555 to 559 under hh3cevtModuleSwitchType by wangyahui
--                  add subidentifier 805 under hh3cevtModuleSwitchType by luoguixing
--                  add subidentifier 401 to 403 under hh3cevtModuleRouterType by tanwen
--                  add subidentifier 43 under hh3cevtPortRouterType by qikai
--                  add subidentifier 266 to 267 under hh3cevtModuleRouterType by qikai
--                  add subidentifier 398 to 399 under hh3cevtModuleSwitchType by hexuefei
-- V4.33 2007-10-22 add subidentifier 189 under hh3cevtPortSwitchType by liaoxin
--                  add subidentifier 268 under hh3cevtModuleRouterType by liutinghai
-- V4.34 2007-11-26 add subidentifier 269 to 273 under hh3cevtModuleRouterType by liutinghai
--                  add subidentifier 274 to 276 under hh3cevtModuleRouterType by qikai
--                  add subidentifier 404 to 406 under hh3cevtModuleRouterType by chaiyaqin
--                  add subidentifier 400 to 407 under hh3cevtModuleSwitchType by shuxiongtao
-- V4.35 2007-12-27 add subidentifier 277 to 278 under hh3cevtModuleRouterType by liutinghai
--                  add subidentifier 560 to 568 under hh3cevtModuleSwitchType by wangyahui
-- V4.36 2008-01-30 add subidentifier 408 under hh3cevtModuleSwitchType by hexuefei
--                  add subidentifier 569 to 572 under hh3cevtModuleSwitchType by wangyahui
--                  add subidentifier 279 to 280 under hh3cevtModuleRouterType by qikai
--                  add subidentifier 190 under hh3cevtPortSwitchType by liujingya
-- V4.37 2008-02-20 add subidentifier 720 to 724 under hh3cevtModuleSwitchType by chaiyaqin
--                  add subidentifier 573 to 574 under hh3cevtModuleSwitchType by zhangjianfeng
--                  modify name of subidentifier 546 and 550 under hh3cevtModuleSwitchType by zhangjianfeng
--                  add subidentifier 575 to 576 under hh3cevtModuleSwitchType by wangyahui
--                  add subidentifier 281 under hh3cevtModuleRouterType by liutinghai
-- V4.38 2008-03-31 add subidentifier 806 to 808 under hh3cevtModuleSwitchType by luoguixing
--                  add subidentifier 709 to 715 under hh3cevtModuleSwitchType by wangcong
--                  add subidentifier 191 to 196 under hh3cevtPortSwitchType by wangcong
--                  add subidentifier 44 under hh3cevtPortRouterType by liutinghai
--                  add subidentifier 409 to 431 under hh3cevtModuleSwitchType by zhaiyingying
--                  add subidentifier 432 under hh3cevtModuleSwitchType by shuxiongtao
-- V4.39 2008-04-29 add subidentifier 577 to 589 under hh3cevtModuleSwitchType by wangyahui
--                  add subidentifier 407 to 409 under hh3cevtModuleRouterType by tanwen
-- V4.40 2008-05-31 add subidentifier 410 to 413 under hh3cevtModuleRouterType by tanwen
--                  add subidentifier 282 to 284 under hh3cevtModuleRouterType by qikai
--                  add subidentifier 285 to 286 under hh3cevtModuleRouterType by liutinghai
-- V4.41 2008-07-28 add subidentifier 590 to 592 under hh3cevtModuleSwitchType by wangyahui
--                  add subidentifier 287 to 289 under hh3cevtModuleRouterType by qikai
--                  add subidentifier 290 to 291 under hh3cevtModuleRouterType by liutinghai
--                  add subidentifier 45 to 46 under hh3cevtPortRouterType by liutinghai
--                  add subidentifier 809 to 810 under hh3cevtModuleSwitchType by luoguixing
-- V4.42 2008-08-26 modify name of 379 and 399 under hh3cevtModuleSwitchType by wangwei
--                  modify description of 408 under hh3cevtModuleSwitchType by wangwei
--                  modify name and description of 804 under hh3cevtModuleSwitchType by wangwei
--                  add subidentifier 433 to 434 under hh3cevtModuleSwitchType by wangwei
--                  add subidentifier 593 to 595 under hh3cevtModuleSwitchType by wangyahui
--                  modify name and description of 256 and 288 under hh3cevtPortRouterType by qikai
--                  add subidentifier 292 to 293 under hh3cevtPortRouterType by qikai
-- V4.43 2008-10-13 add subidentifier 725 under hh3cevtModuleSwitchType by ruanhan
--                  add subidentifier 197 under hh3cevtPortSwitchType by ruanhan
--                  add subidentifier 811 under hh3cevtModuleSwitchType by luoguixing
--                  add subidentifier 596 to 601 under hh3cevtModuleSwitchType by wangyahui
-- V4.44 2008-11-04 add subidentifier 294 under hh3cevtPortRouterType by qikai
--                  add subidentifier 414 under hh3cevtModuleRouterType by tanwen
-- V4.45 2008-12-01 add subidentifier 602 to 619 under hh3cevtModuleSwitchType by wangyahui
--                  add subidentifier 435 to 442 under hh3cevtModuleSwitchType by zhaiyingying
--                  modify name of 546 under hh3cevtModuleSwitchType by zhangjianfeng
--                  add subidentifier 295 under hh3cevtPortRouterType by qikai
--                  add subidentifier 443 under hh3cevtModuleSwitchType by shuxiongtao
-- V4.46 2008-12-25 add subidentifier 620 to 622 under hh3cevtModuleSwitchType by wangyahui
--                  add subidentifier 716 to 718 under hh3cevtModuleSwitchType by zhangshilin
--                  add subidentifier 444 to 445 under hh3cevtModuleSwitchType by wangchang
-- V4.47 2009-03-02 add subidentifier 446 to 452 under hh3cevtModuleSwitchType by wangchang
--                  add subidentifier 719 under hh3cevtModuleSwitchType by zhangshilin
--                  add subidentifier 623 to 633 under hh3cevtModuleSwitchType by wangyahui
-- V4.48 2009-03-31 add subidentifier 415 under hh3cevtModuleRouterType by tanwen
--                  add subidentifier 296 under hh3cevtPortRouterType by qikai
--                  add subidentifier 297 to 298 under hh3cevtPortRouterType by qianjialin
--                  add subidentifier 453 to 464 under hh3cevtModuleSwitchType by huyinxing
-- V4.49 2009-07-02 add subidentifier 299 to 302 under hh3cevtModuleRouterType by qikai
--                  add subidentifier 303 under hh3cevtModuleRouterType by chenfeihu
--                  add subidentifier 304 to 307 under hh3cevtModuleRouterType by qianjialin
--                  add subidentifier 634 to 637 under hh3cevtModuleSwitchType by wangyahui
--                  add subidentifier 604 to 606 under hh3cevtModuleRouterType by chenjianhui
--                  add subidentifier 465 to 468 under hh3cevtModuleSwitchType by zhaiyingying
--                  add subidentifier 469 to 472 under hh3cevtModuleSwitchType by huyinxing
--                  add subidentifier 198 under hh3cevtPortSwitchType by huyinxing
--                  add subidentifier 199 under hh3cevtPortSwitchType by zhangjianfeng
-- V4.50 2009-08-28 add subidentifier 638 to 640 under hh3cevtModuleSwitchType by wangyahui
--                  add subidentifier 308 to 310 under hh3cevtModuleRouterType by qianjialin
-- V4.51 2009-11-09 add subidentifier 726 under hh3cevtModuleSwitchType by ruanhan
--                  add subidentifier 641 under hh3cevtModuleSwitchType by wangyahui
--                  add subidentifier 473 to 477 under hh3cevtModuleSwitchType by yudongyang
--                  add subidentifier 478 to 485 under hh3cevtModuleSwitchType by heweibin
-- V4.52 2009-12-31 add subidentifier 200 to 201 under hh3cevtPortSwitchType by zhanghaiyang
--                  add subidentifier 642 to 651 under hh3cevtModuleSwitchType by wangyahui
--                  add subidentifier 416 under hh3cevtModuleRouterType by lixiaomin
--                  add subidentifier 486 under hh3cevtModuleSwitchType by yudongyang
--                  add subidentifier 727 to 728 under hh3cevtModuleSwitchType by xiaobing
--                  add subidentifier 652 to 659 under hh3cevtModuleSwitchType by wangyahui
--                  add subidentifier 487 to 488 under hh3cevtModuleSwitchType by huyinxing
--                  add subidentifier 660 to 662 under hh3cevtModuleSwitchType by wangyahui
--                  add subidentifier 202 to 203 under hh3cevtPortSwitchType by yangdonghong
-- V4.53 2010-03-03 add subidentifier 812 under hh3cevtModuleSwitchType by mashuhang
--                  add subidentifier 489 to 497 under hh3cevtModuleSwitchType by liubuxiang
--                  add subidentifier 498 to 499 under hh3cevtModuleSwitchType by shikejun
--                  add subidentifier 900 under hh3cevtModuleSwitchType by yangqiulin
--                  add subidentifier 901 to 902 under hh3cevtModuleSwitchType by huyinxing
-- V4.54 2010-04-21 add subidentifier 903 to 904 under hh3cevtModuleSwitchType by huyinxing
--                  add subidentifier 905 to 907 under hh3cevtModuleSwitchType by shikejun
--                  add subidentifier 663 to 685 under hh3cevtModuleSwitchType by wangyahui
--                  add subidentifier 813 under hh3cevtModuleSwitchType by mashuhang
--                  add subidentifier 729 under hh3cevtModuleSwitchType by zhangshilin
--                  add subidentifier 908 to 913 under hh3cevtModuleSwitchType by yangbin
--                  add subidentifier 914 to 918 under hh3cevtModuleSwitchType by huyinxing
--                  add subidentifier 5000 to 5011 under hh3cevtModuleRouterType by qianjialin
--                  add subidentifier 919 to 927 under hh3cevtModuleSwitchType by langgaoyi
-- V4.55 2011-01-31 add subidentifier 417 under hh3cevtModuleRouterType by tanwen
--                  add subidentifier 311 to 314 under hh3cevtModuleRouterType by qianjialin
--                  add subidentifier 686 to 691 under hh3cevtModuleSwitchType by wangyahui
--                  add subidentifier 928 to 929 under hh3cevtModuleSwitchType by langgaoyi
-- V4.56 2011-04-22 add subidentifier 930 under hh3cevtModuleSwitchType by liuhui
--                  add subidentifier 814 to 815 under hh3cevtModuleSwitchType by mashuhang
--                  add subidentifier 692 to 694 under hh3cevtModuleSwitchType by wangyahui
--                  add subidentifier 204 under hh3cevtPortSwitchType by yangliming
-- V4.57 2011-06-30 add subidentifier 695, 1201 to 1211 under hh3cevtModuleSwitchType by wangyahui
--                  add subidentifier 205 to 207 under hh3cevtPortSwitchType by gaoruichang
-- V4.58 2011-08-31 add subidentifier 696 to 697 under hh3cevtModuleSwitchType by langgaoyi
--                  add subidentifier 208 under hh3cevtPortSwitchType by wangshunli
--                  add subidentifier 931 to 933 under hh3cevtModuleSwitchType by langgaoyi
--                  add subidentifier 934 under hh3cevtModuleSwitchType by zhaohonghai
-- V4.59 2012-04-20 add subidentifier 935 to 938, 942 under hh3cevtModuleSwitchType by wangjiangnan
--                  add subidentifier 1212 to 1218 under hh3cevtModuleSwitchType by wangyahui
--                  add subidentifier 939 to 941 under hh3cevtModuleSwitchType by herui
--                  modify name of 205 to 207 under hh3cevtPortSwitchType by xvman
--                  add subidentifier 350 to 360 under hh3cevtModuleRouterType by chenfeihu
--                  add subidentifier 943 to 945 under hh3cevtModuleSwitchType by langgaoyi
--                  add subidentifier 209, 211 under hh3cevtPortSwitchType by wangyahui
--                  add subidentifier 730 to 731 under hh3cevtModuleSwitchType by panxiyuan
--                  add subidentifier 210 under hh3cevtPortSwitchType by panxiyuan
--                  add subidentifier 315 to 349 under hh3cevtModuleRouterType by qianjialin
--                  add subidentifier 946 to 948 under hh3cevtModuleSwitchType by zhangheng
--                  add subidentifier 949 to 956 under hh3cevtModuleSwitchType by zhengjiang
--                  add subidentifier 957 under hh3cevtModuleSwitchType by zhaohonghai
--                  add subidentifier 361 to 372 under hh3cevtModuleRouterType by qianjialin
--                  add subidentifier 212 under hh3cevtPortSwitchType by wangyahui
--                  add subidentifier 732 under hh3cevtModuleSwitchType by houchengshuai
--                  add subidentifier 1219 to 1230 under hh3cevtModuleSwitchType by wangyahui
-- V4.60 2013-01-07 add subidentifier 733 under hh3cevtModuleSwitchType by shixuemei
--                  add subidentifier 958 to 959 under hhh3cevtModuleSwitchType by zhaohonghai
--                  add subidentifier 960 to 965, 996 under hh3cevtModuleSwitchType by zhangheng
--                  add subidentifier 966 to 988 under hh3cevtModuleSwitchType by yebiaoxiang
--                  add subidentifier 989 to 995 under hh3cevtModuleSwitchType by zhaohonghai
--                  add subidentifier 1231 to 1255 under hh3cevtModuleSwitchType by wangyahui
--                  add subidentifier 373 to 388 under hh3cevtModuleRouterType by qianjialin
--                  add subidentifier 1400 to 1410 under hh3cevtModuleSwitchType by qizhenglin
--                  add subidentifier 213 to 219 under hh3cevtPortSwitchType by yebiaoxiang
--                  add subidentifier 47 under hh3cevtPortRouterType by qianjialin
--                  add subidentifier 418 under hh3cevtModuleRouterType by tanwen
--                  modify name of 673, 1214, 1215 under hh3cevtModuleSwitchType by wangyahui
-- V4.61 2013-04-26 add subidentifier 1256 to 1269 under hh3cevtModuleSwitchType by wangyahui
--                  add subidentifier 607 to 610 under hh3cevtModuleRouterType by jiangwendong
--                  add subidentifier 220 to 222 under hh3cevtPortSwitchType by jiangyongjiang
--                  add subidentifier 389 to 392 under hh3cevtModuleRouterType by chenfeihu
--                  add subidentifier 393 to 398 under hh3cevtModuleRouterType by qianjialin
--                  modify name of 975 to 982 under hh3cevtModuleSwitchType by lihaijun
--                  add subidentifier 997 to 1015 under hh3cevtModuleSwitchType by chenke
--                  add subidentifier 1016 to 1018 under hh3cevtModuleSwitchType by jiangyongjiang
--                  add subidentifier 1270 to 1273 under hh3cevtModuleSwitchType by sunzhenxing
--                  add subidentifier 1 to 8 under hh3cevtModuleCommonCards by zhouxiaodong
-- V4.62 2013-10-10 add subidentifier 419 to 431 under hh3cevtModuleRouterType by tanwen
--                  add subidentifier 611 under hh3cevtModuleRouterType by jiangwendong
--                  add subidentifier 399, 800 to 804, 807 under hh3cevtModuleRouterType by qianjialin
--                  add subidentifier 805 to 806 under hh3cevtModuleRouterType by chenfeihu
--                  add subidentifier 1274 to 1279, 1293 to 1296 under hh3cevtModuleSwitchType by lihaijun
--                  add subidentifier 1019 to 1024 under hh3cevtModuleSwitchType by zhaohonghai
--                  add subidentifier 1280 to 1287, 1298 to 1306 under hh3cevtModuleSwitchType by sunzhenxing
--                  add subidentifier 1025, 1028, 1029, 1050 under hh3cevtModuleSwitchType by jiangyongjiang
--                  add subidentifier 1026 to 1027, 1030 to 1049 under hh3cevtModuleSwitchType by chenke
--                  add subidentifier 816 under hh3cevtModuleSwitchType by luoguixing
--                  add subidentifier 1288 to 1292, 1297 under hh3cevtModuleSwitchType by wujili
--                  modify name of 1234 to 1236 under hh3cevtModuleSwitchType by lihaijun
--                  add subidentifier 48 to 49 under hh3cevtPortRouterType by jiangwendong
--                  add subidentifier 223 to 224 under hh3cevtPortSwitchType by jiangyongjiang
-- V4.63 2014-01-26 add subidentifier 432 under hh3cevtModuleRouterType by zhaowenbin
--                  add subidentifier 808 to 809, 814 under hh3cevtModuleRouterType by qianjialin
--                  add subidentifier 810 to 813, 815 to 817 under hh3cevtModuleRouterType by chenfeihu
--                  add subidentifier 734 to 739 under hh3cevtModuleSwitchType by panxiyuan
--                  modify name of 1032 to 1041 under hh3cevtModuleSwitchType by chenke
--                  add subidentifier 1051 to 1055 under hh3cevtModuleSwitchType by zhaohonghai
--                  add subidentifier 1056 to 1058 under hh3cevtModuleSwitchType by chenke
--                  add subidentifier 1307 to 1313 under hh3cevtModuleSwitchType by wujili
--                  add subidentifier 1314 to 1316 under hh3cevtModuleSwitchType by lihaijun
--                  add subidentifier 1317 to 1319 under hh3cevtModuleSwitchType by sunzhenxing
--                  add subidentifier 1320 to 1326 under hh3cevtModuleSwitchType by jiangyongjiang
-- V4.64 2014-04-25 add subidentifier 1059 to 1069 under hh3cevtPortSwitchType by youhua
--                  add subidentifier 1070 to 1102 under hh3cevtModuleSwitchType by chenke
--                  add subidentifier 1103 to 1107 under hh3cevtModuleSwitchType by lihaijun
--                  add subidentifier 1108 under hh3cevtModuleSwitchType by zhaohonghai
--                  add subidentifier 1327 to 1328 under hh3cevtModuleSwitchType by sunzhenxing
--                  add subidentifier 1329 to 1331 under hh3cevtModuleSwitchType by lihaijun
--                  add subidentifier 1332 to 1371 under hh3cevtModuleSwitchType by jiangyongjiang
--                  add subidentifier 1372 to 1373 under hh3cevtModuleSwitchType by sunzhenxing
--                  modify name of 733 under hh3cevtModuleSwitchType by maoyun
--                  add subidentifier 740 to 743 hh3cevtModuleSwitchType by tanxiaopeng
--                  add subidentifier 433 under hh3cevtModuleRouterType by zhaowenbin
--                  add subidentifier 818 to 822, 824 to 825 under hh3cevtModuleRouterType by chenfeihu
--                  add subidentifier 823 under hh3cevtModuleRouterType by qianjialin
--                  add subidentifier 50 to 51 under hh3cevtPortRouterType by chenfeihu
--                  add subidentifier 225 to 232 under hh3cevtPortSwitchType by pantao
--                  modify name of 1400, remove 1401 to 1410 under hh3cevtModuleSwitchType by qizhenglin
-- V4.65 2014-09-18 add subidentifier 434 under hh3cevtModuleRouterType by zhaowenbin
--                  add subidentifier 612 to 615 under hh3cevtModuleRouterType by jiangwendong
--                  add subidentifier 826 to 833, 840 under hh3cevtModuleRouterType by qianjialin
--                  add subidentifier 834 to 839 under hh3cevtModuleRouterType by chenfeihu
--                  add subidentifier 52 under hh3cevtPortRouterType by jiangwendong
--                  add subidentifier 744 hh3cevtModuleSwitchType by tanxiaopeng
--                  add subidentifier 1109 to 1117 under hh3cevtModuleSwitchType by chenke
--                  add subidentifier 1118 to 1119, 1375 to 1376 under hh3cevtModuleSwitchType by lihaijun
--                  add subidentifier 1374, 1382 to 1385 under hh3cevtModuleSwitchType by jiangyongjiang
--                  add subidentifier 1377 to 1381, 1386 to 1389 under hh3cevtModuleSwitchType by sunzhenxing
--                  modify description of 1010 under hh3cevtModuleSwitchType by chenke
--                  modify name of 1320 to 1325, 1332 to 1371 under hh3cevtModuleSwitchType by jiangyongjiang
--                  add subidentifier 8 to 35 under hh3cevtPowerSupply, 3 to 23 under hh3cevtFan by jiangyongjiang
-- V4.66 2015-04-18 add subidentifier 435 under hh3cevtModuleRouterType by zhaowenbin
--                  add subidentifier 841 to 854 under hh3cevtModuleRouterType by qianjialin
--                  add subidentifier 855 to 858 under hh3cevtModuleRouterType by zhaohonghai
--                  add subidentifier 745 to 747 hh3cevtModuleSwitchType by tanxiaopeng
--                  add subidentifier 748 hh3cevtModuleSwitchType by wangshunli
--                  add subidentifier 1120 to 1125, 1127 to 1128, 1390 to 1397,
--                                    1647 to 1649, 1667 to 1673 under hh3cevtModuleSwitchType by lihaijun
--                  add subidentifier 1126 under hh3cevtModuleSwitchType by chenke
--                  add subidentifier 1129 to 1144 under hh3cevtPortSwitchType by youhua
--                  add subidentifier 1398, 1399, 1600 to 1605, 1623 to 1646,
--                                    1650 to 1652, 1660 to 1666, 1674 to 1685
--                                    under hh3cevtModuleSwitchType by jiangyongjiang
--                  add subidentifier 1606 to 1622 under hh3cevtModuleSwitchType by sunzhenxing
--                  add subidentifier 1653 to 1659 under hh3cevtModuleSwitchType by zhaiwanqing
--                  add subidentifier 233 to 237, 239 to 253 under hh3cevtPortSwitchType by pantao
--                  add subidentifier 238 under hh3cevtPortSwitchType by chenke
--                  modify name of 1315 and 1316 under hh3cevtModuleSwitchType by lihaijun
-- V4.67 2016-04-02 add subidentifier 436 to 437, 448 to 449 under hh3cevtModuleRouterType by zhaowenbin
--                  add subidentifier 438 to 439 and 616 to 618 under hh3cevtModuleRouterType by sunqingyan
--                  add subidentifier 440 under hh3cevtModuleRouterType by chengaishuang
--                  add subidentifier 441 to 446 under hh3cevtModuleRouterType by yaoshuo
--                  add subidentifier 447 under hh3cevtModuleRouterType by dongchanghai
--                  modify name of 856 to 858 under hh3cevtModuleSwitchType by zhaohonghai
--                  add subidentifier 859 to 862 under hh3cevtModuleRouterType by zhaohonghai
--                  add subidentifier 863 under hh3cevtModuleRouterType by qianjialin
--                  add subidentifier 864 to 878 under hh3cevtModuleRouterType by chenfeihu
--                  add subidentifier 879 to 884 under hh3cevtModuleRouterType by fujuan
--                  add subidentifier 749 under hh3cevtModuleSwitchType by wangshunli
--                  add subidentifier 750 under hh3cevtModuleSwitchType by yangjianlin
--                  add subidentifier 751 to 752 hh3cevtModuleSwitchType by mengfanhua
--                  add subidentifier 753 to 756 under hh3cevtModuleSwitchType by songkeke
--                  add subidentifier 1145, 1149 under hh3cevtPortSwitchType by youhua
--                  add subidentifier 1146 to 1148, 1150 to 1154 under hh3cevtPortSwitchType by chenke
--                  add subidentifier 1686 to 1694, 1710 to 1722, 1742 to 1760, 1767 to 1784, 1789 to 1793
--                                    under hh3cevtModuleSwitchType by jiangyongjiang
--                  add subidentifier 1695 to 1696 under hh3cevtModuleSwitchType by zhaiwanqing
--                  add subidentifier 1697 to 1709, 1723 to 1741, 1761 to 1766, 1785 to 1788, 1794 to 1805
--                                    under hh3cevtModuleSwitchType by lihaijun
--                  add subidentifier 53 to 54 under hh3cevtPortRouterType by chenfeihu
--                  add subidentifier 55 under hh3cevtPortRouterType by fujuan
--                  add subidentifier 56 under hh3cevtPortRouterType by qianjialin
--                  modify name of 1128 under hh3cevtModuleSwitchType by lihaijun
--                  modify description of 1673 under hh3cevtModuleSwitchType by lihaijun
--                  add subidentifier 254 to 262, 264 to 265 under hh3cevtPortSwitchType by guolei
--                  add subidentifier 263 under hh3cevtPortSwitchType by zhanghuimin
-- V4.68 2018-04-13 add subidentifier 1806 to 1829 under hh3cevtModuleSwitchType by jiangyongjiang
--                  add subidentifier 266 under hh3cevtPortSwitchType by guolei
--                  add subidentifier 1830 to 1841 under hh3cevtModuleSwitchType by lihaijun
--                  add subidentifier 757 to 758 under hh3cevtModuleSwitchType by wangshunli
--                  add subidentifier 1842 under hh3cevtModuleSwitchType by zhaoshihong
--                  add subidentifier 1843 to 1846 under hh3cevtModuleSwitchType by jiangyongjiang
--                  add subidentifier 759 under hh3cevtModuleSwitchType by mengfanhua
--                  add subidentifier 1847 under hh3cevtModuleSwitchType by jiangyongjiang
--                  add subidentifier 619 to 620 under hh3cevtModuleRouterType by songyanqing
--                  add subidentifier 1848 to 1849 under hh3cevtModuleSwitchType by lihaijun
--                  add subidentifier 885 to 886 under hh3cevtModuleRouterType by zhaohonghai
--                  add subidentifier 1850 to 1852 under hh3cevtModuleSwitchType by jiangyongjiang
--                  add subidentifier 1853 to 1857 under hh3cevtModuleSwitchType by lihaijun
--                  add subidentifier 1858 to 1862 under hh3cevtModuleSwitchType by lihaijun
--                  add subidentifier 1863 to 1893 under hh3cevtModuleSwitchType by jiangyongjiang
--                  add subidentifier 1155 to 1170 under hh3cevtModuleSwitchType by chenke
--                  add subidentifier 1894 to 1895 under hh3cevtModuleSwitchType by lihaijun
--                  add subidentifier 1896 under hh3cevtModuleSwitchType by jiangyongjiang
--                  add subidentifier 267 under hh3cevtPortSwitchType by guolei
--                  add subidentifier 887 to 889 under hh3cevtModuleRouterType by mazheng
--                  add subidentifier 1171 to 1176 under hh3cevtModuleSwitchType by chenke
--                  add subidentifier 1897 to 1904 under hh3cevtModuleSwitchType by jiangyongjiang
--                  add subidentifier 1905 hh3cevtModuleSwitchType by liuyanpeng
--                  add subidentifier 450 to 454 hh3cevtModuleRouterType by dongchanghai
--                  add subidentifier 1906 to 1907 hh3cevtModuleSwitchType by jiangyongjiang
--                  add subidentifier 1908 hh3cevtModuleSwitchType by liuyanpeng
--                  add subidentifier 1177 to 1181 under hh3cevtModuleSwitchType by chenke
--                  add subidentifier 760 to 762 hh3cevtModuleSwitchType by mengfanhua
--                  add subidentifier 890 to 894 under hh3cevtModuleRouterType by fujuan
--                  modify name of subidentifier 872 and 873 under hh3cevtModuleRouterType by fujuan
--                  add subidentifier 1909 to 1910 under hh3cevtModuleSwitchType by lihaijun
--                  add subidentifier 455 to 456 hh3cevtModuleRouterType by yaoshuo
--                  add subidentifier 1911 to 1935 under hh3cevtModuleSwitchType by jiangyongjiang
--                  add subidentifier 457 under hh3cevtModuleRouterType by lizhifeng
--                  add subidentifier 895 to 899 under hh3cevtModuleRouterType by zhaohonghai
--                  add subidentifier 1936 to 1938 under hh3cevtModuleSwitchType by zhangkun
--                  add subidentifier 1939 to 1941 under hh3cevtModuleSwitchType by jiangyongjiang
--                  add subidentifier 6 to 8 under hh3cevtOther by chenke
--                  add subidentifier 458 to 462 under hh3cevtModuleRouterType by wangchunlei
--                  add subidentifier 900 to 906 under hh3cevtModuleRouterType by fujuan
--                  add subidentifier 1182 under hh3cevtModuleSwitchType by youhua
--                  add subidentifier 1942 under hh3cevtModuleSwitchType by lihaijun
--                  add subidentifier 1943 to 1953 under hh3cevtModuleSwitchType by jiangyongjiang
--                  add subidentifier 463 to 468 under hh3cevtModuleRouterType by dongchanghai
--                  add subidentifier 1183 to 1196 under hh3cevtModuleSwitchType by chenke
--                  add subidentifier 907 to 921 under hh3cevtModuleRouterType by zhongchao
--                  add subidentifier 763 to 764 under hh3cevtModuleSwitchType by sunfang
--                  add subidentifier 1954 to 1957 under hh3cevtModuleSwitchType by lihaijun
--                  add subidentifier 1958 to 1972 under hh3cevtModuleSwitchType by jiangyongjiang
--                  add subidentifier 1973 to 1979 hh3cevtModuleSwitchType by lihaijun
--                  add subidentifier 1980 to 1981 hh3cevtModuleSwitchType by jiangyongjiang
--                  add subidentifier 274 to 279 under hh3cevtModuleSwitchType by guolei
--                  add subidentifier 469 under hh3cevtModuleRouterType by maxiaojie
--                  add subidentifier 470 to 473 under hh3cevtModuleSwitchType by fuzhanfeng
--                  add subidentifier 765 under hh3cevtModuleSwitchType by mengfanhua
--                  add subidentifier 1982 to 1985 hh3cevtModuleSwitchType by  lihaijun
--                  add subidentifier 1986 to 2003 hh3cevtModuleSwitchType by  jiangyongjiang
--                  add subidentifier 922 under hh3cevtModuleRouterType by mazheng
--                  add subidentifier 58 under hh3cevtPortRouterType by liuhua
--                  add subidentifier 474 to 477 under hh3cevtModuleSwitchType by tanyan
--                  add subidentifier 2004 to 2005 hh3cevtModuleSwitchType by  lihaijun
--                  add subidentifier 2006 to 2008 hh3cevtModuleSwitchType by  jiangyongjiang
--                  add subidentifier 2009 to 2015 hh3cevtModuleSwitchType by  lihaijun
--                  add subidentifier 1401 to 1450 under hh3cevtModuleSwitchType by chenke
--                  add subidentifier 923 under hh3cevtModuleRouterType by zhongchao
--                  add subidentifier 924 to 933 under hh3cevtModuleRouterType by fujuan
--                  add subidentifier 766 to 768 under hh3cevtModuleSwitchType by wangshunli
--                  add subidentifier 482 to 483 under hh3cevtModuleSwitchType by cuipeilei
--                  add subidentifier 35 to 37 under hh3cevtPowerSupply by wangchunlei
--                  add subidentifier 24 to 25 under  hh3cevtFan by wangchunlei
--                  add subidentifier 484 to 489 under hh3cevtModuleSwitchType by wangchunlei
--                  add subidentifier 938 under hh3cevtModuleRouterType by fujuan
--                  add subidentifier 491 to 492 under hh3cevtModuleSwitchType by fuzhanfeng
--                  add subidentifier 939 under hh3cevtModuleRouterType by zhongchao
--                  add subidentifier 769 under hh3cevtModuleSwitchType by yangjianlin
--                  add subidentifier 940 to 945 under hh3cevtModuleRouterType by fujuan
--                  add subidentifier 946 to 953 under hh3cevtModuleRouterType by zhaochao
--                  add subidentifier 493 under hh3cevtModuleSwitchType by liyujun
--                  add subidentifier 2016 to 2017 hh3cevtModuleSwitchType by  jiangyongjiang
--                  add subidentifier 769 to 770 under hh3cevtModuleSwitchType by yangjianlin
--                  add subidentifier 494 to 497 under hh3cevtModuleSwitchType by yangyuan
--                  add subidentifier 2018 to 2021 hh3cevtModuleSwitchType by  lihaijun
--                  add subidentifier 280 under hh3cevtPortSwitchType by yuanzhi
--                  add subidentifier 2022 to 2047 hh3cevtModuleSwitchType by  jiangyongjiang
--                  add subidentifier 281 to 283 under hh3cevtPortSw by wangshunli
--                  add subidentifier 954 to 958 under hh3cevtModuleRouterType by fujuan
--                  add subidentifier 959 to 960 under hh3cevtModuleRouterType by zhongchao
--                  add subidentifier 284 to 285 under hh3cevtPortSwitchType by guolei
--                  add subidentifier 771 to 775 under hh3cevtModuleSwitchType by wangshunli
--                  add subidentifier 961 to 962 under hh3cevtModuleRouterType by fujuan
--                  add subidentifier 963 to 968 under hh3cevtModuleRouterType by zhongchao
--                  modify name of 1822 and 1825 under hh3cevtModuleSwitchType by jiangyongjiang
--                  add subidentifier 499 to 508 under hh3cevtModuleSwitchType by tanyan
--                  add subidentifier 969 under hh3cevtModuleRouterType by fujuan
--                  add subidentifier 970 to 973 under hh3cevtModuleRouterType by zhongchao
--                  add subidentifier 2048 to 2049 hh3cevtModuleSwitchType by  lihaijun
--                  add subidentifier 2050 to 2055 hh3cevtModuleSwitchType by  jiangyongjiang
--                  add subidentifier 974 to 980 under hh3cevtModuleRouterType by zhaomeng
--                  add subidentifier 286 under hh3cevtPortSwitchType by zhaomeng
--                  add subidentifier 502 to 517 under hh3cevtModuleSwitchType by fuzhanfeng
--                  add subidentifier 287 under hh3cevtPortSwitchType by guolei
-- V4.69 2019-01-15 add subidentifier 518 to 519 under hh3cevtModuleSwitchType by tanyan
--                  add subidentifier 520 under hh3cevtModuleSwitchType by fuzhanfeng
--                  add subidentifier 287 under hh3cevtPortSwitchType by qinjuan
--                  add subidentifier 1451 to 1456 under hh3cevtModuleSwitchType by chenke
--                  add subidentifier 2056 to 2060 hh3cevtModuleSwitchType by  jiangyongjiang
-- V4.70 2019-01-21 add subidentifier 2061 to 2063 under hh3cevtModuleSwitchType by jiangyongjiang
--                  add subidentifier 1457 to 1459 under hh3cevtModuleSwitchType by  zhanglili
--       2019-02-12 add subidentifier 2064 to 2072 under hh3cevtModuleSwitchType by lihaijun
--                  add subidentifier 521 to 530 under hh3cevtModuleSwitchType by fuzhanfeng
--                  add subidentifier 621 to 625 under hh3cevtModuleRouterType by wangxinmeng
--                  add subidentifier 776 to 777 under hh3cevtModuleSwitchType by wangshunli
--                  modify name of 966 to 968, 970 to 971,980 under hh3cevtModuleSwitchType by zhaomeng
--                  add subidentifier 289 to 290 under hh3cevtModuleSwitchType by wangzilong
--                  add subidentifier 981 to 984 under hh3cevtModuleRouterType  by fujuan
--                  add subidentifier 985 to 986 under hh3cevtModuleRouterType wangxinmeng
--                  add subidentifier 987 to 989 under hh3cevtModuleRouterType  by fuzhanfeng
--                  add subidentifier 990  under hh3cevtModuleRouterType wangxinmeng
--                  add subidentifier 991 to 1004 under hh3cevtModuleRouterType  by fuzhanfeng
--                  add subidentifier 1005 under hh3cevtModuleRouterType  by zhaomeng
--                  add subidentifier 2076 under hh3cevtModuleSwitchType by maoyun
--                  add subidentifier 2077 under hh3cevtModuleSwitchType by jiangyongjiang
--                  add subidentifier 2078 to 2081 under hh3cevtModuleSwitchType by chenke
--                  add subidentifier 2082 to 2108 under hh3cevtModuleSwitchType by jiangyongjiang
--                  add subidentifier 2109 to 2111 under hh3cevtModuleSwitchType by maoyun
--                  add subidentifier 2112 under hh3cevtModuleSwitchType by chenke
--                  add subidentifier 291 to 292  under hh3cevtPortSwitchType wangzilong
--                  add subidentifier 2113 to 2116 under hh3cevtModuleSwitchType by lihaijun
--                  add subidentifier 2117 to 2118 under hh3cevtModuleSwitchType by chenke
--                  add subidentifier 2119 to 2129 under hh3cevtModuleSwitchType by jiangyongjian
--                  add subidentifier 2130 under hh3cevtModuleSwitchType by maoyun
--                  add subidentifier 1006 under hh3cevtModuleRouterType by fuzhanfeng
--                  add subidentifier 2131 to 2141 under hh3cevtModuleSwitchType by chenke
--                  add subidentifier 2142 to 2146 under hh3cevtModuleSwitchType by jiangyongjiang
--                  add subidentifier 2147 to 2148 under hh3cevtModuleSwitchType by maoyun
--                  add subidentifier 1007 to 1009 under hh3cevtModuleRouterType by zhaomeng
--                  add subidentifier 59 under hh3cevtPortRouterType  by fujuan
--                  add subidentifier 2149 to 2155 under hh3cevtModuleSwitchType by chenke
--                  add subidentifier 2156 to 2169 under hh3cevtModuleSwitchType by lihaijun
--                  add subidentifier 2170 to 2173 under hh3cevtModuleSwitchType by jiangyongjiang
--                  add subidentifier 2174 to 2175 under hh3cevtModuleSwitchType by lihaijun
-- V4.71 2019-08-21 add subidentifier 2176 to 2184 under hh3cevtModuleSwitchType by jiangyongjiang
--                  add subidentifier 1010 under hh3cevtModuleRouterType by zhaomeng
--                  add subidentifier 1011 to 1012 under hh3cevtModuleRouterType by fujuan
--                  add subidentifier 2185 to 2188 under hh3cevtModuleSwitchType by qichenlu
--                  add subidentifier 2189 to 2191 under hh3cevtModuleSwitchType by jiangyongjiang
--                  add subidentifier 60 to 64 under hh3cevtPortRouterType by zhaomeng
--                  add subidentifier 2192 to 2208 under hh3cevtModuleSwitchType by jiangyongjiang
--                  add subidentifier 293 to 294  under hh3cevtPortSwitchType wangzilong
--                  modify name of 901 under hh3cevtModuleRouterType by ludezhen 19699
--                  add subidentifier 1013 under hh3cevtModuleRouterType by zhaomeng
--                  add subidentifier 1014 to 1020 under hh3cevtModuleRouterType by fuzhanfeng
--                  add subidentifier 1021 to 1023 under hh3cevtModuleRouterType by zhaomeng
--                  add subidentifier 2209 under hh3cevtModuleSwitchType by liuhaijun
--                  add subidentifier 295  under hh3cevtPortSwitchType wangzilong
--                  add subidentifier 1024 under hh3cevtModuleRouterType by wangxinmeng
--                  add subidentifier 1025 to 1034 under hh3cevtModuleRouterType by ludezhen
--                  add subidentifier 2210 to 2212 under hh3cevtModuleSwitchType by jiangyongjiang
-- V4.72 2019-12-02 add subidentifier 2213 to 2217 under hh3cevtModuleSwitchType by lihaijun
--                  add subidentifier 2218 to 2222 under hh3cevtModuleSwitchType by jiangyongjiang
--                  modify name of 900 under hh3cevtModuleRouterType by ludezhen
--                  add subidentifier 2223 to 2224 under hh3cevtModuleSwitchType by maoyun
--                  add subidentifier 2225 to 2226 under hh3cevtModuleSwitchType by jiangyongjiang
--                  modify name of 864 to 880890 to 894901 to 906924 to 934938940 to 943945
--                  954 to 958961 to 962969981 to 98410111025 to 1034 under hh3cevtModuleRouterType by ludezhen
--                  add subidentifier 1035 under  hh3cevtModuleRouterType by ludezhen
--                  add subidentifier 1036 under  hh3cevtModuleRouterType by zhaomeng
--                  add subidentifier 1037 to 1040 under  hh3cevtModuleRouterType by wangxinmeng
--                  add subidentifier 2227 under  hh3cevtModuleSwitchType by chenke
-- V4.73 2020-01-07 add subidentifier 2228 to 2229 under hh3cevtModuleSwitchType by chenke
--                  add subidentifier 531 to 538 under hh3cevtModuleRouterType by fuzhanfeng
--                  modify name of 943,1012,1035 under hh3cevtModuleRouterType by ludezhen
--                  add subidentifier 2230 under hh3cevtModuleSwitchType by jiangyongjiang
--                  add subidentifier 1042 to 1044 under hh3cevtModuleRouterType by zhaomeng
--                  add subidentifier 817 to 819 under hh3cevtModuleSwitchType by luoguixing
--                  add subidentifier 1042 to 1044 under hh3cevtModuleRouterType by ludezhen
-- V4.74 2020-02-11 modify name of 1035 under hh3cevtModuleRouterType by ludezhen
--                  add subidentifier 296  under hh3cevtPortSwitchType wangzilong
--                  add subidentifier 2231 to 2232  hh3cevtModuleSwitchType by chenke
--                  add subidentifier 2233 to 2236  hh3cevtModuleSwitchType by lihaijun
--                  add subidentifier 7  hh3cevtOther by ludezhen
--                  add subidentifier 2237 hh3cevtModuleSwitchType by zhanglili
-- V4.75 2020-03-10 add subidentifier 2238 to 2239 hh3cevtModuleSwitchType by zhanglili
--                  add subidentifier 539 to 546 under hh3cevtModuleRouterType by fuzhanfeng
--                  add subidentifier 297 under hh3cevtPortSwitchType wangzilong
--                  add subidentifier 2240 to 2256 hh3cevtModuleSwitchType by jiangyongjiang
--                  add subidentifier 2257 hh3cevtModuleSwitchType by zhanglili
-- V4.76 2020-04-13 add subidentifier 1048 to 1049 hh3cevtModuleRouterType by wangxinmeng
--                  add subidentifier 2258 hh3cevtModuleSwitchType by jiangyongjiang
--                  add subidentifier 1050 hh3cevtModuleRouterType by ludezhen
--                  add subidentifier 547 to 549 under hh3cevtModuleRouterType by fuzhanfeng
--                  add subidentifier 2259 hh3cevtModuleSwitchType by zhanglili
--                  add subidentifier 2260 hh3cevtModuleSwitchType by lihaijun
--                  modify name of 2233 to 2236 hh3cevtModuleSwitchType by lihaijun
-- V4.77 2020-05-13 add subidentifier 550 to hh3cevtModuleRouterType by wangxinmeng
--                  add subidentifier 1051 hh3cevtModuleRouterType by zhaomeng
--                  add subidentifier 1052 hh3cevtModuleRouterType by wangxinmeng
--                  add subidentifier 1053 to 1054 hh3cevtModuleRouterType by ludezhen
--                  modify name 2231 hh3cevtModuleRouterType by zhanglili
--                  add subidentifier 2261 hh3cevtModuleRouterType by zhanglili
--                  add subidentifier 2262 to 2274 hh3cevtModuleRouterType by jiangyongjiang
--                  add subidentifier 2275 hh3cevtModuleRouterType by zhanglili
-- V4.78 2020-06-12 add subidentifier 551 to 555 hh3cevtModuleRouterType by chenwei
--                  add subidentifier 1055 hh3cevtModuleRouterType by zhaomeng
--                  add subidentifier 2276 hh3cevtModuleRouterType by zhanglili
--                  add subidentifier 820 hh3cLswTypeOfSlot by luoguixing
-- V4.79 2020-07-13 add subidentifier 1056 to 1057 hh3cevtModuleRouterType by zhaomeng
--                  add subidentifier 65 under hh3cevtPortRouterType by zhaomeng
--                  add subidentifier 5012 to 5016 hh3cevtModuleRouterType  by songqinghong
--       2020-07-28 add subidentifier 1058 hh3cevtModuleRouterType by ludezhen
--                  add subidentifier 2277 to 2291 hh3cevtModuleRouterType by jiangyongjiang
--                  add subidentifier 66 under hh3cevtPortRouterType by zhaomeng
--                  add subidentifier 2292 hh3cevtModuleRouterType by qichenglu
--                  modify name 2186 hh3cevtModuleRouterType by qichenglu
--                  add subidentifier 2293 to 2295 hh3cevtModuleRouterType by jiangyongjiang
--                  add subidentifier 556 hh3cevtModuleRouterType by wangyuqiang
-- V4.80 2020-08-17 add subidentifier 778 to 780 hh3cevtModuleSwitchType by zhouqin
--                  add subidentifier 1059 to 1061  hh3cevtModuleRouterType by wangxinmeng
--                  add subidentifier 2296 to 2301 hh3cevtModuleRouterType by jiangyongjiang
--                  add subidentifier 2302 to 2307 hh3cevtModuleRouterType by zhanglili
--                  add subidentifier 1062 hh3cevtModuleRouterType by ludezhen
--                  add subidentifier 1063 to 1064  hh3cevtModuleRouterType by zhaomeng
-- V4.81 2020-09-10 modify name 2303 hh3cevtModuleRouterType by zhanglili
--                  add subidentifier 298 to 299 under hh3cevtPortSwitchType wangzilong
--                  add subidentifier 2308 to 2326 hh3cevtModuleRouterType by zhanglili
--                  add subidentifier 1065 to 1066 hh3cevtModuleRouterType by ludezhen
--                  add subidentifier 1067 hh3cevtModuleRouterType by zhaomeng
-- V4.82 2020-10-20 add subidentifier 2327 to 2355 hh3cevtModuleRouterType by jiangyongjiang
--                  add subidentifier 1068 hh3cevtModuleRouterType by zhaomeng
--                  add subidentifier 557 hh3cevtModuleRouterType by chenwei
--                  add subidentifier 67 hh3cevtPortRouterType by zhaomeng
-- V4.83 2020-11-12 add subidentifier 2356 to 2359 hh3cevtModuleRouterType by liuhaijun
--                  add subidentifier 2360 to 2361 hh3cevtModuleRouterType by jiangyongjiang
--                  add subidentifier 821 hh3cLswTypeOfSlot by luoguixing
-- V4.84 2020-12-10 add subidentifier 2362 hh3cevtModuleRouterType by jiangyongjiang
--                  add subidentifier 300 to 304 hh3cevtPortSwitchType by wangzilong
--                  add subidentifier 2363 hh3cLswTypeOfSlot by lihaijun
--                  add subidentifier 558 to 565 hh3cevtModuleRouterType by mazuhan
--                  add subidentifier 781 hh3cevtModuleSwitchType by zhouqin
-- V4.85 2021-01-12 add subidentifier 68 hh3cevtPortRouterType by zhaomeng
--                  modify name 65 hh3cevtPortRouterType by zhaomeng
--                  add subidentifier 566 hh3cevtModuleRouterType by mazuhan
--                  modify name 565 to 566 hh3cevtPortRouterType by wuzuhan
--                  modify name 2223 to 2224 hh3cevtModuleSwitchType by yangzhiyuan
--                  add subidentifier 1069 hh3cevtModuleRouterType by zhaomeng
--                  add subidentifier 166 to 167 under hh3cevtModuleRouterType by dengzhiyin
-- V4.86 2021-02-20 del 166 to 167 under hh3cevtModuleRouterType by dengzhiyin
--                  add subidentifier 1072 to 1073 hh3cevtModuleRouterType by dengzhiyin
--                  modify name 67 hh3cevtPortRouterType by zhaomeng
--                  add subidentifier 2364 to 2377  hh3cevtModuleRouterType by jiangyongjiang
-- V4.87 2021-03-16 modify name 1072 to 1073 hh3cevtModuleRouterType by dengzhiyin
--                  add subidentifier 305 hh3cevtPortSwitchType by wangzilong
--                  add subidentifier 2388 to 2390  hh3cevtModuleRouterType by jiangyongjiang
--                  modify name 1072 to 1073 hh3cevtModuleRouterType by liuzhongyuan
-- V4.88 2021-04-20 add subidentifier 1074 hh3cevtModuleRouterType by zhaomeng
--                  add subidentifier 2381 to 2393 hh3cevtModuleSwitchType by jiangyongjiang
--                  modify name 905 to 906 hh3cevtModuleRouterType by ludezhen
--                  add subidentifier 2394 to 2397 hh3cevtModuleSwitchType by zhanglili
-- V4.89 2021-05-15 add subidentifier 306 to 311 hh3cevtModuleRouterType by wangzilong
--                  add subidentifier 2398 to 2406 hh3cevtModuleSwitchType by lihaijun
--                  add subidentifier 2407 to 2408 hh3cevtModuleSwitchType by jiangyongjiang
--                  modify introduction  975,976 and 1057 hh3cevtModuleRouterType by zhaomeng
--                  modify name 2356 to 2358 subidentifier and del subidentifier 2403 to 2406 hh3cevtModuleSwitchType by lihaijun
--                  modify name 2213 to 2217 subidentifier hh3cevtModuleSwitchType by lihaijun
--                  add subidentifier 2409 hh3cevtModuleSwitchType by qichenglu
--                  add subidentifier 2410 to 2428 hh3cevtModuleSwitchType by jiangyongjiang
-- =================================================================
HH3C-ENTITY-VENDORTYPE-OID-MIB DEFINITIONS ::= BEGIN

IMPORTS
    MODULE-IDENTITY
        FROM SNMPv2-SMI
    hh3c
        FROM HH3C-OID-MIB;


hh3cEntityVendorTypeOID MODULE-IDENTITY

        LAST-UPDATED "200903310000Z"
        ORGANIZATION
            "New H3C Technologies Co., Ltd."
        CONTACT-INFO
            "Platform Team New H3C Technologies Co., Ltd.
            Hai-Dian District Beijing P.R. China
            Zip:100085
            http://www.h3c.com"
        DESCRIPTION
            "The private MIB includes the definition of the object
            identifiers on products, which are used by the
            entPhysicalTable of the ENTITY-MIB to uniquely identify the
            type of each physical entry."
        ::= { hh3c 3 }

hh3cEntityVendortypeObjects   OBJECT IDENTIFIER ::= { hh3cEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

hh3cevtOther     OBJECT IDENTIFIER ::= { hh3cEntityVendortypeObjects 1 }

-- May be defined detailed in future.

hh3cevtOtherUnknownCard  OBJECT IDENTIFIER ::= { hh3cevtOther 1 }
hh3cevtCPU               OBJECT IDENTIFIER ::= { hh3cevtOther 2 }
hh3cevtDOM               OBJECT IDENTIFIER ::= { hh3cevtOther 3 }  -- Disk on Module
hh3cevtCFCard            OBJECT IDENTIFIER ::= { hh3cevtOther 4 }  -- Compact Flash Card
hh3cevtHardDisk          OBJECT IDENTIFIER ::= { hh3cevtOther 5 }  -- Hard Disk
hh3cevtSDCard            OBJECT IDENTIFIER ::= { hh3cevtOther 6 }  -- Secure Digital Memory Card
hh3cevtMEM             OBJECT IDENTIFIER ::= { hh3cevtOther 7 }  -- Internal Memory

-- hh3cevtGeneralCPU is a general vendor type of CPU.  It is used only for
-- general purpose.  It is strongly recommended that this object should not
-- be used to present the specific CPU vendor type in most cases.  More
-- accurate and clear vendor types should be defined to present specific CPU.
hh3cevtGeneralCPU        OBJECT IDENTIFIER ::= { hh3cevtCPU 1 }


hh3cevtUnknown   OBJECT IDENTIFIER ::= { hh3cEntityVendortypeObjects 2 }

hh3cevtChassis   OBJECT IDENTIFIER ::= { hh3cEntityVendortypeObjects 3 }

-- chassis OID assignments
-- May be substituted by sysObjectID.  So none is assigned at present.

--
-- backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

hh3cevtBackplane     OBJECT IDENTIFIER ::= { hh3cEntityVendortypeObjects 4 }

--
-- hh3cevtContainer section:
--
hh3cevtContainer     OBJECT IDENTIFIER ::= { hh3cEntityVendortypeObjects 5 }

--
-- hh3cevtPowerSupply section:
--
hh3cevtPowerSupply   OBJECT IDENTIFIER ::= { hh3cEntityVendortypeObjects 6 }
hh3cevtPowerSupplyAC            OBJECT IDENTIFIER ::= { hh3cevtPowerSupply 2 }
hh3cevtPowerSupplyDC            OBJECT IDENTIFIER ::= { hh3cevtPowerSupply 3 }
hh3cevtPowerSupplySTD130W       OBJECT IDENTIFIER ::= { hh3cevtPowerSupply 4 }     -- Standard 130W PSU
hh3cevtPowerSupplySTD180W       OBJECT IDENTIFIER ::= { hh3cevtPowerSupply 5 }     -- Standard 180W PSU
hh3cevtPowerSupplyPOE24Port     OBJECT IDENTIFIER ::= { hh3cevtPowerSupply 6 }     -- 24 Port POE PSU 480W
hh3cevtPowerSupplyPOE48Port     OBJECT IDENTIFIER ::= { hh3cevtPowerSupply 7 }     -- 48 Port POE PSU 480W
hh3cevtPowerSupplyLSUM1AC2500   OBJECT IDENTIFIER ::= { hh3cevtPowerSupply 8 }
hh3cevtPowerSupplyLSUM2AC2500   OBJECT IDENTIFIER ::= { hh3cevtPowerSupply 9 }
hh3cevtPowerSupplyLSUM1DC2400   OBJECT IDENTIFIER ::= { hh3cevtPowerSupply 10 }
hh3cevtPowerSupplyLSUM1AC1200   OBJECT IDENTIFIER ::= { hh3cevtPowerSupply 11 }
hh3cevtPowerSupplyLSQM1DC2400   OBJECT IDENTIFIER ::= { hh3cevtPowerSupply 12 }
hh3cevtPowerSupplyLSUM5AC2500   OBJECT IDENTIFIER ::= { hh3cevtPowerSupply 13 }
hh3cevtPowerSupplyLSUM5DC2400   OBJECT IDENTIFIER ::= { hh3cevtPowerSupply 14 }
hh3cevtPowerSupplyLSUM6DC2400   OBJECT IDENTIFIER ::= { hh3cevtPowerSupply 15 }
hh3cevtPowerSupplyLSUM6AC2500   OBJECT IDENTIFIER ::= { hh3cevtPowerSupply 16 }
hh3cevtPowerSupplyLSQM1AC1400   OBJECT IDENTIFIER ::= { hh3cevtPowerSupply 17 }
hh3cevtPowerSupplyLSQM1DC1400   OBJECT IDENTIFIER ::= { hh3cevtPowerSupply 18 }
hh3cevtPowerSupplyLSQM1AC2800   OBJECT IDENTIFIER ::= { hh3cevtPowerSupply 19 }
hh3cevtPowerSupplyLSQM2AC1400   OBJECT IDENTIFIER ::= { hh3cevtPowerSupply 20 }
hh3cevtPowerSupplyLSQM1AC6000   OBJECT IDENTIFIER ::= { hh3cevtPowerSupply 21 }
hh3cevtPowerSupplyLSQM2AC6000   OBJECT IDENTIFIER ::= { hh3cevtPowerSupply 22 }
hh3cevtPowerSupplyLSQM1AC300    OBJECT IDENTIFIER ::= { hh3cevtPowerSupply 23 }
hh3cevtPowerSupplyLSQM1AC650    OBJECT IDENTIFIER ::= { hh3cevtPowerSupply 24 }
hh3cevtPowerSupplyLSQM1DC650    OBJECT IDENTIFIER ::= { hh3cevtPowerSupply 25 }
hh3cevtPowerSupplyLSQM1PWRSPA   OBJECT IDENTIFIER ::= { hh3cevtPowerSupply 26 }
hh3cevtPowerSupplyLSWM1RPS800   OBJECT IDENTIFIER ::= { hh3cevtPowerSupply 27 }
hh3cevtPowerSupplyLSQM7AC1400   OBJECT IDENTIFIER ::= { hh3cevtPowerSupply 28 }
hh3cevtPowerSupplyLSQM7DC1400   OBJECT IDENTIFIER ::= { hh3cevtPowerSupply 29 }
hh3cevtPowerSupplyLSQM7AC2800   OBJECT IDENTIFIER ::= { hh3cevtPowerSupply 30 }
hh3cevtPowerSupplyLSQM7AC6000   OBJECT IDENTIFIER ::= { hh3cevtPowerSupply 31 }
hh3cevtPowerSupplyLSQM7AC300    OBJECT IDENTIFIER ::= { hh3cevtPowerSupply 32 }
hh3cevtPowerSupplyLSQM7AC650    OBJECT IDENTIFIER ::= { hh3cevtPowerSupply 33 }
hh3cevtPowerSupplyLSQM7DC650    OBJECT IDENTIFIER ::= { hh3cevtPowerSupply 34 }
hh3cevtPowerSupplyLSWM2RPS800   OBJECT IDENTIFIER ::= { hh3cevtPowerSupply 35 }
hh3cevtPowerSupplySecPathAC     OBJECT IDENTIFIER ::= { hh3cevtPowerSupply 36 }    -- F5000-NSUM1AC650-650W
hh3cevtPowerSupplySecPathDC     OBJECT IDENTIFIER ::= { hh3cevtPowerSupply 37}     -- F5000-NSUM1DC650-650W
--
-- hh3cevtFan section:
--
hh3cevtFan       OBJECT IDENTIFIER ::= { hh3cEntityVendortypeObjects 7 }
hh3cevtHotSwapFan       OBJECT IDENTIFIER ::=  { hh3cevtFan 1 }
hh3cevtNonHotSwapFan    OBJECT IDENTIFIER ::=  { hh3cevtFan 2 }
hh3cevtFanLSUM110504    OBJECT IDENTIFIER ::=  { hh3cevtFan 3 }
hh3cevtFanLSUM110508    OBJECT IDENTIFIER ::=  { hh3cevtFan 4 }
hh3cevtFanLSUM110508V   OBJECT IDENTIFIER ::=  { hh3cevtFan 5 }
hh3cevtFanLSUM110512    OBJECT IDENTIFIER ::=  { hh3cevtFan 6 }
hh3cevtFanLSUM210512    OBJECT IDENTIFIER ::=  { hh3cevtFan 7 }
hh3cevtFanLSUM510504    OBJECT IDENTIFIER ::=  { hh3cevtFan 8 }
hh3cevtFanLSUM510508    OBJECT IDENTIFIER ::=  { hh3cevtFan 9 }
hh3cevtFanLSUM510508V   OBJECT IDENTIFIER ::=  { hh3cevtFan 10 }
hh3cevtFanLSUM510512U   OBJECT IDENTIFIER ::=  { hh3cevtFan 11 }
hh3cevtFanLSUM510512D   OBJECT IDENTIFIER ::=  { hh3cevtFan 12 }
hh3cevtFanLSUM511908V   OBJECT IDENTIFIER ::=  { hh3cevtFan 13 }
hh3cevtFanLSQM17502E    OBJECT IDENTIFIER ::=  { hh3cevtFan 14 }
hh3cevtFanLSQM17503E    OBJECT IDENTIFIER ::=  { hh3cevtFan 15 }
hh3cevtFanLSQM17503ES   OBJECT IDENTIFIER ::=  { hh3cevtFan 16 }
hh3cevtFanLSQM17506E    OBJECT IDENTIFIER ::=  { hh3cevtFan 17 }
hh3cevtFanLSQM17506EV   OBJECT IDENTIFIER ::=  { hh3cevtFan 18 }
hh3cevtFanLSQM17510E    OBJECT IDENTIFIER ::=  { hh3cevtFan 19 }
hh3cevtFanLSQM57503     OBJECT IDENTIFIER ::=  { hh3cevtFan 20 }
hh3cevtFanLSQM57502     OBJECT IDENTIFIER ::=  { hh3cevtFan 21 }
hh3cevtFanLSQM57506     OBJECT IDENTIFIER ::=  { hh3cevtFan 22 }
hh3cevtFanLSQM57510     OBJECT IDENTIFIER ::=  { hh3cevtFan 23 }
hh3cevtHotSwapFan-NSUM1BFANSC         OBJECT IDENTIFIER ::=  { hh3cevtFan 24 }   -- F5000-NSUM1BFANSC
hh3cevtHotSwapFan-NSUM1BFANSCB        OBJECT IDENTIFIER ::=  { hh3cevtFan 25 }   -- F5000-NSUM1BFANSCB
--
-- hh3cevtSensor section:
--
hh3cevtSensor        OBJECT IDENTIFIER ::= { hh3cEntityVendortypeObjects 8 }
hh3cevtSensorTemperature     OBJECT IDENTIFIER ::= { hh3cevtSensor 1 }
hh3cevtSensorVoltage         OBJECT IDENTIFIER ::= { hh3cevtSensor 2 }
hh3cevtSensorFanSpeed        OBJECT IDENTIFIER ::= { hh3cevtSensor 3 }


--
-- hh3cevtModule section:
--
hh3cevtModule        OBJECT IDENTIFIER ::= { hh3cEntityVendortypeObjects 9 }

-- hh3cevtModule is subdivided into sections like Router and Switch. These represent
-- cards used only on the router and switch.
-- hh3cevtModuleCommonCards contains cards that can be used interchangeably
-- across more than one platform


-- Acronyms used in the hh3cevtModule section:
--

hh3cevtModuleUnknownCard     OBJECT IDENTIFIER ::= { hh3cevtModule 1 }

-- hh3cevtModuleCommonCards - cards and subcards common to more
-- than one platform
hh3cevtModuleCommonCards     OBJECT IDENTIFIER ::= { hh3cevtModule 2 }

hh3cevtModuleBoxCEN                         OBJECT IDENTIFIER ::= { hh3cevtModuleCommonCards 1 }
hh3cevtModuleBoxIRF48GE                     OBJECT IDENTIFIER ::= { hh3cevtModuleCommonCards 2 }
hh3cevtModuleBoxIRF24GE24TGE                OBJECT IDENTIFIER ::= { hh3cevtModuleCommonCards 3 }
hh3cevtModuleChassisMpu                     OBJECT IDENTIFIER ::= { hh3cevtModuleCommonCards 4 }
hh3cevtModuleLPU48GE                        OBJECT IDENTIFIER ::= { hh3cevtModuleCommonCards 5 }
hh3cevtModuleLPU4GE4Serial                  OBJECT IDENTIFIER ::= { hh3cevtModuleCommonCards 6 }
hh3cevtModuleLPU4GE4Pos                     OBJECT IDENTIFIER ::= { hh3cevtModuleCommonCards 7 }
hh3cevtModuleLPU4GE4E1                      OBJECT IDENTIFIER ::= { hh3cevtModuleCommonCards 8 }



-- hh3cevtModuleRouterType cards are slot-cards specific to the Router.
hh3cevtModuleRouterType      OBJECT IDENTIFIER ::= { hh3cevtModule 3 }

--hh3cevtModuleRt-Unavailable               OBJECT IDENTIFIER ::= { hh3cevtModuleRouterType 1 }
hh3cevtModuleRt-As                          OBJECT IDENTIFIER ::= { hh3cevtModuleRouterType 2 }
hh3cevtModuleRt-Sa                          OBJECT IDENTIFIER ::= { hh3cevtModuleRouterType 3 }
hh3cevtModuleRt-Bi                          OBJECT IDENTIFIER ::= { hh3cevtModuleRouterType 4 }
hh3cevtModuleRt-E12                         OBJECT IDENTIFIER ::= { hh3cevtModuleRouterType 5 }
hh3cevtModuleRt-E14                         OBJECT IDENTIFIER ::= { hh3cevtModuleRouterType 6 }
hh3cevtModuleRt-Fe1                         OBJECT IDENTIFIER ::= { hh3cevtModuleRouterType 7 }
hh3cevtModuleRt-E1                          OBJECT IDENTIFIER ::= { hh3cevtModuleRouterType 8 }
hh3cevtModuleRt-Fe2                         OBJECT IDENTIFIER ::= { hh3cevtModuleRouterType 9 }
hh3cevtModuleRt-Vi2                         OBJECT IDENTIFIER ::= { hh3cevtModuleRouterType 11 }
hh3cevtModuleRt-Vi4                         OBJECT IDENTIFIER ::= { hh3cevtModuleRouterType 12 }
hh3cevtModuleRt-Vi30                        OBJECT IDENTIFIER ::= { hh3cevtModuleRouterType 13 }
hh3cevtModuleRt-S1b                         OBJECT IDENTIFIER ::= { hh3cevtModuleRouterType 14 }
hh3cevtModuleRt-Sa2                         OBJECT IDENTIFIER ::= { hh3cevtModuleRouterType 15 }
hh3cevtModuleRt-As16                        OBJECT IDENTIFIER ::= { hh3cevtModuleRouterType 16 }
hh3cevtModuleRt-New8as                      OBJECT IDENTIFIER ::= { hh3cevtModuleRouterType 17 }
hh3cevtModuleRt-Sa1                         OBJECT IDENTIFIER ::= { hh3cevtModuleRouterType 18 }
hh3cevtModuleRt-Fxs2                        OBJECT IDENTIFIER ::= { hh3cevtModuleRouterType 19 }
hh3cevtModuleRt-Fxo2                        OBJECT IDENTIFIER ::= { hh3cevtModuleRouterType 20 }
hh3cevtModuleRt-Em2                         OBJECT IDENTIFIER ::= { hh3cevtModuleRouterType 21 }
hh3cevtModuleRt-Fxs4                        OBJECT IDENTIFIER ::= { hh3cevtModuleRouterType 22 }
hh3cevtModuleRt-Fxo4                        OBJECT IDENTIFIER ::= { hh3cevtModuleRouterType 23 }
hh3cevtModuleRt-Em4                         OBJECT IDENTIFIER ::= { hh3cevtModuleRouterType 24 }
hh3cevtModuleRt-Sab                         OBJECT IDENTIFIER ::= { hh3cevtModuleRouterType 25 }
hh3cevtModuleRt-E1vi                        OBJECT IDENTIFIER ::= { hh3cevtModuleRouterType 26 }
hh3cevtModuleRt-Am12                        OBJECT IDENTIFIER ::= { hh3cevtModuleRouterType 27 }
hh3cevtModuleRt-Am6                         OBJECT IDENTIFIER ::= { hh3cevtModuleRouterType 28 }
hh3cevtModuleRt-Ndec                        OBJECT IDENTIFIER ::= { hh3cevtModuleRouterType 29 }
hh3cevtModuleRt-Newsa2                      OBJECT IDENTIFIER ::= { hh3cevtModuleRouterType 30 }
hh3cevtModuleRt-Aux                         OBJECT IDENTIFIER ::= { hh3cevtModuleRouterType 31 }
hh3cevtModuleRt-Console                     OBJECT IDENTIFIER ::= { hh3cevtModuleRouterType 32 }
hh3cevtModuleRt-Sic-wan                     OBJECT IDENTIFIER ::= { hh3cevtModuleRouterType 33 }
hh3cevtModuleRt-Sic-1fe                     OBJECT IDENTIFIER ::= { hh3cevtModuleRouterType 34 }
hh3cevtModuleRt-Sic-1sa                     OBJECT IDENTIFIER ::= { hh3cevtModuleRouterType 35 }
hh3cevtModuleRt-Sic-3as                     OBJECT IDENTIFIER ::= { hh3cevtModuleRouterType 36 }
hh3cevtModuleRt-Sic-1e1                     OBJECT IDENTIFIER ::= { hh3cevtModuleRouterType 37 }
hh3cevtModuleRt-Sic-1t1                     OBJECT IDENTIFIER ::= { hh3cevtModuleRouterType 38 }
hh3cevtModuleRt-Sic-1bu                     OBJECT IDENTIFIER ::= { hh3cevtModuleRouterType 39 }
hh3cevtModuleRt-Sic-2bu                     OBJECT IDENTIFIER ::= { hh3cevtModuleRouterType 40 }
hh3cevtModuleRt-Sic-1bs                     OBJECT IDENTIFIER ::= { hh3cevtModuleRouterType 41 }
hh3cevtModuleRt-Sic-2bs                     OBJECT IDENTIFIER ::= { hh3cevtModuleRouterType 42 }
hh3cevtModuleRt-Sic-1am                     OBJECT IDENTIFIER ::= { hh3cevtModuleRouterType 43 }
hh3cevtModuleRt-Sic-2am                     OBJECT IDENTIFIER ::= { hh3cevtModuleRouterType 44 }
hh3cevtModuleRt-Sic-1em                     OBJECT IDENTIFIER ::= { hh3cevtModuleRouterType 45 }
hh3cevtModuleRt-Sic-2em                     OBJECT IDENTIFIER ::= { hh3cevtModuleRouterType 46 }
hh3cevtModuleRt-Sic-1fxs                    OBJECT IDENTIFIER ::= { hh3cevtModuleRouterType 47 }
hh3cevtModuleRt-Sic-2fxs                    OBJECT IDENTIFIER ::= { hh3cevtModuleRouterType 48 }
hh3cevtModuleRt-Sic-1fxo                    OBJECT IDENTIFIER ::= { hh3cevtModuleRouterType 49 }
hh3cevtModuleRt-Sic-2fxo                    OBJECT IDENTIFIER ::= { hh3cevtModuleRouterType 50 }
hh3cevtModuleRt-Fcm6                        OBJECT IDENTIFIER ::= { hh3cevtModuleRouterType 51 }
hh3cevtModuleRt-Sa8                         OBJECT IDENTIFIER ::= { hh3cevtModuleRouterType 52 }
hh3cevtModuleRt-T11                         OBJECT IDENTIFIER ::= { hh3cevtModuleRouterType 53 }
hh3cevtModuleRt-T12                         OBJECT IDENTIFIER ::= { hh3cevtModuleRouterType 54 }
hh3cevtModuleRt-T14                         OBJECT IDENTIFIER ::= { hh3cevtModuleRouterType 55 }
hh3cevtModuleRt-T1vi                        OBJECT IDENTIFIER ::= { hh3cevtModuleRouterType 56 }
hh3cevtModuleRt-Fcm4                        OBJECT IDENTIFIER ::= { hh3cevtModuleRouterType 57 }
hh3cevtModuleRt-Fcm2                        OBJECT IDENTIFIER ::= { hh3cevtModuleRouterType 58 }
hh3cevtModuleRt-Rtb21ce3                    OBJECT IDENTIFIER ::= { hh3cevtModuleRouterType 59 }
hh3cevtModuleRt-Ame6                        OBJECT IDENTIFIER ::= { hh3cevtModuleRouterType 60 }
hh3cevtModuleRt-Ame12                       OBJECT IDENTIFIER ::= { hh3cevtModuleRouterType 61 }
hh3cevtModuleRt-E11-f                       OBJECT IDENTIFIER ::= { hh3cevtModuleRouterType 65 }
hh3cevtModuleRt-E12-f                       OBJECT IDENTIFIER ::= { hh3cevtModuleRouterType 66 }
hh3cevtModuleRt-E14-f                       OBJECT IDENTIFIER ::= { hh3cevtModuleRouterType 67 }
hh3cevtModuleRt-T11-f                       OBJECT IDENTIFIER ::= { hh3cevtModuleRouterType 68 }
hh3cevtModuleRt-T12-f                       OBJECT IDENTIFIER ::= { hh3cevtModuleRouterType 69 }
hh3cevtModuleRt-T14-f                       OBJECT IDENTIFIER ::= { hh3cevtModuleRouterType 70 }
hh3cevtModuleRt-E11-f-17                    OBJECT IDENTIFIER ::= { hh3cevtModuleRouterType 71 }
hh3cevtModuleRt-T11-f-17                    OBJECT IDENTIFIER ::= { hh3cevtModuleRouterType 72 }
hh3cevtModuleRt-Rtb21ct3                    OBJECT IDENTIFIER ::= { hh3cevtModuleRouterType 73 }
hh3cevtModuleRt-Atmadsl1                    OBJECT IDENTIFIER ::= { hh3cevtModuleRouterType 74 }
hh3cevtModuleRt-Atmadsl2                    OBJECT IDENTIFIER ::= { hh3cevtModuleRouterType 75 }
hh3cevtModuleRt-Atm155m                     OBJECT IDENTIFIER ::= { hh3cevtModuleRouterType 76 }
hh3cevtModuleRt-Ase8                        OBJECT IDENTIFIER ::= { hh3cevtModuleRouterType 77 }
hh3cevtModuleRt-Ase16                       OBJECT IDENTIFIER ::= { hh3cevtModuleRouterType 78 }
hh3cevtModuleRt-Sae4                        OBJECT IDENTIFIER ::= { hh3cevtModuleRouterType 79 }
hh3cevtModuleRt-Sae2                        OBJECT IDENTIFIER ::= { hh3cevtModuleRouterType 80 }
hh3cevtModuleRt-Atmshdsl1                   OBJECT IDENTIFIER ::= { hh3cevtModuleRouterType 90 }
hh3cevtModuleRt-Atmshdsl2                   OBJECT IDENTIFIER ::= { hh3cevtModuleRouterType 91 }
hh3cevtModuleRt-Atmshdsl4                   OBJECT IDENTIFIER ::= { hh3cevtModuleRouterType 92 }
hh3cevtModuleRt-Atm25m                      OBJECT IDENTIFIER ::= { hh3cevtModuleRouterType 93 }
hh3cevtModuleRt-Atme3                       OBJECT IDENTIFIER ::= { hh3cevtModuleRouterType 94 }
hh3cevtModuleRt-Atmt3                       OBJECT IDENTIFIER ::= { hh3cevtModuleRouterType 95 }
hh3cevtModuleRt-Xdsl-fec                    OBJECT IDENTIFIER ::= { hh3cevtModuleRouterType 96 }
hh3cevtModuleRt-Xdsl-adsl                   OBJECT IDENTIFIER ::= { hh3cevtModuleRouterType 97 }
hh3cevtModuleRt-Xdsl-gshdsl                 OBJECT IDENTIFIER ::= { hh3cevtModuleRouterType 98 }
hh3cevtModuleRt-Xdsl-bri                    OBJECT IDENTIFIER ::= { hh3cevtModuleRouterType 99 }
hh3cevtModuleRt-Xdsl-scc                    OBJECT IDENTIFIER ::= { hh3cevtModuleRouterType 100 }
hh3cevtModuleRt-Ge1                         OBJECT IDENTIFIER ::= { hh3cevtModuleRouterType 101 }
hh3cevtModuleRt-Pos155m                     OBJECT IDENTIFIER ::= { hh3cevtModuleRouterType 102 }
hh3cevtModuleRt-Cpos                        OBJECT IDENTIFIER ::= { hh3cevtModuleRouterType 103 }
hh3cevtModuleRt-Fe1op                       OBJECT IDENTIFIER ::= { hh3cevtModuleRouterType 104 }
hh3cevtModuleRt-Sae8                        OBJECT IDENTIFIER ::= { hh3cevtModuleRouterType 105 }
hh3cevtModuleRt-Atm155m-mm                  OBJECT IDENTIFIER ::= { hh3cevtModuleRouterType 106 }
hh3cevtModuleRt-Atm155m-sm                  OBJECT IDENTIFIER ::= { hh3cevtModuleRouterType 107 }
hh3cevtModuleRt-Atm155m-sml                 OBJECT IDENTIFIER ::= { hh3cevtModuleRouterType 108 }
hh3cevtModuleRt-Fe1op-sfx                   OBJECT IDENTIFIER ::= { hh3cevtModuleRouterType 109 }
hh3cevtModuleRt-Fe1op-mfx                   OBJECT IDENTIFIER ::= { hh3cevtModuleRouterType 110 }
hh3cevtModuleRt-Cpos-t1                     OBJECT IDENTIFIER ::= { hh3cevtModuleRouterType 111 }
hh3cevtModuleRt-Ge1op                       OBJECT IDENTIFIER ::= { hh3cevtModuleRouterType 112 }
hh3cevtModuleRt-Ge2op                       OBJECT IDENTIFIER ::= { hh3cevtModuleRouterType 113 }
hh3cevtModuleRt-Ge2                         OBJECT IDENTIFIER ::= { hh3cevtModuleRouterType 114 }
hh3cevtModuleRt-Fix-1wan                    OBJECT IDENTIFIER ::= { hh3cevtModuleRouterType 115 }
hh3cevtModuleRt-Fix-1sae                    OBJECT IDENTIFIER ::= { hh3cevtModuleRouterType 116 }
hh3cevtModuleRt-Cavium                      OBJECT IDENTIFIER ::= { hh3cevtModuleRouterType 117 }
hh3cevtModuleRt-Sic1Eth                     OBJECT IDENTIFIER ::= { hh3cevtModuleRouterType 118 }
hh3cevtModuleRt-atm1ADSLI                   OBJECT IDENTIFIER ::= { hh3cevtModuleRouterType 119 }
hh3cevtModuleRt-atm2ADSLI                   OBJECT IDENTIFIER ::= { hh3cevtModuleRouterType 120 }
hh3cevtModuleRt-fix-e11                     OBJECT IDENTIFIER ::= { hh3cevtModuleRouterType 121 }
hh3cevtModuleRt-fix-t11                     OBJECT IDENTIFIER ::= { hh3cevtModuleRouterType 122 }
hh3cevtModuleRt-e18-75                      OBJECT IDENTIFIER ::= { hh3cevtModuleRouterType 123 }
hh3cevtModuleRt-e18-120                     OBJECT IDENTIFIER ::= { hh3cevtModuleRouterType 124 }
hh3cevtModuleRt-t18                         OBJECT IDENTIFIER ::= { hh3cevtModuleRouterType 125 }
hh3cevtModuleRt-sic-1vifxs                  OBJECT IDENTIFIER ::= { hh3cevtModuleRouterType 126 }
hh3cevtModuleRt-sic-1vifxo                  OBJECT IDENTIFIER ::= { hh3cevtModuleRouterType 127 }
hh3cevtModuleRt-sic-2vifxs                  OBJECT IDENTIFIER ::= { hh3cevtModuleRouterType 128 }
hh3cevtModuleRt-sic-2vifxo                  OBJECT IDENTIFIER ::= { hh3cevtModuleRouterType 129 }
hh3cevtModuleRt-xdsl-fec-new                OBJECT IDENTIFIER ::= { hh3cevtModuleRouterType 130 }
hh3cevtModuleRt-xdsl-sa                     OBJECT IDENTIFIER ::= { hh3cevtModuleRouterType 131 }
hh3cevtModuleRt-bs4                         OBJECT IDENTIFIER ::= { hh3cevtModuleRouterType 132 }
hh3cevtModuleRt-ima-8e175                   OBJECT IDENTIFIER ::= { hh3cevtModuleRouterType 133 }
hh3cevtModuleRt-ima-8e1120                  OBJECT IDENTIFIER ::= { hh3cevtModuleRouterType 134 }
hh3cevtModuleRt-ima-4e175                   OBJECT IDENTIFIER ::= { hh3cevtModuleRouterType 135 }
hh3cevtModuleRt-ima-4e1120                  OBJECT IDENTIFIER ::= { hh3cevtModuleRouterType 136 }
hh3cevtModuleRt-ima-8t1                     OBJECT IDENTIFIER ::= { hh3cevtModuleRouterType 137 }
hh3cevtModuleRt-ima-4t1                     OBJECT IDENTIFIER ::= { hh3cevtModuleRouterType 138 }
hh3cevtModuleRt-sic-1t1f                    OBJECT IDENTIFIER ::= { hh3cevtModuleRouterType 139 }
hh3cevtModuleRT-SIC-1E1F                    OBJECT IDENTIFIER ::= { hh3cevtModuleRouterType 140 }
hh3cevtModuleRt-VG-16fxs                    OBJECT IDENTIFIER ::= { hh3cevtModuleRouterType 141 }
hh3cevtModuleRt-VG-32fxs                    OBJECT IDENTIFIER ::= { hh3cevtModuleRouterType 142 }
hh3cevtModuleRt-VG-8fxo                     OBJECT IDENTIFIER ::= { hh3cevtModuleRouterType 143 }
hh3cevtModuleRt-VG-2fe                      OBJECT IDENTIFIER ::= { hh3cevtModuleRouterType 144 }
hh3cevtModuleRt-sib                         OBJECT IDENTIFIER ::= { hh3cevtModuleRouterType 145 } -- SIB card
hh3cevtModuleRt-cie32                       OBJECT IDENTIFIER ::= { hh3cevtModuleRouterType 146 } -- 32M SSRAM CIE card
hh3cevtModuleRt-cie64                       OBJECT IDENTIFIER ::= { hh3cevtModuleRouterType 147 } -- 64M SSRAM CIE card
hh3cevtModuleRt-cie96                       OBJECT IDENTIFIER ::= { hh3cevtModuleRouterType 148 } -- 96M SSRAM CIE card
hh3cevtModuleRt-Fe4                         OBJECT IDENTIFIER ::= { hh3cevtModuleRouterType 149 } -- 4FE card
hh3cevtModuleRt-fxs4fxo1                    OBJECT IDENTIFIER ::= { hh3cevtModuleRouterType 150 } -- 4 Port Foreign Exchange Station and 1 Port Foreign Exchange Office Interface
hh3cevtModuleRt-atm1shdsl4wire              OBJECT IDENTIFIER ::= { hh3cevtModuleRouterType 151 } -- G.SHDSL 4 wire MIM card, 1 port
hh3cevtModuleRt-atmIma4shdsl                OBJECT IDENTIFIER ::= { hh3cevtModuleRouterType 152 } -- G.SHDSL 8 wire MIM card, 4 ports
hh3cevtModuleRt-ls4                         OBJECT IDENTIFIER ::= { hh3cevtModuleRouterType 153 } -- 4 Ports Layer 2 Lanswitch Module
hh3cevtModuleRt-ls8                         OBJECT IDENTIFIER ::= { hh3cevtModuleRouterType 154 } -- 8 Ports Layer 2 Lanswitch Module
hh3cevtModuleRt-ls16                        OBJECT IDENTIFIER ::= { hh3cevtModuleRouterType 155 } -- 16 Ports Layer 2 Lanswitch Module
hh3cevtModuleRt-sic-adls2plus-isdn          OBJECT IDENTIFIER ::= { hh3cevtModuleRouterType 156 } -- ADLS2Plus SIC card, ISDN port
hh3cevtModuleRt-sic-adls2plus-pots          OBJECT IDENTIFIER ::= { hh3cevtModuleRouterType 157 } -- ADLS2Plus SIC card, POTS port
hh3cevtModuleRt-ft3                         OBJECT IDENTIFIER ::= { hh3cevtModuleRouterType 158 } -- 1 Port Fractional T3 module
hh3cevtModuleRt-ce32                        OBJECT IDENTIFIER ::= { hh3cevtModuleRouterType 159 } -- 2 Port Channelized E3 module
hh3cevtModuleRt-bsv2                        OBJECT IDENTIFIER ::= { hh3cevtModuleRouterType 160 } -- 2 Port BSV module
hh3cevtModuleRt-bsv4                        OBJECT IDENTIFIER ::= { hh3cevtModuleRouterType 161 } -- 4 Port BSV module
hh3cevtModuleRt-RPU                         OBJECT IDENTIFIER ::= { hh3cevtModuleRouterType 162 } -- Route processing unit
hh3cevtModuleRt-ERPU                        OBJECT IDENTIFIER ::= { hh3cevtModuleRouterType 163 } -- Enhanced route processing unit
hh3cevtModuleRt-SSL                         OBJECT IDENTIFIER ::= { hh3cevtModuleRouterType 164 } -- SSL Encrypt Card
hh3cevtModuleRt-NSA                         OBJECT IDENTIFIER ::= { hh3cevtModuleRouterType 165 } -- NSA Encrypt Card

--
-- 166 to 199 reserved for other devices
--


--
-- 200 to 399 reserved for normal routers part I
--
hh3cevtModuleRT-SIC-1GEC                    OBJECT IDENTIFIER ::= { hh3cevtModuleRouterType 200 } -- 1-Port 10M/100M/1000M COMBO Ethernet Interface SIC Module
hh3cevtModuleRT-24FSW                       OBJECT IDENTIFIER ::= { hh3cevtModuleRouterType 201 } -- 24-Port 10M/100M and 2-Port 1000BASE-T/1000BASE-X(COMBO) Ethernet L2 Switch Module
hh3cevtModuleRT-24FSWP                      OBJECT IDENTIFIER ::= { hh3cevtModuleRouterType 202 } -- 24-Port 10M/100M(WITH POE) and 2-Port 1000BASE-T/1000BASE-X(COMBO) Ethernet L2 Switch Module
hh3cevtModuleRT-16FSW                       OBJECT IDENTIFIER ::= { hh3cevtModuleRouterType 203 } -- 16-Port 10M/100M Ethernet L2 Switch Module
hh3cevtModuleRT-16FSWP                      OBJECT IDENTIFIER ::= { hh3cevtModuleRouterType 204 } -- 16-Port 10M/100M(WITH POE) Ethernet L2 Switch Module
hh3cevtModuleRT-1VE1                        OBJECT IDENTIFIER ::= { hh3cevtModuleRouterType 205 } -- 1-Port Voice E1 Module
hh3cevtModuleRT-1VT1                        OBJECT IDENTIFIER ::= { hh3cevtModuleRouterType 206 } -- 1-Port Voice T1 Module
hh3cevtModuleRT-2VE1                        OBJECT IDENTIFIER ::= { hh3cevtModuleRouterType 207 } -- 2-Port Voice E1 Module
hh3cevtModuleRT-2VT1                        OBJECT IDENTIFIER ::= { hh3cevtModuleRouterType 208 } -- 2-Port Voice T1 Module
hh3cevtModuleRT-SIC-4FSW                    OBJECT IDENTIFIER ::= { hh3cevtModuleRouterType 209 } -- 4-Port 10M/100M Ethernet L2 Switch Module (RJ45)
hh3cevtModuleRT-SIC-4FSWP                   OBJECT IDENTIFIER ::= { hh3cevtModuleRouterType 210 } -- 4-Port 10M/100M Ethernet L2 Switch Module(RJ45,WITH POE)
hh3cevtModuleRT-DSIC-9FSW                   OBJECT IDENTIFIER ::= { hh3cevtModuleRouterType 211 } -- 9-Port 10M/100M Ethernet L2 Switch Module(RJ45)
hh3cevtModuleRT-DSIC-9FSWP                  OBJECT IDENTIFIER ::= { hh3cevtModuleRouterType 212 } -- 9-Port 10M/100M Ethernet L2 Switch Module(RJ45,WITH POE)
hh3cevtModuleRT-SIC-1VE1                    OBJECT IDENTIFIER ::= { hh3cevtModuleRouterType 213 } -- 1-Port Voice E1 SIC Interface Module
hh3cevtModuleRT-SIC-1VT1                    OBJECT IDENTIFIER ::= { hh3cevtModuleRouterType 214 } -- 1-Port Voice T1 SIC Interface Module
hh3cevtModuleRT-VCPM                        OBJECT IDENTIFIER ::= { hh3cevtModuleRouterType 215 } -- Voice Co-Processing Module
hh3cevtModuleRT-VPM                         OBJECT IDENTIFIER ::= { hh3cevtModuleRouterType 216 } -- 32-Channels Voice Processing Module
hh3cevtModuleRT-VPMA                        OBJECT IDENTIFIER ::= { hh3cevtModuleRouterType 217 } -- 16-Channels Voice Processing Module
hh3cevtModuleRT-VPMB                        OBJECT IDENTIFIER ::= { hh3cevtModuleRouterType 218 } -- 8-Channels Voice Processing Module
hh3cevtModuleRT-VPMC                        OBJECT IDENTIFIER ::= { hh3cevtModuleRouterType 219 } -- 24-Channels Voice Processing Module
hh3cevtModuleRt-fe18-75                     OBJECT IDENTIFIER ::= { hh3cevtModuleRouterType 220 } -- 8 Port FE1(75 O) module
hh3cevtModuleRt-fe18-120                    OBJECT IDENTIFIER ::= { hh3cevtModuleRouterType 221 } -- 8 Port FE1(120 O) module
hh3cevtModuleRt-ft18                        OBJECT IDENTIFIER ::= { hh3cevtModuleRouterType 222 } -- 8 Port FT1 module
hh3cevtModuleRt-CF                          OBJECT IDENTIFIER ::= { hh3cevtModuleRouterType 223 } -- Compact Flash Card
hh3cevtModuleRt-bsv2-v2                     OBJECT IDENTIFIER ::= { hh3cevtModuleRouterType 224 } -- 2 Port BSV Version 2
hh3cevtModuleRt-e1vi1-v2                    OBJECT IDENTIFIER ::= { hh3cevtModuleRouterType 225 } -- E1VI Version 2
hh3cevtModuleRt-e1vi2                       OBJECT IDENTIFIER ::= { hh3cevtModuleRouterType 226 } -- 2 Port E1VI
hh3cevtModuleRt-t1vi1-v2                    OBJECT IDENTIFIER ::= { hh3cevtModuleRouterType 227 } -- T1VI Version 2
hh3cevtModuleRt-t1vi2                       OBJECT IDENTIFIER ::= { hh3cevtModuleRouterType 228 } -- 2 Port T1VI
hh3cevtModuleRt-osm                         OBJECT IDENTIFIER ::= { hh3cevtModuleRouterType 229 } -- Open Service Module
hh3cevtModuleRt-sd707                       OBJECT IDENTIFIER ::= { hh3cevtModuleRouterType 230 } -- Encryption Accelerator
hh3cevtModuleRt-dm-epri                     OBJECT IDENTIFIER ::= { hh3cevtModuleRouterType 231 } -- E1 Pri Digital Modem
hh3cevtModuleRt-dm-tpri                     OBJECT IDENTIFIER ::= { hh3cevtModuleRouterType 232 } -- T1 Pri Digital Modem
hh3cevtModuleRt-ERPU-H                      OBJECT IDENTIFIER ::= { hh3cevtModuleRouterType 233 } -- Enhanced route processing unit with only one optic GE interface
hh3cevtModuleRT-SIC-1BSV                    OBJECT IDENTIFIER ::= { hh3cevtModuleRouterType 234 } -- 1-Port Bri S/T VoiceInterface SIC Module
hh3cevtModuleRT-SIC-2BSV                    OBJECT IDENTIFIER ::= { hh3cevtModuleRouterType 235 } -- 2-Port Bri S/T VoiceInterface SIC Module
hh3cevtModuleRt-gbe8                        OBJECT IDENTIFIER ::= { hh3cevtModuleRouterType 236 } -- 8-Port Gigabit Ethernet interface card
hh3cevtModuleRt-gbe4                        OBJECT IDENTIFIER ::= { hh3cevtModuleRouterType 237 } -- 4-Port Gigabit Ethernet interface card
hh3cevtModuleRt-cpos2-v2                    OBJECT IDENTIFIER ::= { hh3cevtModuleRouterType 238 } -- 2-Port Channelized Low speed POS interface card
hh3cevtModuleRt-cpos1-v2                    OBJECT IDENTIFIER ::= { hh3cevtModuleRouterType 239 } -- 1-Port Channelized Low speed POS interface card
hh3cevtModuleRt-oap                         OBJECT IDENTIFIER ::= { hh3cevtModuleRouterType 240 } -- Open Application Platform
hh3cevtModuleRT-48FSWP                      OBJECT IDENTIFIER ::= { hh3cevtModuleRouterType 241 } -- 46-Port 10M/100M(With PoE) and 2-Port 1000BASE-T(With PoE) Ethernet L2 Switch Module
hh3cevtModuleRT-48FSW                       OBJECT IDENTIFIER ::= { hh3cevtModuleRouterType 242 } -- 46-Port 10M/100M and 2-Port 1000BASE-T Ethernet L2 Switch Module
hh3cevtModuleRT-ASM                         OBJECT IDENTIFIER ::= { hh3cevtModuleRouterType 243 } -- Anti-virus Security Module
hh3cevtModuleRT-SIC-1FEF                    OBJECT IDENTIFIER ::= { hh3cevtModuleRouterType 244 } -- 1-Port 100M SFP Interface SIC Module
hh3cevtModuleRT-XMIM-24FSW                  OBJECT IDENTIFIER ::= { hh3cevtModuleRouterType 245 } -- 24-Port 10M/100MBASE-TX Ethernet L2 Switch Interface XMIM-Module
hh3cevtModuleRT-WLAN-AG-1RADIO              OBJECT IDENTIFIER ::= { hh3cevtModuleRouterType 246 } -- Mini PCI Interface 802.11ag Radio Frequency Adapter Card
hh3cevtModuleRT-1CE3                        OBJECT IDENTIFIER ::= { hh3cevtModuleRouterType 247 } -- 1-port E3/CE3/FE3 Compatible Interface Module,(M)
hh3cevtModuleRT-XMIM-16FSW                  OBJECT IDENTIFIER ::= { hh3cevtModuleRouterType 248 } -- 16-Port 10M/100MBASE-TX Ethernet L2 Switch Interface XMIM-Module
hh3cevtModuleRT-OAPS                        OBJECT IDENTIFIER ::= { hh3cevtModuleRouterType 249 } -- Open Application System-Smart
hh3cevtModuleRT-NAM                         OBJECT IDENTIFIER ::= { hh3cevtModuleRouterType 250 } -- Network Analysis Module
hh3cevtModuleRT-RPE-X1                      OBJECT IDENTIFIER ::= { hh3cevtModuleRouterType 251 } -- Route Processing Engine
hh3cevtModuleRT-FIP-100                     OBJECT IDENTIFIER ::= { hh3cevtModuleRouterType 252 } -- Flexible Interface Platform-100
hh3cevtModuleRT-FIP-200                     OBJECT IDENTIFIER ::= { hh3cevtModuleRouterType 253 } -- Flexible Interface Platform-200
hh3cevtModuleRT-SIC-8AS                     OBJECT IDENTIFIER ::= { hh3cevtModuleRouterType 254 } -- 8-Port Asynchronous Serial
hh3cevtModuleRT-WAAM                        OBJECT IDENTIFIER ::= { hh3cevtModuleRouterType 255 } -- WAN Application Acceleration Module
hh3cevtModuleRt-msp4p-OC3c                  OBJECT IDENTIFIER ::= { hh3cevtModuleRouterType 256 } -- 4 Port Multi-Speed POS Interface Module (OC-3c Mode)
hh3cevtModuleRt-1pos-oc48                   OBJECT IDENTIFIER ::= { hh3cevtModuleRouterType 257 } -- 1 Port Super-Speed POS Interface Card
hh3cevtModuleRt-xgbe                        OBJECT IDENTIFIER ::= { hh3cevtModuleRouterType 258 } -- 1-Port 10GBASE-R/W Ethernet Optical Interface Card
hh3cevtModuleRT-EADM                        OBJECT IDENTIFIER ::= { hh3cevtModuleRouterType 259 } -- EAD Integrated Module
hh3cevtModuleRT-VCM                         OBJECT IDENTIFIER ::= { hh3cevtModuleRouterType 260 } -- Voice Convergence Module
hh3cevtModuleRT-SIC-2FXS1FXO                OBJECT IDENTIFIER ::= { hh3cevtModuleRouterType 261 } -- 2FXS+1FXO Interface SIC-Module
hh3cevtModuleRT-8FXS8FXO                    OBJECT IDENTIFIER ::= { hh3cevtModuleRouterType 262 } -- 8FXS+8FXO Interface Module
hh3cevtModuleRT-16FXS                       OBJECT IDENTIFIER ::= { hh3cevtModuleRouterType 263 } -- 16-port FXS Interface Module
hh3cevtModuleRT-OAPS-ICM                    OBJECT IDENTIFIER ::= { hh3cevtModuleRouterType 264 } -- OAPS Information Communication Module
hh3cevtModuleRT-OAP-ICM                     OBJECT IDENTIFIER ::= { hh3cevtModuleRouterType 265 } -- OAP Information Communication Module
hh3cevtModuleRT-8fe                         OBJECT IDENTIFIER ::= { hh3cevtModuleRouterType 266 } -- 8-Port 100M Ethernet Electrical Interface Module
hh3cevtModuleRT-4gbp                        OBJECT IDENTIFIER ::= { hh3cevtModuleRouterType 267 } -- 4-Port GigaBit Ethernet Optical Interface Module(SFP)
hh3cevtModuleRT-MPU-G2                      OBJECT IDENTIFIER ::= { hh3cevtModuleRouterType 268 } -- Main Processor Unit
hh3cevtModuleRT-OAPS-OCE                    OBJECT IDENTIFIER ::= { hh3cevtModuleRouterType 269 } -- OAPS Office Communication Engine
hh3cevtModuleRT-OAP-OCE                     OBJECT IDENTIFIER ::= { hh3cevtModuleRouterType 270 } -- OAP Office Communication Engine
hh3cevtModuleRT-OAPS-ICE                    OBJECT IDENTIFIER ::= { hh3cevtModuleRouterType 271 } -- OAPS Information Communication Engine
hh3cevtModuleRT-OAP-ICE                     OBJECT IDENTIFIER ::= { hh3cevtModuleRouterType 272 } -- OAP Information Communication Module
hh3cevtModuleRT-SIC-16AS                    OBJECT IDENTIFIER ::= { hh3cevtModuleRouterType 273 } -- 16-Port Asynchronous Serial
hh3cevtModuleRT-SPE-FWM                     OBJECT IDENTIFIER ::= { hh3cevtModuleRouterType 274 } -- Gigabit Firewall Module
hh3cevtModuleRT-cls2p                       OBJECT IDENTIFIER ::= { hh3cevtModuleRouterType 275 } -- 2 Port Channelized 155M POS to E3/T3 Interface Module
hh3cevtModuleRT-cls1p                       OBJECT IDENTIFIER ::= { hh3cevtModuleRouterType 276 } -- 1 Port Channelized 155M POS to E3/T3 Interface Module
hh3cevtModuleRT-SIC-2E1-F                   OBJECT IDENTIFIER ::= { hh3cevtModuleRouterType 277 } -- 2-Port Fractional E1 Interface SIC-Module
hh3cevtModuleRT-SIC-1E1-F-V2                OBJECT IDENTIFIER ::= { hh3cevtModuleRouterType 278 } -- 1-Port Fractional E1 Interface SIC-Module
hh3cevtModuleRT-MCU                         OBJECT IDENTIFIER ::= { hh3cevtModuleRouterType 279 } -- Main Control Unit
hh3cevtModuleRT-ACU                         OBJECT IDENTIFIER ::= { hh3cevtModuleRouterType 280 } -- Access Control Unit
hh3cevtModuleRT-1ATM-OC3                    OBJECT IDENTIFIER ::= { hh3cevtModuleRouterType 281 } -- 1-Port Asynchronous Transfer Mode OC3 Board
hh3cevtModuleRT-RSE-X1                      OBJECT IDENTIFIER ::= { hh3cevtModuleRouterType 282 } -- Main Processing Unit With XAUI Switch
hh3cevtModuleRT-FIP-210                     OBJECT IDENTIFIER ::= { hh3cevtModuleRouterType 283 } -- Multi-core CPU Line Processing Board with 2 Combo GE Ports
hh3cevtModuleRT-1expa                       OBJECT IDENTIFIER ::= { hh3cevtModuleRouterType 284 } -- 1 Port Ten Gigabit Interface Module
hh3cevtModuleRT-WLAN-SIC-N-1RADIO           OBJECT IDENTIFIER ::= { hh3cevtModuleRouterType 285 } -- 1 wlan-radio 802.11n sic Interface Board
hh3cevtModuleRT-WLAN-SIC-BG-1RADIO          OBJECT IDENTIFIER ::= { hh3cevtModuleRouterType 286 } -- 1 wlan-radio 802.11b/g sic Interface Board
hh3cevtModuleRT-al2p                        OBJECT IDENTIFIER ::= { hh3cevtModuleRouterType 287 } -- 2 Port 155M ATM Interface Module
hh3cevtModuleRT-msp2p-OC3c                  OBJECT IDENTIFIER ::= { hh3cevtModuleRouterType 288 } -- 2-Port Multi-speed POS Interface Module (OC-3c Mode)
hh3cevtModuleRT-8gbp                        OBJECT IDENTIFIER ::= { hh3cevtModuleRouterType 289 } -- 8-Port GigaBit Ethernet Optical Interface Module(SFP)
hh3cevtModuleRT-SIC-EPON                    OBJECT IDENTIFIER ::= { hh3cevtModuleRouterType 290 } -- 1-Port Ethernet Passive Optical Network SIC Card(SFF)
hh3cevtModuleRT-SIC-3G-GSM-H3               OBJECT IDENTIFIER ::= { hh3cevtModuleRouterType 291 } -- 3G Wireless WAN Interface SIC Module Supporting GPRS/EDGE/UMTS/HSDPA
hh3cevtModuleRT-msp2p-OC12c                 OBJECT IDENTIFIER ::= { hh3cevtModuleRouterType 292 } -- 2-Port Multi-speed POS Interface Module (OC-12c Mode)
hh3cevtModuleRt-msp4p-OC12c                 OBJECT IDENTIFIER ::= { hh3cevtModuleRouterType 293 } -- 4-Port Multi-Speed POS Interface Module (OC-12c Mode)
hh3cevtModuleRt-al1p                        OBJECT IDENTIFIER ::= { hh3cevtModuleRouterType 294 } -- 1-Port 155M ATM Interface Module
hh3cevtModuleRt-OAP-100                     OBJECT IDENTIFIER ::= { hh3cevtModuleRouterType 295 } -- Open Application Platform Module
hh3cevtModuleRt-FIP-110                     OBJECT IDENTIFIER ::= { hh3cevtModuleRouterType 296 } -- Flexible Interface Platform-110
hh3cevtModuleRt-OSM-SSM                     OBJECT IDENTIFIER ::= { hh3cevtModuleRouterType 297 } -- OSM Security Services Module
hh3cevtModuleRt-OAP-SSM                     OBJECT IDENTIFIER ::= { hh3cevtModuleRouterType 298 } -- OAP Security Services Module
hh3cevtModuleRt-rs2p                        OBJECT IDENTIFIER ::= { hh3cevtModuleRouterType 299 } -- 2-Port OC-48c/STM-16c RPR Interface Module
hh3cevtModuleRt-SAP-48GBE                   OBJECT IDENTIFIER ::= { hh3cevtModuleRouterType 300 } -- 48-Port 1000Base-T Gigabit Ethernet Interface Module
hh3cevtModuleRt-SAP-48GBP                   OBJECT IDENTIFIER ::= { hh3cevtModuleRouterType 301 } -- 48-Port 1000BASE Ethernet Optical Interface Module
hh3cevtModuleRt-SAP-24GBP                   OBJECT IDENTIFIER ::= { hh3cevtModuleRouterType 302 } -- 24-Port 1000BASE Ethernet Optical Interface Module
hh3cevtModuleRt-SPE-SSL                     OBJECT IDENTIFIER ::= { hh3cevtModuleRouterType 303 } -- SSL VPN Module
hh3cevtModuleRt-SIC-AUDIO                   OBJECT IDENTIFIER ::= { hh3cevtModuleRouterType 304 } -- MOH and PAGE Interface SIC Module Supporting MOH/PAGE/DOOR RELAY
hh3cevtModuleRt-FIC-1E1POS-H3               OBJECT IDENTIFIER ::= { hh3cevtModuleRouterType 305 } -- 1-Port E1 POS Interface FIC Module
hh3cevtModuleRt-DSIC-4FXS1FXO               OBJECT IDENTIFIER ::= { hh3cevtModuleRouterType 306 } -- 4FXS+1FXO Interface DSIC-Module
hh3cevtModuleRt-FIC-CPOS                    OBJECT IDENTIFIER ::= { hh3cevtModuleRouterType 307 } -- 1-Port CPOS Interface Module
hh3cevtModuleRt-DSIC-1SHDSL-8W              OBJECT IDENTIFIER ::= { hh3cevtModuleRouterType 308 } -- 1-Port 8 Wire SHDSL Interface DSIC Module
hh3cevtModuleRt-SIC-3G-TD                   OBJECT IDENTIFIER ::= { hh3cevtModuleRouterType 309 } -- 1 Port TD-Cellular Interface SIC-Module
hh3cevtModuleRt-SIC-3G-CDMA                 OBJECT IDENTIFIER ::= { hh3cevtModuleRouterType 310 } -- 1 Port CDMA-Cellular Interface SIC-Module
hh3cevtModuleRt-SIC-3G-HSPA                 OBJECT IDENTIFIER ::= { hh3cevtModuleRouterType 311 } -- 1 Port HSPA-Cellular Interface SIC-Module
hh3cevtModuleRt-FIC-OAP-V2                  OBJECT IDENTIFIER ::= { hh3cevtModuleRouterType 312 } -- Open Application Platform V2 FIC Module
hh3cevtModuleRt-MIM-OAP-V2                  OBJECT IDENTIFIER ::= { hh3cevtModuleRouterType 313 } -- Open Application Platform V2 MIM Module
hh3cevtModuleRt-MIM-OAPS-V2                 OBJECT IDENTIFIER ::= { hh3cevtModuleRouterType 314 } -- Open Application System-Smart V2 MIM Module
hh3cevtModuleRt-HMIM-1CT3                   OBJECT IDENTIFIER ::= { hh3cevtModuleRouterType 315 } -- 1 Port Channelized T3 Interface HMIM Module
hh3cevtModuleRt-HMIM-1CE3                   OBJECT IDENTIFIER ::= { hh3cevtModuleRouterType 316 } -- 1 Port Channelized E3 Interface HMIM Module
hh3cevtModuleRt-HMIM-1POS                   OBJECT IDENTIFIER ::= { hh3cevtModuleRouterType 317 } -- 1 Port POS Interface HMIM Module
hh3cevtModuleRt-HMIM-2SAE                   OBJECT IDENTIFIER ::= { hh3cevtModuleRouterType 318 } -- 2 Port SAE Interface HMIM Module
hh3cevtModuleRt-HMIM-4SAE                   OBJECT IDENTIFIER ::= { hh3cevtModuleRouterType 319 } -- 4 Port SAE Interface HMIM Module
hh3cevtModuleRt-HMIM-8SAE                   OBJECT IDENTIFIER ::= { hh3cevtModuleRouterType 320 } -- 8 Port SAE Interface HMIM Module
hh3cevtModuleRt-HMIM-8ASE                   OBJECT IDENTIFIER ::= { hh3cevtModuleRouterType 321 } -- 8 Port ASE Interface HMIM Module
hh3cevtModuleRt-HMIM-16ASE                  OBJECT IDENTIFIER ::= { hh3cevtModuleRouterType 322 } -- 16 Port ASE Interface HMIM Module
hh3cevtModuleRt-HMIM-1E1                    OBJECT IDENTIFIER ::= { hh3cevtModuleRouterType 323 } -- 1 Port E1 Interface HMIM Module
hh3cevtModuleRt-HMIM-2E1                    OBJECT IDENTIFIER ::= { hh3cevtModuleRouterType 324 } -- 2 Port E1 Interface HMIM Module
hh3cevtModuleRt-HMIM-4E1                    OBJECT IDENTIFIER ::= { hh3cevtModuleRouterType 325 } -- 4 Port E1 Interface HMIM Module
hh3cevtModuleRt-HMIM-8E1-75                 OBJECT IDENTIFIER ::= { hh3cevtModuleRouterType 326 } -- 8 Port E1(75 o) Interface HMIM Module
hh3cevtModuleRt-HMIM-1E1-F                  OBJECT IDENTIFIER ::= { hh3cevtModuleRouterType 327 } -- 1 Port E1-F Interface HMIM Module
hh3cevtModuleRt-HMIM-2E1-F                  OBJECT IDENTIFIER ::= { hh3cevtModuleRouterType 328 } -- 2 Port E1-F Interface HMIM Module
hh3cevtModuleRt-HMIM-4E1-F                  OBJECT IDENTIFIER ::= { hh3cevtModuleRouterType 329 } -- 4 Port E1-F Interface HMIM Module
hh3cevtModuleRt-HMIM-8E1-F-75               OBJECT IDENTIFIER ::= { hh3cevtModuleRouterType 330 } -- 8 Port E1-F(75 o) Interface HMIM Module
hh3cevtModuleRt-HMIM-6AM                    OBJECT IDENTIFIER ::= { hh3cevtModuleRouterType 331 } -- 6 Port AM Interface HMIM Module
hh3cevtModuleRt-HMIM-6FCM                   OBJECT IDENTIFIER ::= { hh3cevtModuleRouterType 332 } -- 6 Port FCM Interface HMIM Module
hh3cevtModuleRt-HMIM-2T1                    OBJECT IDENTIFIER ::= { hh3cevtModuleRouterType 333 } -- 2 Port T1 Interface HMIM Module
hh3cevtModuleRt-HMIM-4T1-F                  OBJECT IDENTIFIER ::= { hh3cevtModuleRouterType 334 } -- 4 Port T1-F Interface HMIM Module
hh3cevtModuleRt-HMIM-8T1                    OBJECT IDENTIFIER ::= { hh3cevtModuleRouterType 335 } -- 8 Port T1 Interface HMIM Module
hh3cevtModuleRt-HMIM-8T1-F                  OBJECT IDENTIFIER ::= { hh3cevtModuleRouterType 336 } -- 8 Port T1-F Interface HMIM Module
hh3cevtModuleRt-HMIM-1VE1                   OBJECT IDENTIFIER ::= { hh3cevtModuleRouterType 337 } -- 1 Port Voice E1 Interface HMIM Module
hh3cevtModuleRt-HMIM-1VT1                   OBJECT IDENTIFIER ::= { hh3cevtModuleRouterType 338 } -- 1 Port Voice T1 Interface HMIM Module
hh3cevtModuleRt-HMIM-2VE1                   OBJECT IDENTIFIER ::= { hh3cevtModuleRouterType 339 } -- 2 Port Voice E1 Interface HMIM Module
hh3cevtModuleRt-HMIM-2VT1                   OBJECT IDENTIFIER ::= { hh3cevtModuleRouterType 340 } -- 2 Port Voice T1 Interface HMIM Module
hh3cevtModuleRt-HMIM-8FXS8FXO               OBJECT IDENTIFIER ::= { hh3cevtModuleRouterType 341 } -- 8FXS + 8FXO Interface HMIM Module
hh3cevtModuleRt-HMIM-16FXS                  OBJECT IDENTIFIER ::= { hh3cevtModuleRouterType 342 } -- 16 Port FXS Interface HMIM Module
hh3cevtModuleRt-HMIM-4FXS                   OBJECT IDENTIFIER ::= { hh3cevtModuleRouterType 343 } -- 4 Port FXS Interface HMIM Module
hh3cevtModuleRt-HMIM-4FXO                   OBJECT IDENTIFIER ::= { hh3cevtModuleRouterType 344 } -- 4 Port FXO Interface HMIM Module
hh3cevtModuleRt-HMIM-4EM                    OBJECT IDENTIFIER ::= { hh3cevtModuleRouterType 345 } -- 4 Port E&M Interface HMIM Module
hh3cevtModuleRt-HMIM-4BSV                   OBJECT IDENTIFIER ::= { hh3cevtModuleRouterType 346 } -- 4 Port Bri S/T Voice Interface HMIM Module
hh3cevtModuleRt-SIC-CNDE                    OBJECT IDENTIFIER ::= { hh3cevtModuleRouterType 347 } -- CNDE Crypto Engine SIC-Module
hh3cevtModuleRt-ESM-CNDE                    OBJECT IDENTIFIER ::= { hh3cevtModuleRouterType 348 } -- CNDE Crypto Engine ESM-Module
hh3cevtModuleRt-ESM-CNDE-M                  OBJECT IDENTIFIER ::= { hh3cevtModuleRouterType 349 } -- CNDE Crypto Engine MiniPCI-ESM-Module
hh3cevtModuleRt-SR6602-X1                   OBJECT IDENTIFIER ::= { hh3cevtModuleRouterType 350 } -- 2U Router Host(4GE Combo/2 HIM slot)
hh3cevtModuleRt-SR6602-X2                   OBJECT IDENTIFIER ::= { hh3cevtModuleRouterType 351 } -- 2U Router Host(4GE Combo/2 10G SFP+/2 HIM slot)
hh3cevtModuleRt-MCP-X1                      OBJECT IDENTIFIER ::= { hh3cevtModuleRouterType 352 } -- Main Controller and Processor X1
hh3cevtModuleRt-MCP-X2                      OBJECT IDENTIFIER ::= { hh3cevtModuleRouterType 353 } -- Main Controller and Processor X2
hh3cevtModuleRt-FIP-10                      OBJECT IDENTIFIER ::= { hh3cevtModuleRouterType 354 } -- Flexible Interface Platform 10
hh3cevtModuleRt-FIP-20                      OBJECT IDENTIFIER ::= { hh3cevtModuleRouterType 355 } -- Flexible Interface Platform 20
hh3cevtModuleRt-RSE-X2                      OBJECT IDENTIFIER ::= { hh3cevtModuleRouterType 356 } -- Route Switch Engine X2
hh3cevtModuleRt-FIP-600                     OBJECT IDENTIFIER ::= { hh3cevtModuleRouterType 357 } -- Flexible Interface Platform 600
hh3cevtModuleRt-SAP-4EXP                    OBJECT IDENTIFIER ::= { hh3cevtModuleRouterType 358 } -- 4-Port 10GBASE-R/W Ethernet Optical Interface Module(SFP+)
hh3cevtModuleRt-SFE-X1                      OBJECT IDENTIFIER ::= { hh3cevtModuleRouterType 359 } -- Switch Fabric Engine X1
hh3cevtModuleRt-SFE-A1                      OBJECT IDENTIFIER ::= { hh3cevtModuleRouterType 360 } -- Switch Fabric Engine A1
hh3cevtModuleRt-HMIM-24GSW                  OBJECT IDENTIFIER ::= { hh3cevtModuleRouterType 361 } -- 24-Port 10M/100M/1000MBASE-T Ethernet L2 Switch Interface HMIM_Module
hh3cevtModuleRt-HMIM-24GSWP                 OBJECT IDENTIFIER ::= { hh3cevtModuleRouterType 362 } -- 24-Port 10M/100M/1000MBASE-T(WITH POE) Ethernet L2 Switch Interface HMIM_Module
hh3cevtModuleRt-MPU100                      OBJECT IDENTIFIER ::= { hh3cevtModuleRouterType 363 } -- Main Processing Unit 100
hh3cevtModuleRt-SPU100                      OBJECT IDENTIFIER ::= { hh3cevtModuleRouterType 364 } -- Service Processing Unit 100
hh3cevtModuleRt-SPU200                      OBJECT IDENTIFIER ::= { hh3cevtModuleRouterType 365 } -- Service Processing Unit 200
hh3cevtModuleRt-WLAN-N-1RADIO               OBJECT IDENTIFIER ::= { hh3cevtModuleRouterType 366 } -- Mini PCI Interface 802.11n Radio Frequency Adapter Card
hh3cevtModuleRt-3G-CDMA                     OBJECT IDENTIFIER ::= { hh3cevtModuleRouterType 367 } -- 1 Port CDMA-Cellular Interface Adapter Card
hh3cevtModuleRt-3G-WCDMA                    OBJECT IDENTIFIER ::= { hh3cevtModuleRouterType 368 } -- 1 Port WCDMA-Cellular Interface Adapter Card
hh3cevtModuleRt-3G-HSPAPLUS                 OBJECT IDENTIFIER ::= { hh3cevtModuleRouterType 369 } -- 1 Port HSPA+-Cellular Interface Adapter Card
hh3cevtModuleRt-VPM-128                     OBJECT IDENTIFIER ::= { hh3cevtModuleRouterType 370 } -- 128-VoiceChannel VPM Module
hh3cevtModuleRt-VPM-256                     OBJECT IDENTIFIER ::= { hh3cevtModuleRouterType 371 } -- 256-VoiceChannel VPM Module
hh3cevtModuleRt-VPM-512                     OBJECT IDENTIFIER ::= { hh3cevtModuleRouterType 372 } -- 512-VoiceChannel VPM Module
hh3cevtModuleRt-HMIM-8GEE                   OBJECT IDENTIFIER ::= { hh3cevtModuleRouterType 373 } -- 8-port copper GigabitEthernet HMIM Module
hh3cevtModuleRt-HMIM-4GEE                   OBJECT IDENTIFIER ::= { hh3cevtModuleRouterType 374 } -- 4-port copper GigabitEthernet HMIM Module
hh3cevtModuleRt-HMIM-2GEE                   OBJECT IDENTIFIER ::= { hh3cevtModuleRouterType 375 } -- 2-port copper GigabitEthernet HMIM Module
hh3cevtModuleRt-HMIM-8GEF                   OBJECT IDENTIFIER ::= { hh3cevtModuleRouterType 376 } -- 8-port fiber GigabitEthernet HMIM Module
hh3cevtModuleRt-HMIM-4GEF                   OBJECT IDENTIFIER ::= { hh3cevtModuleRouterType 377 } -- 4-port fiber GigabitEthernet HMIM Module
hh3cevtModuleRt-HMIM-2GEF                   OBJECT IDENTIFIER ::= { hh3cevtModuleRouterType 378 } -- 2-port fiber GigabitEthernet HMIM Module
hh3cevtModuleRt-SPU300                      OBJECT IDENTIFIER ::= { hh3cevtModuleRouterType 379 } -- Service Processing Unit 300
hh3cevtModuleRt-HMIM-1CPOS                  OBJECT IDENTIFIER ::= { hh3cevtModuleRouterType 380 } -- 1-port CPOS Interface HMIM Module
hh3cevtModuleRt-HMIM-2CPOS                  OBJECT IDENTIFIER ::= { hh3cevtModuleRouterType 381 } -- 2-port CPOS Interface HMIM Module
hh3cevtModuleRt-SPU100-5080                 OBJECT IDENTIFIER ::= { hh3cevtModuleRouterType 382 } -- Service Processing Unit 100
hh3cevtModuleRt-SPU200-5080                 OBJECT IDENTIFIER ::= { hh3cevtModuleRouterType 383 } -- Service Processing Unit 200
hh3cevtModuleRt-SPU300-5080                 OBJECT IDENTIFIER ::= { hh3cevtModuleRouterType 384 } -- Service Processing Unit 300
hh3cevtModuleRt-4G-LTE-Verizon              OBJECT IDENTIFIER ::= { hh3cevtModuleRouterType 385 } -- 1 Port 4G-LTE-Verizon-Cellular Interface Adapter Card
hh3cevtModuleRt-4G-LTE-Global               OBJECT IDENTIFIER ::= { hh3cevtModuleRouterType 386 } -- 1 Port 4G-LTE-Global-Cellular Interface Adapter Card
hh3cevtModuleRt-HMIM-1ATM-OC3               OBJECT IDENTIFIER ::= { hh3cevtModuleRouterType 387 } -- 1-Port OC3 ATM MM/SM/SML HMIM Module
hh3cevtModuleRt-SIC-1E1-V2                  OBJECT IDENTIFIER ::= { hh3cevtModuleRouterType 388 } -- 1-Port E1/CE1/PRI Interface SIC Module
hh3cevtModuleRt-FIP-300                     OBJECT IDENTIFIER ::= { hh3cevtModuleRouterType 389 } -- Flexible Interface Platform 300
hh3cevtModuleRt-FIP-310                     OBJECT IDENTIFIER ::= { hh3cevtModuleRouterType 390 } -- Flexible Interface Platform 310
hh3cevtModuleRt-TS8P                        OBJECT IDENTIFIER ::= { hh3cevtModuleRouterType 391 } -- 8-Port OC-3c/OC-12c POS or Gigabit Ethernet Optical Interface Module(SFP)
hh3cevtModuleRt-4G4P                        OBJECT IDENTIFIER ::= { hh3cevtModuleRouterType 392 } -- 4-Port Gigabit Ethernet Optical Interface and 4-Port OC-3c POS Interface Module(SFP)
hh3cevtModuleRt-SIC-4G-LTE-V                OBJECT IDENTIFIER ::= { hh3cevtModuleRouterType 393 } -- 1 Port 4G-LTE-Verizon-Cellular Interface SIC-Module
hh3cevtModuleRt-SIC-4G-LTE-A                OBJECT IDENTIFIER ::= { hh3cevtModuleRouterType 394 } -- 1 Port 4G-LTE-AT&T-Cellular Interface SIC-Module
hh3cevtModuleRt-SIC-4G-LTE-G                OBJECT IDENTIFIER ::= { hh3cevtModuleRouterType 395 } -- 1 Port 4G-LTE-Global-Cellular Interface SIC-Module
hh3cevtModuleRt-SIC-2SAE                    OBJECT IDENTIFIER ::= { hh3cevtModuleRouterType 396 } -- 2 Port SAE Interface SIC Module
hh3cevtModuleRt-SIC-4SAE                    OBJECT IDENTIFIER ::= { hh3cevtModuleRouterType 397 } -- 4 Port SAE Interface SIC Module
hh3cevtModuleRt-HMIM-OAP                    OBJECT IDENTIFIER ::= { hh3cevtModuleRouterType 398 } -- Open Application Platform HMIM Interface Module with Cloud Virtualization Kernel
hh3cevtModuleRt-HMIM-8GSW                   OBJECT IDENTIFIER ::= { hh3cevtModuleRouterType 399 } -- 8-Port 10M/100M/1000MBASE-T Ethernet L2 Switch Interface HMIM-Module,including 2 Combo Ports

--
-- 400 to 599 reserved for security routers
--
hh3cevtModuleRt-IPU                         OBJECT IDENTIFIER ::= { hh3cevtModuleRouterType 400 } -- IPS Processing Unit
hh3cevtModuleRt-MIM2GEBE-PCIE               OBJECT IDENTIFIER ::= { hh3cevtModuleRouterType 401 } -- 2-port UTM GigabitEthernet Interface Module
hh3cevtModuleRt-HIM12GE-PCIE                OBJECT IDENTIFIER ::= { hh3cevtModuleRouterType 402 } -- 12-port GigabitEthernet Interface Module
hh3cevtModuleRt-HIM2XGE-PCIE                OBJECT IDENTIFIER ::= { hh3cevtModuleRouterType 403 } -- 2-port Ten-GigabitEthernet Interface Module
hh3cevtModuleRt-IPU-T1000-M                 OBJECT IDENTIFIER ::= { hh3cevtModuleRouterType 404 } -- IPS Processing Unit for T1000-M Mainboard Module
hh3cevtModuleRt-IPU-GX4C                    OBJECT IDENTIFIER ::= { hh3cevtModuleRouterType 405 } -- 4 Port Gigabit Fiber Module
hh3cevtModuleRt-IPU-GT4C                    OBJECT IDENTIFIER ::= { hh3cevtModuleRouterType 406 } -- 4 Port 1000BASE-T Module
hh3cevtModuleRt-RPU-IAG2000-A               OBJECT IDENTIFIER ::= { hh3cevtModuleRouterType 407 } -- Intelligence Application Gateway Module
hh3cevtModuleRt-RPU-AFD1000-A               OBJECT IDENTIFIER ::= { hh3cevtModuleRouterType 408 } -- Anomaly Flow Detector Module
hh3cevtModuleRt-RPU-F5000-A                 OBJECT IDENTIFIER ::= { hh3cevtModuleRouterType 409 } -- Advanced Firewall Module
hh3cevtModuleRt-ACG-8800S3-MPU              OBJECT IDENTIFIER ::= { hh3cevtModuleRouterType 410 } -- Main Control Unit,with 24 1000BASE-X/100BASE-FX Optical Ports,including 8 Combo Ports,SFP Req
hh3cevtModuleRt-T5000S3-MPU                 OBJECT IDENTIFIER ::= { hh3cevtModuleRouterType 411 } -- Main Control Unit,with 24 1000BASE-X/100BASE-FX Optical Ports,including 8 Combo Ports,SFP Req
hh3cevtModuleRt-NS21S2MSPB0                 OBJECT IDENTIFIER ::= { hh3cevtModuleRouterType 412 } -- Multi Service Processing Module
hh3cevtModuleRt-NS11S2MSPB0                 OBJECT IDENTIFIER ::= { hh3cevtModuleRouterType 413 } -- Multi Service Processing Module
hh3cevtModuleRt-NSQ1WLAN                    OBJECT IDENTIFIER ::= { hh3cevtModuleRouterType 414 } -- Dual-Band,Multi-Mode 802.11a/b/g Wireless LAN card
hh3cevtModuleRt-NSQ1GP4U0                   OBJECT IDENTIFIER ::= { hh3cevtModuleRouterType 415 } -- 4 Port Gigabit Fiber Module
hh3cevtModuleRt-NSQ1GP8C40                  OBJECT IDENTIFIER ::= { hh3cevtModuleRouterType 416 } -- 12-Port GigabitEthernet Interface Module,with 4 Combo Ports,8 Fiber Ports
hh3cevtModuleRt-NSQ1XS2U0                   OBJECT IDENTIFIER ::= { hh3cevtModuleRouterType 417 } -- 2-Port Ten GigabitEthernet Interface Module
hh3cevtModuleRt-NSQ1G24XS60                 OBJECT IDENTIFIER ::= { hh3cevtModuleRouterType 418 } -- 12-copper 12-fiber and 6-XGE Interface Module
hh3cevtModuleRt-NSQ1TGX4EA0                 OBJECT IDENTIFIER ::= { hh3cevtModuleRouterType 419 } -- 4-XGE Fabric Interface Module
hh3cevtModuleRt-NSQ1FAB08D0                 OBJECT IDENTIFIER ::= { hh3cevtModuleRouterType 420 } -- Switch Module
hh3cevtModuleRt-NSQ1TGS32SF0                OBJECT IDENTIFIER ::= { hh3cevtModuleRouterType 421 } -- 32-XGE Fabric Interface Module
hh3cevtModuleRt-NSQ1QGS4SF0                 OBJECT IDENTIFIER ::= { hh3cevtModuleRouterType 422 } -- 4-XGE Fabric Interface Module
hh3cevtModuleRt-NSQ1GP24TXEA0               OBJECT IDENTIFIER ::= { hh3cevtModuleRouterType 423 } -- 16-GE Fabric,8-GE Combo,2-XGE Interface Module
hh3cevtModuleRt-NSQ1GP48EB0                 OBJECT IDENTIFIER ::= { hh3cevtModuleRouterType 424 } -- 48-GE Fabric Interface Module
hh3cevtModuleRt-NSQ1FWCEA0                  OBJECT IDENTIFIER ::= { hh3cevtModuleRouterType 425 } -- Firewall Module
hh3cevtModuleRt-NSQ1GT48EA0                 OBJECT IDENTIFIER ::= { hh3cevtModuleRouterType 426 } -- 48-GE Copper Interface
hh3cevtModuleRt-NSQ1TGS8EA0                 OBJECT IDENTIFIER ::= { hh3cevtModuleRouterType 427 } -- 8-XGE Fabric Interface
hh3cevtModuleRt-NSQ1FAB04B0                 OBJECT IDENTIFIER ::= { hh3cevtModuleRouterType 428 } -- Switch Module
hh3cevtModuleRt-NSQ1FAB12D0                 OBJECT IDENTIFIER ::= { hh3cevtModuleRouterType 429 } -- Switch Module
hh3cevtModuleRt-NSQ1SUPB0                   OBJECT IDENTIFIER ::= { hh3cevtModuleRouterType 430 } -- Main Control Module
hh3cevtModuleRt-VFW1000                     OBJECT IDENTIFIER ::= { hh3cevtModuleRouterType 431 } -- Virtual Firwall Gateway module over virtual machine
hh3cevtModuleRt-NSQ1CGC2SE0                 OBJECT IDENTIFIER ::= { hh3cevtModuleRouterType 432 } -- 2 Port 100GBASE Ethernet Optical Interface Board(CFP)(SE)
hh3cevtModuleRt-VLB1000                     OBJECT IDENTIFIER ::= { hh3cevtModuleRouterType 433 } -- Virtual LB module over virtual machine
hh3cevtModuleRt-NSQM1GT4PFC                 OBJECT IDENTIFIER ::= { hh3cevtModuleRouterType 434 } -- 4 Port GigabitEthernet Interface
hh3cevtModuleRt-NSQM1FWDFG0                 OBJECT IDENTIFIER ::= { hh3cevtModuleRouterType 435 } -- Firewall Module
hh3cevtModuleRt-NSQM1NATDFGA0               OBJECT IDENTIFIER ::= { hh3cevtModuleRouterType 436 } -- NAT A module
hh3cevtModuleRt-NSQM1NATDFGB0               OBJECT IDENTIFIER ::= { hh3cevtModuleRouterType 437 } -- NAT B module
hh3cevtModuleRt-VFW2000                     OBJECT IDENTIFIER ::= { hh3cevtModuleRouterType 438 } -- Virtual Firwall Gateway module over physical machine
hh3cevtModuleRt-VLB2000                     OBJECT IDENTIFIER ::= { hh3cevtModuleRouterType 439 } -- Virtual LB module ver physical machine
hh3cevtModuleRt-NSQM1IPSDFG0                OBJECT IDENTIFIER ::= { hh3cevtModuleRouterType 440 } -- NSQM1IPSDFG0
hh3cevtModuleRt-NSQM1FWDFGB0                OBJECT IDENTIFIER ::= { hh3cevtModuleRouterType 441 } -- NSQM1FWDFGB0-SecBlade IV
hh3cevtModuleRt-NSQM1FWDFGC0                OBJECT IDENTIFIER ::= { hh3cevtModuleRouterType 442 } -- NSQM1FWDFGC0-SecBlade IV
hh3cevtModuleRt-NSQM1FWDFGA1                OBJECT IDENTIFIER ::= { hh3cevtModuleRouterType 443 } -- NSQM1FWDFGA1-SecBlade IV
hh3cevtModuleRt-NSQM1FWDFGB1                OBJECT IDENTIFIER ::= { hh3cevtModuleRouterType 444 } -- NSQM1FWDFGB1-SecBlade IV
hh3cevtModuleRt-NSQM1FWDFGC1                OBJECT IDENTIFIER ::= { hh3cevtModuleRouterType 445 } -- NSQM1FWDFGC1-SecBlade IV
hh3cevtModuleRt-NSQM1FWDFGD1                OBJECT IDENTIFIER ::= { hh3cevtModuleRouterType 446 } -- NSQM1FWDFGD1-SecBlade IV
hh3cevtModuleRt-NSQM1SUPC0                  OBJECT IDENTIFIER ::= { hh3cevtModuleRouterType 447 } -- SecPath T9000-NSQM1SUPC0
hh3cevtModuleRt-NSQM1TG4FBA                 OBJECT IDENTIFIER ::= { hh3cevtModuleRouterType 448 } -- SecPath F1000-NSQM1TG4FBA
hh3cevtModuleRt-NSQM1GP4FBA                 OBJECT IDENTIFIER ::= { hh3cevtModuleRouterType 449 } -- SecPath F1000-NSQM1GP4FBA
hh3cevtModuleRt-NSQM2MPUC0                  OBJECT IDENTIFIER ::= { hh3cevtModuleRouterType 450 } -- M9008-S FW  NSQM2MPUC0
hh3cevtModuleRt-NSQM2TGS16SF0               OBJECT IDENTIFIER ::= { hh3cevtModuleRouterType 451 } -- M9008-S FW  NSQM2TGS16SF0
hh3cevtModuleRt-NSQM2QGS4SC0                OBJECT IDENTIFIER ::= { hh3cevtModuleRouterType 452 } -- M9008-S FW  NSQM2QGS4SC0
hh3cevtModuleRt-NSQM2GP24TSSC0              OBJECT IDENTIFIER ::= { hh3cevtModuleRouterType 453 } -- M9008-S FW  NSQM2GP24TSSC0
hh3cevtModuleRt-NSQM2FWDSC0                 OBJECT IDENTIFIER ::= { hh3cevtModuleRouterType 454 } -- M9008-S FW  NSQM2FWDSC0
hh3cevtModuleRt-NSQM1ADEDFGA0               OBJECT IDENTIFIER ::= { hh3cevtModuleRouterType 455 } -- NSQM1ADEDFGA0-SecBlade IV ADE A module
hh3cevtModuleRt-NSQM2FWDSCA0                OBJECT IDENTIFIER ::= { hh3cevtModuleRouterType 456 } -- M9000-S FW NSQM2FWDSCA0-SecBlade IV
hh3cevtModuleRt-NSQM1TGS32QSSG0             OBJECT IDENTIFIER ::= { hh3cevtModuleRouterType 457 } -- SecPath M9000-NSQM1TGS32QSSG0
hh3cevtModuleRt-NSQM1GT4PFCA                OBJECT IDENTIFIER ::= { hh3cevtModuleRouterType 458 } -- 4 Port GigabitEthernet Interface Module
hh3cevtModuleRt-NSQM1TG8A                   OBJECT IDENTIFIER ::= { hh3cevtModuleRouterType 459 } -- 8 Port Ten-GigabitEthernet Interface Module
hh3cevtModuleRt-NSQM1QG2A                   OBJECT IDENTIFIER ::= { hh3cevtModuleRouterType 460 } -- 2 Port Forty-GigabitEthernet Interface Module
hh3cevtModuleRt-NSQM1GT8A                   OBJECT IDENTIFIER ::= { hh3cevtModuleRouterType 461 } -- 8-Port Gigabit Ethernet interface Module
hh3cevtModuleRt-NSQM1GP8A                   OBJECT IDENTIFIER ::= { hh3cevtModuleRouterType 462 } -- 8 Port Fabric GigabitEthernet Interface Module
hh3cevtModuleRt-NSQM1MBFE0                  OBJECT IDENTIFIER ::= { hh3cevtModuleRouterType 463 } -- SecPath M9008-S  NSQM1MBFE0
hh3cevtModuleRt-NSQM2MBFD0                  OBJECT IDENTIFIER ::= { hh3cevtModuleRouterType 464 } -- SecPath M9008-S NSQM2MBFD0
hh3cevtModuleRt-NSQM2QG2TG8GP40             OBJECT IDENTIFIER ::= { hh3cevtModuleRouterType 465 } -- SecPath M9008-S  NSQM2QG2TG8GP40
hh3cevtModuleRt-NSQM2QG4GP40                OBJECT IDENTIFIER ::= { hh3cevtModuleRouterType 466 } -- SecPath M9008-S  NSQM2QG4GP40
hh3cevtModuleRt-NSQM2TG16GP40               OBJECT IDENTIFIER ::= { hh3cevtModuleRouterType 467 } -- SecPath M9008-S  NSQM2TG16GP40
hh3cevtModuleRt-NSQM1CGQ20                  OBJECT IDENTIFIER ::= { hh3cevtModuleRouterType 468 } -- SecPath M9008-S  NSQM1CGQ20
hh3cevtModuleRt-NSQM2FWDFG0                 OBJECT IDENTIFIER ::= { hh3cevtModuleRouterType 469 } -- M9000-S FW NSQM2FWDFG0-SecBlade IV
hh3cevtModuleRt-NSQM2TMPUC0                 OBJECT IDENTIFIER ::= { hh3cevtModuleRouterType 470 } -- SecPath T9000-S-NSQM2TMPUC0
hh3cevtModuleRt-NSQM2IPSDSCA0               OBJECT IDENTIFIER ::= { hh3cevtModuleRouterType 471 } -- SecPath T9000-S-NSQM2IPSDSCA0-SecBlade IV
hh3cevtModuleRt-NSQM2AC1400                 OBJECT IDENTIFIER ::= { hh3cevtModuleRouterType 472 } -- SecPath M9000-S-NSQM2AC1400
hh3cevtModuleRt-NSQM2DC1400                 OBJECT IDENTIFIER ::= { hh3cevtModuleRouterType 473 } -- SecPath M9000-S-NSQM2DC1400
hh3cevtModuleRt-NSQM1F1KGM0                 OBJECT IDENTIFIER ::= { hh3cevtModuleRouterType 474} -- F1000 GM Crypto Module
hh3cevtModuleRt-NSQM1F1KGM0-context         OBJECT IDENTIFIER ::= { hh3cevtModuleRouterType 475} -- F1000 GM Crypto Module
hh3cevtModuleRt-NSQM1F5KGM0                 OBJECT IDENTIFIER ::= { hh3cevtModuleRouterType 476} -- F5000 GM Crypto Module
hh3cevtModuleRt-NSQM1F5KGM0-context         OBJECT IDENTIFIER ::= { hh3cevtModuleRouterType 477} -- F5000 GM Crypto Module
hh3cevtModuleRt-NSQM2QG2GP40                OBJECT IDENTIFIER ::= { hh3cevtModuleRouterType 478 } -- SecPath M9000-NSQM2QG2GP40
hh3cevtModuleRt-NSQM2TG8GP40                OBJECT IDENTIFIER ::= { hh3cevtModuleRouterType 479 } -- SecPath M9000-NSQM2TG8GP40

hh3cevtModuleRt-NSQM2ADEDSCA0               OBJECT IDENTIFIER ::= { hh3cevtModuleRouterType 482 } -- M9000-S FW NSQM2ADEDSCA0-SecBlade IV
hh3cevtModuleRt-NSQM2IPSDSCB0               OBJECT IDENTIFIER ::= { hh3cevtModuleRouterType 483 } -- M9000-S FW NSQM2IPSDSCB0-SecBlade IV
hh3cevtModuleRt-NSQM1G4XS4                  OBJECT IDENTIFIER ::= { hh3cevtModuleRouterType 484 } -- 4-GE Fabric,4-XGE Fabric Interface Module
hh3cevtModuleRt-NSUM1GT4PFCA                OBJECT IDENTIFIER ::= { hh3cevtModuleRouterType 485 } -- 4 Port GigabitEthernet Interface Module
hh3cevtModuleRt-NSUM1TG8A                   OBJECT IDENTIFIER ::= { hh3cevtModuleRouterType 486 } -- 8 Port Ten-GigabitEthernet Interface Module
hh3cevtModuleRt-NSUM1QG2A                   OBJECT IDENTIFIER ::= { hh3cevtModuleRouterType 487 } -- 2 Port Forty-GigabitEthernet Interface Module
hh3cevtModuleRt-NSUM1GT8A                   OBJECT IDENTIFIER ::= { hh3cevtModuleRouterType 488 } -- 8-Port Gigabit Ethernet interface Module
hh3cevtModuleRt-NSUM1GP8A                   OBJECT IDENTIFIER ::= { hh3cevtModuleRouterType 489 } -- 8 Port Fabric GigabitEthernet Interface Module

hh3cevtModuleRt-NSQM2MPUD0                  OBJECT IDENTIFIER ::= { hh3cevtModuleRouterType 491 } -- SecPath M9000-S- NSQM2MPUD0
hh3cevtModuleRt-NSQM1GMDSCA1                OBJECT IDENTIFIER ::= { hh3cevtModuleRouterType 492 } -- SecPath M9000-GM- NSQM1GMDSCA1
hh3cevtModuleRt-NSQM1MPULA                  OBJECT IDENTIFIER ::= { hh3cevtModuleRouterType 493} -- SecPath F50X0-D NSQM1MPULA
hh3cevtModuleRt-NSQM1MPULA2                 OBJECT IDENTIFIER ::= { hh3cevtModuleRouterType 494} -- SecPath F5000-AK515 NSQM1MPULA2
hh3cevtModuleRt-NSQM1GT8A2                  OBJECT IDENTIFIER ::= { hh3cevtModuleRouterType 495} -- SecPath F5000-AK515 NSQM1GT8A2
hh3cevtModuleRt-NSQM1GP4TG4A2               OBJECT IDENTIFIER ::= { hh3cevtModuleRouterType 496} -- SecPath F5000-AK515 NSQM1GP4TG4A2
hh3cevtModuleRt-NSQM1GP2TG6A2               OBJECT IDENTIFIER ::= { hh3cevtModuleRouterType 497} -- SecPath F5000-AK515 NSQM1GP2TG6A2
hh3cevtModuleRt-NSQM1TG4FBA7                OBJECT IDENTIFIER ::= { hh3cevtModuleRouterType 498} -- SecPath F1000-AK-NSQM1TG4FBA7

hh3cevtModuleRt-NSQM1F1KGMB                 OBJECT IDENTIFIER ::= { hh3cevtModuleRouterType 499} -- F1000 GM Crypto Module
hh3cevtModuleRt-NSQM1F1KGMC                 OBJECT IDENTIFIER ::= { hh3cevtModuleRouterType 500} -- F1000 GM Crypto Module
hh3cevtModuleRt-NSQM1F5KGMC                 OBJECT IDENTIFIER ::= { hh3cevtModuleRouterType 501} -- F1000 GM Crypto Module
hh3cevtModuleRt-NSQM5SUP08H0                OBJECT IDENTIFIER ::= { hh3cevtModuleRouterType 502 } -- SecPath M9000-E8-NSQM5SUP08H0
hh3cevtModuleRt-NSQM5SUP16C0                OBJECT IDENTIFIER ::= { hh3cevtModuleRouterType 503 } -- SecPath M9000-E16-NSQM5SUP16C0
hh3cevtModuleRt-NS-FWEMPA0                  OBJECT IDENTIFIER ::= { hh3cevtModuleRouterType 504 } -- SecPath M9000-E-NS-FWEMPA0
hh3cevtModuleRt-NSQM5MBSHA0                 OBJECT IDENTIFIER ::= { hh3cevtModuleRouterType 505 } -- SecPath M9000-E-NSQM5MBSHA0
hh3cevtModuleRt-NS-C600-CGQ6A0              OBJECT IDENTIFIER ::= { hh3cevtModuleRouterType 506 } -- SecPath M9000-E-NS-C600-CGQ6A0
hh3cevtModuleRt-NS-C300-CGQ2TG16A0          OBJECT IDENTIFIER ::= { hh3cevtModuleRouterType 507 } -- SecPath M9000-E-NS-C300-CGQ2TG16A0
hh3cevtModuleRt-NS-C300-TG24A0              OBJECT IDENTIFIER ::= { hh3cevtModuleRouterType 508 } -- SecPath M9000-E-NS-C300-TG24A0
hh3cevtModuleRt-NS-C300-QG4TG16A0           OBJECT IDENTIFIER ::= { hh3cevtModuleRouterType 509 } -- SecPath M9000-E-NS-C300-QG4TG16A0
hh3cevtModuleRt-NSQM5FAB08A0                OBJECT IDENTIFIER ::= { hh3cevtModuleRouterType 510 } -- SecPath M9000-E-NSQM5FAB08A0
hh3cevtModuleRt-NSQM5FAB16A0                OBJECT IDENTIFIER ::= { hh3cevtModuleRouterType 511 } -- SecPath M9000-E-NSQM5FAB16A0
hh3cevtModuleRt-NSQM5SL16UA0                OBJECT IDENTIFIER ::= { hh3cevtModuleRouterType 512 } -- SecPath M9000-E-NSQM5SL16UA0
hh3cevtModuleRt-NSQM5SL16LA0                OBJECT IDENTIFIER ::= { hh3cevtModuleRouterType 513 } -- SecPath M9000-E-NSQM5SL16LA0
hh3cevtModuleRt-NSQM2MPU12E0                OBJECT IDENTIFIER ::= { hh3cevtModuleRouterType 514 } -- SecPath M9000-S-NSQM2MPU12E0
hh3cevtModuleRt-NSQM2MBFEA0                 OBJECT IDENTIFIER ::= { hh3cevtModuleRouterType 515 } -- SecPath M9000-S-NSQM2MBFEA0
hh3cevtModuleRt-NSQM2AC2500HD               OBJECT IDENTIFIER ::= { hh3cevtModuleRouterType 516 } -- SecPath M9000-S-NSQM2AC2500HD
hh3cevtModuleRt-NSQM2DC2500                 OBJECT IDENTIFIER ::= { hh3cevtModuleRouterType 517 } -- SecPath M9000-S-NSQM2DC2500
hh3cevtModuleRt-NSQM1HTIMGMG2A              OBJECT IDENTIFIER ::= { hh3cevtModuleRouterType 518 } -- F5080 GM Crypto Module
hh3cevtModuleRt-NSQM1HTIMGMG2B              OBJECT IDENTIFIER ::= { hh3cevtModuleRouterType 519 } -- F5080-D GM Crypto Module
hh3cevtModuleRt-NSQM2V6DSCA0                OBJECT IDENTIFIER ::= { hh3cevtModuleRouterType 520 } -- SecPath M9000-S-6GW-NSQM2V6DSCA0
hh3cevtModuleRt-NSQM1AFC2000GDFGA0          OBJECT IDENTIFIER ::= { hh3cevtModuleRouterType 521 } -- SecPath NSQM1AFC2000GDFGA0
hh3cevtModuleRt-NSQM2AFC2000GDFGA0          OBJECT IDENTIFIER ::= { hh3cevtModuleRouterType 522 } -- SecPath NSQM2AFC2000GDFGA0
hh3cevtModuleRt-NSQM1FWDFGD1-Z              OBJECT IDENTIFIER ::= { hh3cevtModuleRouterType 523 } -- SecPath NSQM1FWDFGD1
hh3cevtModuleRt-NSQM1FAB12D0                OBJECT IDENTIFIER ::= { hh3cevtModuleRouterType 524 } -- SecPath NSQM1FAB12D0
hh3cevtModuleRt-NSQM1MBFEA0                 OBJECT IDENTIFIER ::= { hh3cevtModuleRouterType 525 } -- SecPath NSQM1MBFEA0
hh3cevtModuleRt-NSQM2TG16GP40-Z             OBJECT IDENTIFIER ::= { hh3cevtModuleRouterType 526 } -- SecPath NSQM2TG16GP40
hh3cevtModuleRt-NSQM2QG4GP40-Z              OBJECT IDENTIFIER ::= { hh3cevtModuleRouterType 527 } -- SecPath NSQM2QG4GP40
hh3cevtModuleRt-NSQM1CGQ20-Z                OBJECT IDENTIFIER ::= { hh3cevtModuleRouterType 528 } -- SecPath NSQM1CGQ20
hh3cevtModuleRt-NSQM1TGS32QSSG0-Z           OBJECT IDENTIFIER ::= { hh3cevtModuleRouterType 529 } -- SecPath NSQM1TGS32QSSG0
hh3cevtModuleRt-NSQM1AFC2000GDFGA0-Z        OBJECT IDENTIFIER ::= { hh3cevtModuleRouterType 530 } -- SecPath NSQM1AFC2000GDFGA0
hh3cevtModuleRt-NSQM5AIASKA1                OBJECT IDENTIFIER ::= { hh3cevtModuleRouterType 531 } -- SecPath M9000-AI-E- NSQM5AIASKA1
hh3cevtModuleRt-NSQM1FWEFGA0                OBJECT IDENTIFIER ::= { hh3cevtModuleRouterType 532 } -- SecPath M9000-NSQM1FMEFGA0
hh3cevtModuleRt-NS-ADEEMPA0                 OBJECT IDENTIFIER ::= { hh3cevtModuleRouterType 533 } -- SecPath M9000-AD-NSQM6ADEEMPA0-SecBlade V
hh3cevtModuleRt-NSQM2QG2TG8A0               OBJECT IDENTIFIER ::= { hh3cevtModuleRouterType 534 } -- SecPath M9000-AD-NSQM2QG2TG8A0
hh3cevtModuleRt-NS-ADEEMPB0                 OBJECT IDENTIFIER ::= { hh3cevtModuleRouterType 535 } -- SecPath M9000-AD-NSQM6ADEEMPB0-SecBlade V
hh3cevtModuleRt-NSQM2TG16A0                 OBJECT IDENTIFIER ::= { hh3cevtModuleRouterType 536 } -- SecPath M9000-AD-NSQM2TG16A0
hh3cevtModuleRt-NSQM6SUP04A0                OBJECT IDENTIFIER ::= { hh3cevtModuleRouterType 537 } -- SecPath M9000-AD-NSQM6SUP04A0
hh3cevtModuleRt-NSQM2QG4A0                  OBJECT IDENTIFIER ::= { hh3cevtModuleRouterType 538 } -- SecPath M9000-AD-NSQM2QG4A0
hh3cevtModuleRt-NSQM1SUPD0                  OBJECT IDENTIFIER ::= { hh3cevtModuleRouterType 539 } -- SecPath M9000-NSQM1SUPD0
hh3cevtModuleRt-NSQM1FAB08E0                OBJECT IDENTIFIER ::= { hh3cevtModuleRouterType 540 } -- SecPath M9016-V-NSQM1FAB08E0
hh3cevtModuleRt-NSQM1CGQ4TG24SHA0           OBJECT IDENTIFIER ::= { hh3cevtModuleRouterType 541 } -- SecPath M9000-NSQM1CGQ4TG24SHA0
hh3cevtModuleRt-NSQM2MPUF0                  OBJECT IDENTIFIER ::= { hh3cevtModuleRouterType 542 } -- SecPath M9000-S-V-NSQM2MPUF0
hh3cevtModuleRt-NSQM2FWDFGD0                OBJECT IDENTIFIER ::= { hh3cevtModuleRouterType 543 } -- SecPath M9000-S-V-NSQM2FWDFGD0-SecBlade IV
hh3cevtModuleRt-NSQM2MBFDB0                 OBJECT IDENTIFIER ::= { hh3cevtModuleRouterType 544 } -- SecPath M9000-S-V-NSQM2MBFDB0
hh3cevtModuleRt-NSQM2QG2TG8GP4B0            OBJECT IDENTIFIER ::= { hh3cevtModuleRouterType 545 } -- SecPath M9000-NSQM2QG2TG8GP4B0
hh3cevtModuleRt-NSQM2FAN08B                 OBJECT IDENTIFIER ::= { hh3cevtModuleRouterType 546 } -- SecPath M9000-S-V-NSQM2FAN08B
hh3cevtModuleRt-NSQM5TSUP08A0               OBJECT IDENTIFIER ::= { hh3cevtModuleRouterType 547 } -- SecPath T9000-E8-NSQM5TSUP08A0
hh3cevtModuleRt-NSQM5TIPSEMPA0              OBJECT IDENTIFIER ::= { hh3cevtModuleRouterType 548 } -- SecPath T9000-E-NS-IPSEMPA0
hh3cevtModuleRt-NSQM5AIASKB1                OBJECT IDENTIFIER ::= { hh3cevtModuleRouterType 549 } -- SecPath M9000-AI-E-NSQM5AIASKB1
hh3cevtModuleRt-NSQM1G4XS4-Z                OBJECT IDENTIFIER ::= { hh3cevtModuleRouterType 550 } -- 4-GE Fabric,4-XGE Fabric Interface Module
hh3cevtModuleRt-NSQM5TIPSEMPB0              OBJECT IDENTIFIER ::= { hh3cevtModuleRouterType 551 } -- SecPath T9000-E-NS-IPSEMPB0
hh3cevtModuleRt-NSQM5SUP04A1                OBJECT IDENTIFIER ::= { hh3cevtModuleRouterType 552 } -- SecPath M9000-E-NSQM5SUP04A1
hh3cevtModuleRt-NS-FWEMPB1                  OBJECT IDENTIFIER ::= { hh3cevtModuleRouterType 553 } -- SecPath M9000-E-NSQM5FWEMPB1
hh3cevtModuleRt-NS-AFC2000EMPB1             OBJECT IDENTIFIER ::= { hh3cevtModuleRouterType 554 } -- SecPath M9000-E-NSQM5AFC2000EMPB1
hh3cevtModuleRt-NS-AFC2000EMPA1             OBJECT IDENTIFIER ::= { hh3cevtModuleRouterType 555 } -- SecPath M9000-E-NSQM5AFC2000EMPA1
hh3cevtModuleRt-NS-ADEEMPC0                 OBJECT IDENTIFIER ::= { hh3cevtModuleRouterType 556 } -- SecPath M9000-AD-NSQM6ADEEMPC0-SecBlade V
hh3cevtModuleRt-NSQM1CGQ6SH0                OBJECT IDENTIFIER ::= { hh3cevtModuleRouterType 557 } -- H3C SecPath NSQM1CGQ6SH0
hh3cevtModuleRt-NSQM7SUPB0                  OBJECT IDENTIFIER ::= { hh3cevtModuleRouterType 558 } -- H3C SecPath M9000-X06-NSQM7SUPB0
hh3cevtModuleRt-NSQM7FAB06A0                OBJECT IDENTIFIER ::= { hh3cevtModuleRouterType 559 } -- H3C SecPath M9000-X06-NS-NSQM7FAB06A0
hh3cevtModuleRt-NSQM7SUPA0                  OBJECT IDENTIFIER ::= { hh3cevtModuleRouterType 560 } -- H3C SecPath M9000-X10-NSQM7SUPA0
hh3cevtModuleRt-NSQM7FAB10A0                OBJECT IDENTIFIER ::= { hh3cevtModuleRouterType 561 } -- H3C SecPath M9000-X10-NSQM7FAB10A0
hh3cevtModuleRt-FAN-120B-3-A10              OBJECT IDENTIFIER ::= { hh3cevtModuleRouterType 562 } -- H3C SecPath M9000-X10-FAN-120B-3-A10
hh3cevtModuleRt-NSQM7MBSHB0                 OBJECT IDENTIFIER ::= { hh3cevtModuleRouterType 563 } -- H3C SecPath M9000-X-NSQM7MBSHB0
hh3cevtModuleRt-NSQM7MBSHA0                 OBJECT IDENTIFIER ::= { hh3cevtModuleRouterType 564 } -- H3C SecPath M9000-X-NSQM7MBSHA0
hh3cevtModuleRt-NS-FWFFGA0                  OBJECT IDENTIFIER ::= { hh3cevtModuleRouterType 565 } -- H3C SecPath M9000-X-NS-FWFFGA0
hh3cevtModuleRt-NS-FWFFGB0                  OBJECT IDENTIFIER ::= { hh3cevtModuleRouterType 566 } -- H3C SecPath M9000-X-NS-FWFFGB0
-- 600 to 799 reserved for voice router--
hh3cevtModuleRt-VG-8fxs                     OBJECT IDENTIFIER ::= { hh3cevtModuleRouterType 600 } -- 8 Port Foreign Exchange Station module
hh3cevtModuleRt-VG-24fxs                    OBJECT IDENTIFIER ::= { hh3cevtModuleRouterType 601 } -- 24 Port Foreign Exchange Station module
hh3cevtModuleRt-VG-24fxs24fxo               OBJECT IDENTIFIER ::= { hh3cevtModuleRouterType 602 } -- 24 Port Foreign Exchange Station and 24 Port Foreign Exchange Office module
hh3cevtModuleRt-VG-MPU                      OBJECT IDENTIFIER ::= { hh3cevtModuleRouterType 603 } -- Media Processing Unit
hh3cevtModuleRt-MIM-VCX-CONNECT-P-3C        OBJECT IDENTIFIER ::= { hh3cevtModuleRouterType 604 } -- MIM VCX Connect Primary module
hh3cevtModuleRt-MIM-VCX-CONNECT-S-3C        OBJECT IDENTIFIER ::= { hh3cevtModuleRouterType 605 } -- MIM VCX Connect Secondary module
hh3cevtModuleRt-MIM-VCX-3C                  OBJECT IDENTIFIER ::= { hh3cevtModuleRouterType 606 } -- MIM VCX Enterprise module
hh3cevtModuleRt-VNIC-VMXNET3                OBJECT IDENTIFIER ::= { hh3cevtModuleRouterType 607 } -- 1 Port Gigabit Ethernet interface virtual VMXNET3 module
hh3cevtModuleRt-VNIC-E1000                  OBJECT IDENTIFIER ::= { hh3cevtModuleRouterType 608 } -- 1 Port Gigabit Ethernet interface virtual E1000 module
hh3cevtModuleRt-VNIC-VIRTIO                 OBJECT IDENTIFIER ::= { hh3cevtModuleRouterType 609 } -- 1 Port Gigabit Ethernet interface virtual VIRTIO module
hh3cevtModuleRt-VNIC-RTL8139                OBJECT IDENTIFIER ::= { hh3cevtModuleRouterType 610 } -- 1 Port Gigabit Ethernet interface virtual RTL8139 module
hh3cevtModuleRt-VNIC-IXGBEVF                OBJECT IDENTIFIER ::= { hh3cevtModuleRouterType 611 } -- 1 Port Ten-Gigabit Ethernet interface virtual IXGBEVF module
hh3cevtModuleRt-IXGBE-2XGE                  OBJECT IDENTIFIER ::= { hh3cevtModuleRouterType 612 } -- 2 Port Ten-Gigabit Ethernet interface IXGBE module
hh3cevtModuleRt-TG3-4GE                     OBJECT IDENTIFIER ::= { hh3cevtModuleRouterType 613 } -- 4 Port Gigabit Ethernet interface TG3 module
hh3cevtModuleRt-MPUV16                      OBJECT IDENTIFIER ::= { hh3cevtModuleRouterType 614 } -- Main Processing Unit over virtual machine
hh3cevtModuleRt-MPUP6                       OBJECT IDENTIFIER ::= { hh3cevtModuleRouterType 615 } -- Main Processing Unit over physical machine
hh3cevtModuleRt-IGB-1GE                     OBJECT IDENTIFIER ::= { hh3cevtModuleRouterType 616 } -- 1 Port Gigabit Ethernet interface IGB module
hh3cevtModuleRt-IGB-2GE                     OBJECT IDENTIFIER ::= { hh3cevtModuleRouterType 617 } -- 2 Port Gigabit Ethernet interface IGB module
hh3cevtModuleRt-IGB-4GE                     OBJECT IDENTIFIER ::= { hh3cevtModuleRouterType 618 } -- 4 Port Gigabit Ethernet interface IGB module
hh3cevtModuleRt-VLNS1000                    OBJECT IDENTIFIER ::= { hh3cevtModuleRouterType 619 } -- Virtual L2TP Network Server over virtual machine
hh3cevtModuleRt-VLNS2000                    OBJECT IDENTIFIER ::= { hh3cevtModuleRouterType 620 } -- Virtual L2TP Network Server over physical machine
hh3cevtModuleRt-NS-MIM-GP4A2                OBJECT IDENTIFIER ::= { hh3cevtModuleRouterType 621 } -- 4 Port GigabitEthernet Interface Module
hh3cevtModuleRt-NS-MIM-GT4PFCA2             OBJECT IDENTIFIER ::= { hh3cevtModuleRouterType 622 } -- 4 Port GigabitEthernet Interface Module
hh3cevtModuleRt-NS-NIM-TG6A2                OBJECT IDENTIFIER ::= { hh3cevtModuleRouterType 623 } -- 6 Port Ten-GigabitEthernet Interface Module
hh3cevtModuleRt-NS-SIM-GT4PFCA2             OBJECT IDENTIFIER ::= { hh3cevtModuleRouterType 624 } -- 4 Port GigabitEthernet Interface Module
hh3cevtModuleRt-NS-NIM-TG6A-Z               OBJECT IDENTIFIER ::= { hh3cevtModuleRouterType 625 } -- 6 Port Ten-GigabitEthernet Interface Module

--
-- 800 to 999 reserved for normal routers part II
--
hh3cevtModuleRt-SIC-4GSW                    OBJECT IDENTIFIER ::= { hh3cevtModuleRouterType 800 } -- 4-Port 10M/100M/1000MBASE-T Ethernet L2 Switch Interface SIC-Module
hh3cevtModuleRt-SIC-4GSWP                   OBJECT IDENTIFIER ::= { hh3cevtModuleRouterType 801 } -- 4-Port 10M/100M/1000MBASE-T(WITH POE) Ethernet L2 Switch Interface SIC-Module
hh3cevtModuleRt-SIC-1GEC-V2                 OBJECT IDENTIFIER ::= { hh3cevtModuleRouterType 802 } -- 1-Port Combo Gigabit Ethernet Interface SIC-Module
hh3cevtModuleRt-4G-LTE-ATT                  OBJECT IDENTIFIER ::= { hh3cevtModuleRouterType 803 } -- 1 Port 4G-LTE-ATT-Cellular Interface Adapter Card
hh3cevtModuleRt-4G-TD-LTE                   OBJECT IDENTIFIER ::= { hh3cevtModuleRouterType 804 } -- 1 Port 4G-TD-LTE-Cellular Interface Adapter Card
hh3cevtModuleRt-FIP-240                     OBJECT IDENTIFIER ::= { hh3cevtModuleRouterType 805 } -- Flexible Interface Platform 240
hh3cevtModuleRt-8GBP-V2                     OBJECT IDENTIFIER ::= { hh3cevtModuleRouterType 806 } -- 8-Port GigaBit Ethernet Optical Interface Module(SFP) V2
hh3cevtModuleRt-HMIM-CNDE                   OBJECT IDENTIFIER ::= { hh3cevtModuleRouterType 807 } -- CNDE Crypto Engine HMIM-Module
hh3cevtModuleRt-4G-LTE-Mobile               OBJECT IDENTIFIER ::= { hh3cevtModuleRouterType 808 } -- 1 Port 4G-LTE-Mobile-Cellular Interface Adapter Card
hh3cevtModuleRt-SIC-4G-LTE-M                OBJECT IDENTIFIER ::= { hh3cevtModuleRouterType 809 } -- 1 Port 4G-LTE/TD-SCDMA/WCDMA Cellular Interface SIC-Module
hh3cevtModuleRt-CRSE-X3                     OBJECT IDENTIFIER ::= { hh3cevtModuleRouterType 810 } -- Carrier Route Switch Engine X3
hh3cevtModuleRt-CFIP-300                    OBJECT IDENTIFIER ::= { hh3cevtModuleRouterType 811 } -- Carrier Flexible Interface Platform 300
hh3cevtModuleRt-CFIP-310                    OBJECT IDENTIFIER ::= { hh3cevtModuleRouterType 812 } -- Carrier Flexible Interface Platform 310
hh3cevtModuleRt-CSAP-4EXP                   OBJECT IDENTIFIER ::= { hh3cevtModuleRouterType 813 } -- Carrier 4-Port 10GBASE-R/W Ethernet Optical Interface Module(SFP+)
hh3cevtModuleRt-RSU                         OBJECT IDENTIFIER ::= { hh3cevtModuleRouterType 814 } -- Route Switch Unit
hh3cevtModuleRt-CFIP-610                    OBJECT IDENTIFIER ::= { hh3cevtModuleRouterType 815 } -- Carrier Flexible Interface Platform 610
hh3cevtModuleRt-2EXP                        OBJECT IDENTIFIER ::= { hh3cevtModuleRouterType 816 } -- 2-Port 10GBASE-R/W Ethernet Optical Interface Module(SFP+)
hh3cevtModuleRt-16GBP                       OBJECT IDENTIFIER ::= { hh3cevtModuleRouterType 817 } -- 16-Port Gigabit Ethernet Optical Interface Module(SFP)
hh3cevtModuleRt-CFIP-240                    OBJECT IDENTIFIER ::= { hh3cevtModuleRouterType 818 } -- Carrier Flexible Interface Platform 240
hh3cevtModuleRt-RSE-X3                      OBJECT IDENTIFIER ::= { hh3cevtModuleRouterType 819 } -- Route Switch Engine X3
hh3cevtModuleRt-SAP-8EXP                    OBJECT IDENTIFIER ::= { hh3cevtModuleRouterType 820 } -- 8-Port 10GBASE-R/W Ethernet Optical Interface Module(SFP+)
hh3cevtModuleRt-SAP-16EXP                   OBJECT IDENTIFIER ::= { hh3cevtModuleRouterType 821 } -- 16-Port 10GBASE-R/W Ethernet Optical Interface Module(SFP+)
hh3cevtModuleRt-PU1P                        OBJECT IDENTIFIER ::= { hh3cevtModuleRouterType 822 } -- 1-Port 10G POS/RPR Interface Module(XFP)
hh3cevtModuleRt-RSU100                      OBJECT IDENTIFIER ::= { hh3cevtModuleRouterType 823 } -- Router Switch Unit 100
hh3cevtModuleRt-SAP-2QGP                    OBJECT IDENTIFIER ::= { hh3cevtModuleRouterType 824 } -- 2-Port 40GBASE Ethernet Optical Interface Module(QSFP+)
hh3cevtModuleRt-CSFE-X1                     OBJECT IDENTIFIER ::= { hh3cevtModuleRouterType 825 } -- Carrier Switch Fabric Engine X1
hh3cevtModuleRt-RIC-4GEE                    OBJECT IDENTIFIER ::= { hh3cevtModuleRouterType 826 } -- 4-Port 10M/100M/1000MBASE-T Ethernet Interface RIC-Module
hh3cevtModuleRt-RIC-4GEF                    OBJECT IDENTIFIER ::= { hh3cevtModuleRouterType 827 } -- 4-Port 1000M Base-F Optical Ethernet Interface RIC-Module
hh3cevtModuleRt-RIC-8GEE                    OBJECT IDENTIFIER ::= { hh3cevtModuleRouterType 828 } -- 8-Port 10M/100M/1000MBASE-T Ethernet Interface RIC-Module
hh3cevtModuleRt-RIC-8GEF                    OBJECT IDENTIFIER ::= { hh3cevtModuleRouterType 829 } -- 8-Port 1000M Base-F Optical Ethernet Interface RIC-Module
hh3cevtModuleRt-RIC-1XGEF                   OBJECT IDENTIFIER ::= { hh3cevtModuleRouterType 830 } -- 1-Port Ten-GigabitEthernet Optical Interface RIC-Module
hh3cevtModuleRt-HMIM-1E1POS                 OBJECT IDENTIFIER ::= { hh3cevtModuleRouterType 831 } -- 1 PORT E1 Interface HMIM-Module
hh3cevtModuleRt-DHMIM-1DM                   OBJECT IDENTIFIER ::= { hh3cevtModuleRouterType 832 } -- 1 PORT E1 Interface DHMIM-Module
hh3cevtModuleRt-DHMIM-1E1POS1DM             OBJECT IDENTIFIER ::= { hh3cevtModuleRouterType 833 } -- 1 PORT E1 Interface DHMIM-Module
hh3cevtModuleRt-RPE-X3                      OBJECT IDENTIFIER ::= { hh3cevtModuleRouterType 834 } -- Route Processing Engine X3
hh3cevtModuleRt-CRPE-X3                     OBJECT IDENTIFIER ::= { hh3cevtModuleRouterType 835 } -- Carrier Route Processing Engine X3
hh3cevtModuleRt-SAP-28GE                    OBJECT IDENTIFIER ::= { hh3cevtModuleRouterType 836 } -- 16-Port SFP and 12-Port Combo GE Module
hh3cevtModuleRt-SAP-20GE2XP                 OBJECT IDENTIFIER ::= { hh3cevtModuleRouterType 837 } -- 16-Port SFP 4-Port Combo GE and 2-Port 10GE Module
hh3cevtModuleRt-SFE-L1                      OBJECT IDENTIFIER ::= { hh3cevtModuleRouterType 838 } -- Switch Fabric Engine L1
hh3cevtModuleRt-FIP-640                     OBJECT IDENTIFIER ::= { hh3cevtModuleRouterType 839 } -- Flexible Interface Platform 640
hh3cevtModuleRt-HMIM-8GSWF                  OBJECT IDENTIFIER ::= { hh3cevtModuleRouterType 840 } -- 8-Port 1000M Base-F Optical Ethernet L2 Switch Interface HMIM_Module, including 4 Combo Ports
hh3cevtModuleRt-HMIM-8E1T1                  OBJECT IDENTIFIER ::= { hh3cevtModuleRouterType 841 } -- 8-port E1/CE1/T1/CT1/PRI HMIM Module
hh3cevtModuleRt-HMIM-4E1T1                  OBJECT IDENTIFIER ::= { hh3cevtModuleRouterType 842 } -- 4-port E1/CE1/T1/CT1/PRI HMIM Module
hh3cevtModuleRt-HMIM-2E1T1                  OBJECT IDENTIFIER ::= { hh3cevtModuleRouterType 843 } -- 2-port E1/CE1/T1/CT1/PRI HMIM Module
hh3cevtModuleRt-HMIM-8E1T1-F                OBJECT IDENTIFIER ::= { hh3cevtModuleRouterType 844 } -- 8-port E1/T1/Fractional E1/T1 HMIM Module
hh3cevtModuleRt-HMIM-4E1T1-F                OBJECT IDENTIFIER ::= { hh3cevtModuleRouterType 845 } -- 4-port E1/T1/Fractional E1/T1 HMIM Module
hh3cevtModuleRt-HMIM-2E1T1-F                OBJECT IDENTIFIER ::= { hh3cevtModuleRouterType 846 } -- 2-port E1/T1/Fractional E1/T1 HMIM Module
hh3cevtModuleRt-SIC-3G-HSPA-V2              OBJECT IDENTIFIER ::= { hh3cevtModuleRouterType 847 } -- 1 Port HSPA-Cellular Interface SIC-Module V2
hh3cevtModuleRt-SIC-4GSWF                   OBJECT IDENTIFIER ::= { hh3cevtModuleRouterType 848 } -- 4-Port 1000M Base-F Optical Ethernet L2 Switch Interface SIC-Module
hh3cevtModuleRt-SIC-4G-LTE-G-V2             OBJECT IDENTIFIER ::= { hh3cevtModuleRouterType 849 } -- 1 Port 4G-LTE-G-V2 Cellular Interface SIC-Module
hh3cevtModuleRt-SIC-4G-LTE-A-V2             OBJECT IDENTIFIER ::= { hh3cevtModuleRouterType 850 } -- 1 Port 4G-LTE-A-V2 Cellular Interface SIC-Module
hh3cevtModuleRt-SIC-4G-LTE-V-V2             OBJECT IDENTIFIER ::= { hh3cevtModuleRouterType 851 } -- 1 Port 4G-LTE-V-V2 Cellular Interface SIC-Module
hh3cevtModuleRt-MPU60                       OBJECT IDENTIFIER ::= { hh3cevtModuleRouterType 852 } -- Main Processing Unit 60
hh3cevtModuleRt-SPU                         OBJECT IDENTIFIER ::= { hh3cevtModuleRouterType 853 } -- Service Processing Unit
hh3cevtModuleRt-SIC-1VE1T1                  OBJECT IDENTIFIER ::= { hh3cevtModuleRouterType 854 } -- 1-Port E1/T1 Voice SIC Module,Domestic&Overseas Version
hh3cevtModuleRt-CFIP-700                    OBJECT IDENTIFIER ::= { hh3cevtModuleRouterType 855 } -- Carrier Flexible Interface Platform 700
hh3cevtModuleRt-HIM-20GBP-H3                OBJECT IDENTIFIER ::= { hh3cevtModuleRouterType 856 } -- 20-Port Gigabit Ethernet Optical Interface Module(SFP)
hh3cevtModuleRt-HIM-4EXP-H3                 OBJECT IDENTIFIER ::= { hh3cevtModuleRouterType 857 } -- 4-Port 10GBASE-R/W Ethernet Optical Interface Module(SFP+)
hh3cevtModuleRt-HIM-2EXP-H3                 OBJECT IDENTIFIER ::= { hh3cevtModuleRouterType 858 } -- 2-Port 10GBASE-R/W Ethernet Optical Interface Module(SFP+)
hh3cevtModuleRt-HIM-8GBE-V3                 OBJECT IDENTIFIER ::= { hh3cevtModuleRouterType 859 } -- 8-port GigaBit Ethernet Electrical Interface Module
hh3cevtModuleRt-HIM-4GBE-V3                 OBJECT IDENTIFIER ::= { hh3cevtModuleRouterType 860 } -- 4-port GigaBit Ethernet Electrical Interface Module
hh3cevtModuleRt-HIM-8GBP-V3                 OBJECT IDENTIFIER ::= { hh3cevtModuleRouterType 861 } -- 8-Port GigaBit Ethernet Optical Interface Module(SFP)
hh3cevtModuleRt-HIM-4GBP-V3                 OBJECT IDENTIFIER ::= { hh3cevtModuleRouterType 862 } -- 4-Port GigaBit Ethernet Optical Interface Module(SFP)
hh3cevtModuleRt-SIC-AP                      OBJECT IDENTIFIER ::= { hh3cevtModuleRouterType 863 } -- 1-Port AP SIC Module,Domestic&Overseas Version
hh3cevtModuleRt-CR-MPU-04B                  OBJECT IDENTIFIER ::= { hh3cevtModuleRouterType 864 } -- CR Main Processing Unit B for 04 Chassis
hh3cevtModuleRt-CR-MPU-16B                  OBJECT IDENTIFIER ::= { hh3cevtModuleRouterType 865 } -- CR Main Processing Unit B for 08 and 16 Chassis
hh3cevtModuleRt-CR-MPU-16E                  OBJECT IDENTIFIER ::= { hh3cevtModuleRouterType 866 } -- CR Main Processing Unit E for 08 and 16 Chassis
hh3cevtModuleRt-CR-SFU-04D-H                OBJECT IDENTIFIER ::= { hh3cevtModuleRouterType 867 } -- CR Switching Fabric Unit(HD) for 04 Chassis
hh3cevtModuleRt-CR-SFU-08C-H                OBJECT IDENTIFIER ::= { hh3cevtModuleRouterType 868 } -- CR Switching Fabric Unit(HC) for 08 Chassis
hh3cevtModuleRt-CR-SFU-08D-H                OBJECT IDENTIFIER ::= { hh3cevtModuleRouterType 869 } -- CR Switching Fabric Unit(HD) for 08 Chassis
hh3cevtModuleRt-CR-SFU-16B-H                OBJECT IDENTIFIER ::= { hh3cevtModuleRouterType 870 } -- CR Switching Fabric Unit(HB) for 16 Chassis
hh3cevtModuleRt-CR-SFU-16C-H                OBJECT IDENTIFIER ::= { hh3cevtModuleRouterType 871 } -- CR Switching Fabric Unit(HC) for 16 Chassis
hh3cevtModuleRt-CR-LPU-CQ12                 OBJECT IDENTIFIER ::= { hh3cevtModuleRouterType 872 } -- CR 12-Port 100G Ethernet Optical Interface Module
hh3cevtModuleRt-CR-LPU-4004                 OBJECT IDENTIFIER ::= { hh3cevtModuleRouterType 873 } -- CR Flexible Interface Module 4004
hh3cevtModuleRt-CR-HIC-PU02                 OBJECT IDENTIFIER ::= { hh3cevtModuleRouterType 874 } -- CR 2-Port 10G POS Optical Interface Card
hh3cevtModuleRt-CR-HIC-XP12                 OBJECT IDENTIFIER ::= { hh3cevtModuleRouterType 875 } -- CR 12-Port 10G Ethernet Optical Interface Card
hh3cevtModuleRt-CR-HIC-GP12                 OBJECT IDENTIFIER ::= { hh3cevtModuleRouterType 876 } -- CR 12-Port Gigabit Ethernet Optical Interface Card
hh3cevtModuleRt-CR-HIC-QQ03                 OBJECT IDENTIFIER ::= { hh3cevtModuleRouterType 877 } -- CR 3-Port 40G Ethernet Optical Interface Card(QSFP+)
hh3cevtModuleRt-CR-HIC-CC01                 OBJECT IDENTIFIER ::= { hh3cevtModuleRouterType 878 } -- CR 1-Port 100G Ethernet Optical Interface Card(CFP2)
hh3cevtModuleRt-CR-HIC-CP01                 OBJECT IDENTIFIER ::= { hh3cevtModuleRouterType 879 } -- CR 1-Port 100G Ethernet Optical Interface Card(CFP)
hh3cevtModuleRt-CR-MPU-16C                  OBJECT IDENTIFIER ::= { hh3cevtModuleRouterType 880 } -- CR Main Processing Unit C for 08 and 16 Chassis
hh3cevtModuleRt-MPU-100-X1                  OBJECT IDENTIFIER ::= { hh3cevtModuleRouterType 881 } -- Main Processing Unit 100-X1
hh3cevtModuleRt-SPU-100-X1                  OBJECT IDENTIFIER ::= { hh3cevtModuleRouterType 882 } -- Service Processing Unit 100-X1
hh3cevtModuleRt-SPU-200-X1                  OBJECT IDENTIFIER ::= { hh3cevtModuleRouterType 883 } -- Service Processing Unit 200-X1
hh3cevtModuleRt-SPU-400-X1                  OBJECT IDENTIFIER ::= { hh3cevtModuleRouterType 884 } -- Service Processing Unit 400-X1
hh3cevtModuleRt-HIM-10GB2EXP-H3             OBJECT IDENTIFIER ::= { hh3cevtModuleRouterType 885 } -- 10-port 1000BASE-X Ethernet Optical Interface(SFP)+2-port 10GBASE-R/W Ethernet Optical Interface Card(SFP+)
hh3cevtModuleRt-HIM-11GB1EXP-H3             OBJECT IDENTIFIER ::= { hh3cevtModuleRouterType 886 } -- 11-port 1000BASE-X Ethernet Optical Interface(SFP)+1-port 10GBASE-R/W Ethernet Optical Interface Card(SFP+)
hh3cevtModuleRt-HMIM-1E3T3                  OBJECT IDENTIFIER ::= { hh3cevtModuleRouterType 887 } -- 1-port T3 HMIM-Module
hh3cevtModuleRt-SIC-4G-CNDE                 OBJECT IDENTIFIER ::= { hh3cevtModuleRouterType 888 } -- 1-port 4G LTE and CNDE SIC Module
hh3cevtModuleRt-SIC-D4G-CNDE                OBJECT IDENTIFIER ::= { hh3cevtModuleRouterType 889 } -- 2-port 4G LTE and CNDE SIC Module
hh3cevtModuleRt-CR-LPU-CC08                 OBJECT IDENTIFIER ::= { hh3cevtModuleRouterType 890 } -- CR 8-Port 100G Ethernet Optical Interface Module
hh3cevtModuleRt-CR-LPU-2002                 OBJECT IDENTIFIER ::= { hh3cevtModuleRouterType 891 } -- CR Flexible Interface Module 2002
hh3cevtModuleRt-CR-LPU-XP20CC02             OBJECT IDENTIFIER ::= { hh3cevtModuleRouterType 892 } -- CR 20-Port 10G Ethernet Optical Interface Module and 2-Port 100G Ethernet Optical Interface Module
hh3cevtModuleRt-CR-LPU-XP40                 OBJECT IDENTIFIER ::= { hh3cevtModuleRouterType 893 } -- CR 40-Port 10G Ethernet Optical Interface Module
hh3cevtModuleRt-CR-LPU-CC04                 OBJECT IDENTIFIER ::= { hh3cevtModuleRouterType 894 } -- CR 4-Port 100G Ethernet Optical Interface Module
hh3cevtModuleRt-FIP-680                     OBJECT IDENTIFIER ::= { hh3cevtModuleRouterType 895 } -- Service Processing Unit(680)
hh3cevtModuleRt-MIC-XP4L                    OBJECT IDENTIFIER ::= { hh3cevtModuleRouterType 896 } -- 4-port 10GBASE-R/W Ethernet Optical Interface Card(SFP+,LC)
hh3cevtModuleRt-MIM-1T3-V2                  OBJECT IDENTIFIER ::= { hh3cevtModuleRouterType 897 } -- 1-port T3 Interface Card
hh3cevtModuleRt-MIC-GP4L                    OBJECT IDENTIFIER ::= { hh3cevtModuleRouterType 898 } -- 4-Port 1000BASE-X COMBO Interface Card,(SFP,LC)
hh3cevtModuleRt-MIC-GP8L                    OBJECT IDENTIFIER ::= { hh3cevtModuleRouterType 899 } -- 8-Port 1000BASE-X Optical Interface Card,(SFP,LC)
hh3cevtModuleRt-CR-19K-MPU-20A              OBJECT IDENTIFIER ::= { hh3cevtModuleRouterType 900 } -- CR Main Processing Unit A for 19 Chassis
hh3cevtModuleRt-CR-19K-MPU-20B              OBJECT IDENTIFIER ::= { hh3cevtModuleRouterType 901 } -- CR Main Processing Unit B for 19 Chassis
hh3cevtModuleRt-CR-19K-SFU-20C              OBJECT IDENTIFIER ::= { hh3cevtModuleRouterType 902 } -- CR Switching Fabric Unit(HC) for 20 Chassis
hh3cevtModuleRt-CR-19K-MSFU-20B             OBJECT IDENTIFIER ::= { hh3cevtModuleRouterType 903 } -- CR Multi-Switching Fabric Unit(HB) for 20 Chassis
hh3cevtModuleRt-CR-19K-MSFU-20C             OBJECT IDENTIFIER ::= { hh3cevtModuleRouterType 904 } -- CR Multi-Switching Fabric Unit(HC) for 20 Chassis
hh3cevtModuleRt-CR-19K-MCCU                 OBJECT IDENTIFIER ::= { hh3cevtModuleRouterType 905 } -- CR Multi-Control Connection A Unit for 24 Chassis
hh3cevtModuleRt-CR-19K-MFCU                 OBJECT IDENTIFIER ::= { hh3cevtModuleRouterType 906 } -- CR Multi-Fabric Connection A Unit for 24 Chassis
hh3cevtModuleRt-RIC-8E1                     OBJECT IDENTIFIER ::= { hh3cevtModuleRouterType 907 } -- 8-Port E1/CE1/PRI Interface RIC-Module
hh3cevtModuleRt-RIC-1XGEF4GEF               OBJECT IDENTIFIER ::= { hh3cevtModuleRouterType 908 } -- 1-Port 10M/100M/1000M/10000MBASE-F and 4-Port 10M/100M/1000MBASE-F Ethernet Interface 1XGEF4GEFModule
hh3cevtModuleRt-RIC-TU01A                   OBJECT IDENTIFIER ::= { hh3cevtModuleRouterType 909 } -- 1-Port 10M/100M/1000M/10000MBASE-F and 4-Port 10M/100M/1000MBASE-F Ethernet Interface TU01AModule
hh3cevtModuleRt-SPE-S1                      OBJECT IDENTIFIER ::= { hh3cevtModuleRouterType 910 } -- Service Processing Engine S1
hh3cevtModuleRt-SPE-S3                      OBJECT IDENTIFIER ::= { hh3cevtModuleRouterType 911 } -- Service Processing Engine S3
hh3cevtModuleRt-SPU-600-X1                  OBJECT IDENTIFIER ::= { hh3cevtModuleRouterType 912 } -- Service Processing Unit 600-X1
hh3cevtModuleRt-RIC-CP08                    OBJECT IDENTIFIER ::= { hh3cevtModuleRouterType 913 } -- 8-Port E1/CE1/PRI Interface RIC-Module
hh3cevtModuleRt-MIC-SP4L                    OBJECT IDENTIFIER ::= { hh3cevtModuleRouterType 914 } -- 4-Port OC-3/STM-1 POS/CPOS/ATM or 1-Port OC-12/STM-4 POS/ATM Optical Interface Card,(SFP,LC)
hh3cevtModuleRt-MIC-ET16L                   OBJECT IDENTIFIER ::= { hh3cevtModuleRouterType 915 } -- 16-Port E1/T1 Electrical Interface Card
hh3cevtModuleRt-MIC-CLP4L                   OBJECT IDENTIFIER ::= { hh3cevtModuleRouterType 916 } -- 4-Port OC-3/STM-1 CPOS/POS Optical Interface Card,(SFP,LC)
hh3cevtModuleRt-MIC-CLP2L                   OBJECT IDENTIFIER ::= { hh3cevtModuleRouterType 917 } -- 2-Port OC-3/STM-1 CPOS/POS Optical Interface Card,(SFP,LC)
hh3cevtModuleRt-MIC-SP8L                    OBJECT IDENTIFIER ::= { hh3cevtModuleRouterType 918 } -- 8-Port OC-3c/STM-1c POS Optical Interface Card
hh3cevtModuleRt-HMIM-8EM                    OBJECT IDENTIFIER ::= { hh3cevtModuleRouterType 919 } -- 8-Port E&M Interface HMIM-Module
hh3cevtModuleRt-SFU                         OBJECT IDENTIFIER ::= { hh3cevtModuleRouterType 920 } -- Switching Fabric Unit
hh3cevtModuleRt-SFE-L2                      OBJECT IDENTIFIER ::= { hh3cevtModuleRouterType 921 } -- Switching Fabric Engine L2
hh3cevtModuleRt-SFU-UNFIXED                 OBJECT IDENTIFIER ::= { hh3cevtModuleRouterType 922 } -- Unfixed Switching Fabric Unit
hh3cevtModuleRt-FIP-380                     OBJECT IDENTIFIER ::= { hh3cevtModuleRouterType 923 } -- Flexible Interface Platform-380
hh3cevtModuleRt-CR-19K-MPU-08A              OBJECT IDENTIFIER ::= { hh3cevtModuleRouterType 924 } -- CR Main Processing Unit A for 08 Chassis
hh3cevtModuleRt-CR-19K-MPU-16A              OBJECT IDENTIFIER ::= { hh3cevtModuleRouterType 925 } -- CR Main Processing Unit A for 16 Chassis
hh3cevtModuleRt-CR-19K-SFU-08C              OBJECT IDENTIFIER ::= { hh3cevtModuleRouterType 926 } -- CR Switching Fabric Unit(HC) for 08 Chassis
hh3cevtModuleRt-CR-19K-SFU-16C              OBJECT IDENTIFIER ::= { hh3cevtModuleRouterType 927 } -- CR Switching Fabric Unit(HC) for 16 Chassis
hh3cevtModuleRt-CR-19K-LPU-CC08             OBJECT IDENTIFIER ::= { hh3cevtModuleRouterType 928 } -- CR 8-Port 100G Ethernet Optical Interface Module
hh3cevtModuleRt-CR-19K-LPU-2002             OBJECT IDENTIFIER ::= { hh3cevtModuleRouterType 929 } -- CR Flexible Interface Module 2002
hh3cevtModuleRt-CR-19K-LPU-XP20CC02         OBJECT IDENTIFIER ::= { hh3cevtModuleRouterType 930 } -- CR 20-Port 10G Ethernet Optical Interface Module and 2-Port 100G Ethernet Optical Interface Module
hh3cevtModuleRt-CR-19K-LPU-XP40             OBJECT IDENTIFIER ::= { hh3cevtModuleRouterType 931 } -- CR 40-Port 10G Ethernet Optical Interface Module
hh3cevtModuleRt-CR-19K-LPU-CC04             OBJECT IDENTIFIER ::= { hh3cevtModuleRouterType 932 } -- CR 4-Port 100G Ethernet Optical Interface Module
hh3cevtModuleRt-CR-19K-LPU-CQ12             OBJECT IDENTIFIER ::= { hh3cevtModuleRouterType 933 } -- CR 12-Port 100G Ethernet Optical Interface Module
hh3cevtModuleRt-MIC-X-GT8                   OBJECT IDENTIFIER ::= { hh3cevtModuleRouterType 934 } -- 8-Port 10/100/1000BASE-T Electronic Multi-functional Interface Card
hh3cevtModuleRt-MIC-X-GP4GT4                OBJECT IDENTIFIER ::= { hh3cevtModuleRouterType 935 } -- 4-Port 10/100/1000BASE-T Electronic + 4-Port 1000BASE-X Optical Multi-functional Interface Card
hh3cevtModuleRt-MIC-X-GP10                  OBJECT IDENTIFIER ::= { hh3cevtModuleRouterType 936 } -- 10-Port 1000BASE-X Optical Multi-functional Interface Card
hh3cevtModuleRt-MIC-X-GP8                   OBJECT IDENTIFIER ::= { hh3cevtModuleRouterType 937 } -- 8-Port 1000BASE-X Optical Multi-functional Interface Card
hh3cevtModuleRt-CR-19K-LPU-4004             OBJECT IDENTIFIER ::= { hh3cevtModuleRouterType 938 } -- CR Flexible Interface Module 4004
hh3cevtModuleRt-FIP-260                     OBJECT IDENTIFIER ::= { hh3cevtModuleRouterType 939 } -- Flexible Interface Platform-260
hh3cevtModuleRt-CR-LPU-XP72                 OBJECT IDENTIFIER ::= { hh3cevtModuleRouterType 940 } -- CR 72-Port 10G Ethernet Optical Interface Module
hh3cevtModuleRt-CR-LPU-XP48                 OBJECT IDENTIFIER ::= { hh3cevtModuleRouterType 941 } -- CR 48-Port 10G Ethernet Optical Interface Module
hh3cevtModuleRt-CR-LPU-CC04B                OBJECT IDENTIFIER ::= { hh3cevtModuleRouterType 942 } -- CR 4-Port 100G Ethernet Optical Interface Module
hh3cevtModuleRt-CR-LPU-2002B                OBJECT IDENTIFIER ::= { hh3cevtModuleRouterType 943 } -- CR Flexible Interface Module 2002B
hh3cevtModuleRt-LPU-1001B                   OBJECT IDENTIFIER ::= { hh3cevtModuleRouterType 944 } -- CR Flexible Interface Module 1001B
hh3cevtModuleRt-CR-19K-MSFU-08A             OBJECT IDENTIFIER ::= { hh3cevtModuleRouterType 945 } -- CR Multi-Switching Fabric Unit for 8 Chassis
hh3cevtModuleRt-Sic-AP220                   OBJECT IDENTIFIER ::= { hh3cevtModuleRouterType 946 } -- SIC-AP220 External Antennas 3 Streams Dual Radio
hh3cevtModuleRt-FIP-660                     OBJECT IDENTIFIER ::= { hh3cevtModuleRouterType 947 } -- Flexible Interface Platform 660
hh3cevtModuleRT-MIC-X-ET16                  OBJECT IDENTIFIER ::= { hh3cevtModuleRouterType 948 } -- 16-Port E1/T1 Electrical Interface Card,(RJ45)
hh3cevtModuleRT-MIC-X-SP4                   OBJECT IDENTIFIER ::= { hh3cevtModuleRouterType 949 } -- 4-Port OC-3/STM-1 POS or 1-Port OC-12/STM-4 POS Optical Interface Card,(SFP)
hh3cevtModuleRT-MIC-X-SP8                   OBJECT IDENTIFIER ::= { hh3cevtModuleRouterType 950 } -- 8-Port OC-3c/STM-1c POS Optical Interface Card,(SFP)
hh3cevtModuleRT-MIC-X-CLP2                  OBJECT IDENTIFIER ::= { hh3cevtModuleRouterType 951 } -- 2-Port OC-3/STM-1 CPOS Optical Interface Card,(SFP)
hh3cevtModuleRT-MIC-X-CLP4                  OBJECT IDENTIFIER ::= { hh3cevtModuleRouterType 952 } -- 4-Port OC-3/STM-1 CPOS Optical Interface Card,(SFP)
hh3cevtModuleRt-SPU-300                     OBJECT IDENTIFIER ::= { hh3cevtModuleRouterType 953 } -- ICG Service Processing Unit 300(10GE Combo)
hh3cevtModuleRt-CR-19K-LPU-XP72             OBJECT IDENTIFIER ::= { hh3cevtModuleRouterType 954 } -- 72-Port 10G Ethernet Optical Interface Module for 19 chassis
hh3cevtModuleRt-CR-19K-LPU-XP48             OBJECT IDENTIFIER ::= { hh3cevtModuleRouterType 955 } -- 48-Port 10G Ethernet Optical Interface Module for 19 chassis
hh3cevtModuleRt-CR-19K-LPU-2002B            OBJECT IDENTIFIER ::= { hh3cevtModuleRouterType 956 } -- Flexible Interface Module 2002B for 19 chassis
hh3cevtModuleRt-CR-19K-LPU-CC04B            OBJECT IDENTIFIER ::= { hh3cevtModuleRouterType 957 } -- 4-Port 100G Ethernet Optical Interface Module for 19 chassis
hh3cevtModuleRt-CR-19K-MPU-16B              OBJECT IDENTIFIER ::= { hh3cevtModuleRouterType 958 } -- Main Processing Unit B for 19016 Chassis
hh3cevtModuleRT-RPE-X5                      OBJECT IDENTIFIER ::= { hh3cevtModuleRouterType 959 } -- Route Processing Engine X5
hh3cevtModuleRT-RPE-X5E                     OBJECT IDENTIFIER ::= { hh3cevtModuleRouterType 960 } -- Route Processing Engine X5E
hh3cevtModuleRt-CR-HIC-PS04                 OBJECT IDENTIFIER ::= { hh3cevtModuleRouterType 961 } -- CR 4-Port non-channelized POS(155M/622M/2.5G) Interface Card,Sub Module
hh3cevtModuleRt-CR-HIC-PL08                 OBJECT IDENTIFIER ::= { hh3cevtModuleRouterType 962 } -- CR 8-Port non-channelized POS(155M) Interface Card,Sub Module
hh3cevtModuleRT-MIC-X-XP2                   OBJECT IDENTIFIER ::= { hh3cevtModuleRouterType 963 } -- 2-Port 1000BASE-R-SFP+ Optical Multi-functional Interface Card
hh3cevtModuleRT-MIC-X-XP4                   OBJECT IDENTIFIER ::= { hh3cevtModuleRouterType 964 } -- 4-Port 1000BASE-R-SFP+ Optical Multi-functional Interface Card
hh3cevtModuleRT-MIC-X-XP4W                  OBJECT IDENTIFIER ::= { hh3cevtModuleRouterType 965 } -- 4-Port 1000BASE-R-SFP+ Optical Multi-functional Interface Card(Support LAN/WAN mode)
hh3cevtModuleRT-SIC-CNDE-SJK                OBJECT IDENTIFIER ::= { hh3cevtModuleRouterType 966 } -- SJK CNDE SIC Module
hh3cevtModuleRT-SIC-4G-CNDE-SJK             OBJECT IDENTIFIER ::= { hh3cevtModuleRouterType 967 } -- SJK 4G LTE and CNDE SIC Module
hh3cevtModuleRT-SIC-D4G-CNDE-SJK            OBJECT IDENTIFIER ::= { hh3cevtModuleRouterType 968 } -- SJK Double 4G LTE and CNDE SIC Module
hh3cevtModuleRt-CR-19K-MSFU-16A             OBJECT IDENTIFIER ::= { hh3cevtModuleRouterType 969 } -- CR Multi-Switching Fabric Unit(A) for 16 Chassis
hh3cevtModuleRT-HMIM-CNDE-SJK               OBJECT IDENTIFIER ::= { hh3cevtModuleRouterType 970 } -- SJK CNDE HMIM Module
hh3cevtModuleRT-MIBIF-MINI-CNDE-SJK         OBJECT IDENTIFIER ::= { hh3cevtModuleRouterType 971 } -- SJK MINI CNDE Module
hh3cevtModuleRT-SIC-AP320-FIT               OBJECT IDENTIFIER ::= { hh3cevtModuleRouterType 972 } -- AP320 FIT SIC Module
hh3cevtModuleRT-SAP-XP4GE32                 OBJECT IDENTIFIER ::= { hh3cevtModuleRouterType 973 } -- 4-Port 10G and 32-Port G Ethernet Optical Interface Module(SFP+)
hh3cevtModuleRT-SIC-4E1-F-Z                 OBJECT IDENTIFIER ::= { hh3cevtModuleRouterType 974 } -- 4-Port Fractional E1 Interface SIC-Module
hh3cevtModuleRT-HRIC-CLGQ2                  OBJECT IDENTIFIER ::= { hh3cevtModuleRouterType 975 } -- 1-Port 50-100-GE and 1-Port 50-GE Optical Interface HRIC-Module
hh3cevtModuleRT-HRIC-YGS4                   OBJECT IDENTIFIER ::= { hh3cevtModuleRouterType 976 } -- 4-Port 25-GE Optical Interface HRIC-Module
hh3cevtModuleRT-HRIC-XP8                    OBJECT IDENTIFIER ::= { hh3cevtModuleRouterType 977 } -- 8-Port Ten-GigabitEthernet Optical Interface HRIC-Module
hh3cevtModuleRT-HRIC-GP8                    OBJECT IDENTIFIER ::= { hh3cevtModuleRouterType 978 } -- 8-Port 1000M Base-F Optical Ethernet Interface HRIC-Module
hh3cevtModuleRT-HRIC-GT8                    OBJECT IDENTIFIER ::= { hh3cevtModuleRouterType 979 } -- 8-Port 1000M Base-T Ethernet Interface HRIC-Module

hh3cevtModuleRT-MIC-X-CNDE-SJK             OBJECT IDENTIFIER ::= { hh3cevtModuleRouterType 980 } -- SJK CNDE MIC-X Module
hh3cevtModuleRt-CR-19K-LPU-CQ18            OBJECT IDENTIFIER ::= { hh3cevtModuleRouterType 981 }
hh3cevtModuleRt-CR-19K-LPU-CQ12B           OBJECT IDENTIFIER ::= { hh3cevtModuleRouterType 982 }
hh3cevtModuleRt-CR-19K-LPU-SP              OBJECT IDENTIFIER ::= { hh3cevtModuleRouterType 983 }
hh3cevtModuleRt-CR-HIC-CQ01                OBJECT IDENTIFIER ::= { hh3cevtModuleRouterType 984 }
hh3cevtModuleRt-NS-NIM-TG6A                OBJECT IDENTIFIER ::= { hh3cevtModuleRouterType 985 }
hh3cevtModuleRtNS-NIM-TG4A3                OBJECT IDENTIFIER ::= { hh3cevtModuleRouterType 986 }
hh3cevtModuleRtNSQM2CGQ20                  OBJECT IDENTIFIER ::= { hh3cevtModuleRouterType 987 }
hh3cevtModuleRtNSQM2FWDFGC0                OBJECT IDENTIFIER ::= { hh3cevtModuleRouterType 988 }
hh3cevtModuleRtNSQM2FWDFGB0                OBJECT IDENTIFIER ::= { hh3cevtModuleRouterType 989 }
hh3cevtModuleRt-NS-TIM-TG8A2               OBJECT IDENTIFIER ::= { hh3cevtModuleRouterType 990 }
hh3cevtModuleRtNSQM5MBSHA1                 OBJECT IDENTIFIER ::= { hh3cevtModuleRouterType 991 }
hh3cevtModuleRtNS-C600-CGQ6A1              OBJECT IDENTIFIER ::= { hh3cevtModuleRouterType 992 }
hh3cevtModuleRtNSQM5SUP08A1                OBJECT IDENTIFIER ::= { hh3cevtModuleRouterType 993 }
hh3cevtModuleRtNSQ1M9ESL16UA0              OBJECT IDENTIFIER ::= { hh3cevtModuleRouterType 994 }
hh3cevtModuleRtNS-C300-CGQ2TG16A1          OBJECT IDENTIFIER ::= { hh3cevtModuleRouterType 995 }
hh3cevtModuleRtNS-FWEMPA1                  OBJECT IDENTIFIER ::= { hh3cevtModuleRouterType 996 }
hh3cevtModuleRtNSQM5FAB08A1                OBJECT IDENTIFIER ::= { hh3cevtModuleRouterType 997 }
hh3cevtModuleRtNS-C300-QG4TG16A1           OBJECT IDENTIFIER ::= { hh3cevtModuleRouterType 998 }
hh3cevtModuleRtNSQM5FAB16A1                OBJECT IDENTIFIER ::= { hh3cevtModuleRouterType 999 }
hh3cevtModuleRtNSQM5SUP16A1                OBJECT IDENTIFIER ::= { hh3cevtModuleRouterType 1000 }
hh3cevtModuleRtNSQ1M9ESL16LA0              OBJECT IDENTIFIER ::= { hh3cevtModuleRouterType 1001 }
hh3cevtModuleRtNS-C300-TG24A1              OBJECT IDENTIFIER ::= { hh3cevtModuleRouterType 1002 }
hh3cevtModuleRtNSQM1SSICASK1               OBJECT IDENTIFIER ::= { hh3cevtModuleRouterType 1003 }
hh3cevtModuleRtNSQM2AFC2000DGDSCA0         OBJECT IDENTIFIER ::= { hh3cevtModuleRouterType 1004 }
hh3cevtModuleRt-MPU-60-WiNet               OBJECT IDENTIFIER ::= { hh3cevtModuleRouterType 1005 }
hh3cevtModuleRtNSQM2VGDSCA0                OBJECT IDENTIFIER ::= { hh3cevtModuleRouterType 1006 }
hh3cevtModuleRt-HRIC-YGS2                  OBJECT IDENTIFIER ::= { hh3cevtModuleRouterType 1007 }  -- 2-Port 25-GigabitEthernet Optical Interface HRIC-Module
hh3cevtModuleRt-HRIC-LGQ1                  OBJECT IDENTIFIER ::= { hh3cevtModuleRouterType 1008 }  -- 1-Port 50-GigabitEthernet Optical Interface HRIC-Module
hh3cevtModuleRt-HRIC-XP4                   OBJECT IDENTIFIER ::= { hh3cevtModuleRouterType 1009 }  -- 4-Port Ten-GigabitEthernet Optical Interface HRIC-Module
hh3cevtModuleRt-RSU-300                    OBJECT IDENTIFIER ::= { hh3cevtModuleRouterType 1010 }
hh3cevtModuleRt-CR-19K-LPU-CQ06B           OBJECT IDENTIFIER ::= { hh3cevtModuleRouterType 1011 }
hh3cevtModuleRt-CR-HIC-XP10                OBJECT IDENTIFIER ::= { hh3cevtModuleRouterType 1012 }
hh3cevtModuleRt-SIC-1SSD                   OBJECT IDENTIFIER ::= { hh3cevtModuleRouterType 1013 }
hh3cevtModuleRtNSQM1AFC2000GDFGA0-Z        OBJECT IDENTIFIER ::= { hh3cevtModuleRouterType 1014 }
hh3cevtModuleRtNSQM2QG4GP40-Z              OBJECT IDENTIFIER ::= { hh3cevtModuleRouterType 1015 }
hh3cevtModuleRtNSQM1CGQ20-Z                OBJECT IDENTIFIER ::= { hh3cevtModuleRouterType 1016 }
hh3cevtModuleRtNSQM1FWDFGD1-Z              OBJECT IDENTIFIER ::= { hh3cevtModuleRouterType 1017 }
hh3cevtModuleRtNSQM1TGS32QSSG0-Z           OBJECT IDENTIFIER ::= { hh3cevtModuleRouterType 1018 }
hh3cevtModuleRtNSQM2TG16GP40-Z             OBJECT IDENTIFIER ::= { hh3cevtModuleRouterType 1019 }
hh3cevtModuleRtNSQM2TMPU12E0               OBJECT IDENTIFIER ::= { hh3cevtModuleRouterType 1020 }
hh3cevtModuleRt-HMIM-4XP                   OBJECT IDENTIFIER ::= { hh3cevtModuleRouterType 1021 }  -- 4-Port 10GBASE-R-SFP+ Optical Ethernet Interface Card
hh3cevtModuleRt-SIC-1POS-STM1              OBJECT IDENTIFIER ::= { hh3cevtModuleRouterType 1022 }
hh3cevtModuleRt-HMIM-4POS                  OBJECT IDENTIFIER ::= { hh3cevtModuleRouterType 1023 }
hh3cevtModuleRt-NSQM1MPULB                 OBJECT IDENTIFIER ::= { hh3cevtModuleRouterType 1024 }
hh3cevtModuleRt-CR-LPU-CQ12B               OBJECT IDENTIFIER ::= { hh3cevtModuleRouterType 1025 }
hh3cevtModuleRt-CR-LPU-CQ18                OBJECT IDENTIFIER ::= { hh3cevtModuleRouterType 1026 }
hh3cevtModuleRt-CR-MPU-20A                 OBJECT IDENTIFIER ::= { hh3cevtModuleRouterType 1027 }
hh3cevtModuleRt-CR-HIC-CLP04               OBJECT IDENTIFIER ::= { hh3cevtModuleRouterType 1028 }
hh3cevtModuleRt-CR-SFU-08C                 OBJECT IDENTIFIER ::= { hh3cevtModuleRouterType 1029 }
hh3cevtModuleRt-CR-HIC-PHP08               OBJECT IDENTIFIER ::= { hh3cevtModuleRouterType 1030 }
hh3cevtModuleRt-CR-MPU-08A                 OBJECT IDENTIFIER ::= { hh3cevtModuleRouterType 1031 }
hh3cevtModuleRt-CR-HIC-XP12B               OBJECT IDENTIFIER ::= { hh3cevtModuleRouterType 1032 }
hh3cevtModuleRt-CR-HIC-ET16                OBJECT IDENTIFIER ::= { hh3cevtModuleRouterType 1033 }
hh3cevtModuleRt-CR-MSFU-08A                OBJECT IDENTIFIER ::= { hh3cevtModuleRouterType 1034 }
hh3cevtModuleRt-CR-SFU-20C                 OBJECT IDENTIFIER ::= { hh3cevtModuleRouterType 1035 }
hh3cevtModuleRt-SIC-M2-SATA                OBJECT IDENTIFIER ::= { hh3cevtModuleRouterType 1036 }
hh3cevtModuleRtNSQM1MPULC                  OBJECT IDENTIFIER ::= { hh3cevtModuleRouterType 1037 }
hh3cevtModuleRt-NSUM1QG1A                  OBJECT IDENTIFIER ::= { hh3cevtModuleRouterType 1038 }
hh3cevtModuleRt-NSUM1TG4A                  OBJECT IDENTIFIER ::= { hh3cevtModuleRouterType 1039 }
hh3cevtModuleRt-NSUM1GP4A                  OBJECT IDENTIFIER ::= { hh3cevtModuleRouterType 1040 }
hh3cevtModuleRt-FIP-30                     OBJECT IDENTIFIER ::= { hh3cevtModuleRouterType 1041 }  -- Flexible Interface Platform Module 30,2 MIC-X Slots, 4*10GBASE-R SFP+ Ports, and 16*1000BASE-X SFP Ports
hh3cevtModuleRt-RISER-FHFL-X16             OBJECT IDENTIFIER ::= { hh3cevtModuleRouterType 1042 }  ---SR6602-I PCIe Riser Module(FHFL, 1 PCIe X16 Slot)
hh3cevtModuleRt-RISER-GPU                  OBJECT IDENTIFIER ::= { hh3cevtModuleRouterType 1043 } --- Graphic Processiong Unit On Riser Card
hh3cevtModuleRt-RISER-RAID                 OBJECT IDENTIFIER ::= { hh3cevtModuleRouterType 1044 } --- Redundant Arrays of Independent Disks On Riser Card
hh3cevtModuleRt-CR-19K-LPU-8004            OBJECT IDENTIFIER ::= { hh3cevtModuleRouterType 1045 }  -- CR Flexible Interface Module 8004
hh3cevtModuleRt-CR-19K-MPU-08B             OBJECT IDENTIFIER ::= { hh3cevtModuleRouterType 1046 }  -- CR Main Processing Unit B for 08 Chassis
hh3cevtModuleRt-CR-HIC-CQ02                OBJECT IDENTIFIER ::= { hh3cevtModuleRouterType 1047 }  -- 2-Port 100-GigabitEthernet Optical Interface HIC-Module
hh3cevtModuleRt-NSQM1ISPAXA1               OBJECT IDENTIFIER ::= { hh3cevtModuleRouterType 1048 }  -- 2-Port 10/100/1000BASE-T and 2-Port 1000BASE-X SFP Interface Module
hh3cevtModuleRt-NSQM1ISPAXB1               OBJECT IDENTIFIER ::= { hh3cevtModuleRouterType 1049 }  -- 2-Port 10/100/1000BASE-T and 2-Port 1000BASE-X SFP Interface Module
hh3cevtModuleRt-CR-USBDISK                 OBJECT IDENTIFIER ::= { hh3cevtModuleRouterType 1050 }  -- CR USB DISK
hh3cevtModuleRt-SIC-4RS                    OBJECT IDENTIFIER ::= { hh3cevtModuleRouterType 1051 }  -- H3C MSR,RTU1S4RS,4-Port Asynchronous Serial Interface SIC Interface Board,2*1
hh3cevtModuleRt-NSQM1MPULC-Z               OBJECT IDENTIFIER ::= { hh3cevtModuleRouterType 1052 }
hh3cevtModuleRt-CR-18K-MPU-16B             OBJECT IDENTIFIER ::= { hh3cevtModuleRouterType 1053 } -- CR Main Processing Unit B for 18 Chassis
hh3cevtModuleRt-CR-18K-SFU-16C             OBJECT IDENTIFIER ::= { hh3cevtModuleRouterType 1054 } -- CR Switching Fabric Unit(HC) C for 18 Chassis
hh3cevtModuleRt-DS-3RH-4T                  OBJECT IDENTIFIER ::= { hh3cevtModuleRouterType 1055 } -- H Series Enterprise Router 4 Gigabit Electrical Port SIC Module
hh3cevtModuleRt-HRIC-CQ1F                  OBJECT IDENTIFIER ::= { hh3cevtModuleRouterType 1056 } -- 1-Port 100-GigabitEthernet Optical Interface HRIC-Module
hh3cevtModuleRt-HRIC-LGQ2F                 OBJECT IDENTIFIER ::= { hh3cevtModuleRouterType 1057 } -- 1-Port 50-100-GE and 1-Port 50-GE Optical Interface HRIC-Module
hh3cevtModuleRt-CR-HIC-CLGQ04              OBJECT IDENTIFIER ::= { hh3cevtModuleRouterType 1058 } -- CR 4-Port FlexE Optical SubCard
hh3cevtModuleRt-NSQM1QG1A-Z                OBJECT IDENTIFIER ::= { hh3cevtModuleRouterType 1059 } -- 1-Port 40GBASE Ethernet Optical Interface Module(QSFP+)
hh3cevtModuleRt-NSQM1TG4A-Z                OBJECT IDENTIFIER ::= { hh3cevtModuleRouterType 1060 } -- 4-Port 10GBASE Ethernet Optical Interface Module(SFP+)
hh3cevtModuleRt-NSQM1GP4A-Z                OBJECT IDENTIFIER ::= { hh3cevtModuleRouterType 1061 } -- 4-Port Gigabit Ethernet Optical Interface Module(SFP)
hh3cevtModuleRt-CR-LPU-8004                OBJECT IDENTIFIER ::= { hh3cevtModuleRouterType 1062 }  -- CR Flexible Interface Module 8004
hh3cevtModuleRt-MPU-100-G                  OBJECT IDENTIFIER ::= { hh3cevtModuleRouterType 1063 } -- MPU-100-G Main Processing Unit
hh3cevtModuleRt-SPU-300-G                  OBJECT IDENTIFIER ::= { hh3cevtModuleRouterType 1064 } -- SPU-300-G Service Processing Unit
hh3cevtModuleRt-CR-19K-MPU-20C             OBJECT IDENTIFIER ::= { hh3cevtModuleRouterType 1065 } -- CR X86 MPU  for 20 Chassis
hh3cevtModuleRt-CR-18K-MPU-16C             OBJECT IDENTIFIER ::= { hh3cevtModuleRouterType 1066 } -- CR X86 MPU  for 18 Chassis
hh3cevtModuleRt-SIC-5G                     OBJECT IDENTIFIER ::= { hh3cevtModuleRouterType 1067 } -- H3C MSR,RTUM1S5G,5G(5G NR/NSA/SA/4G FDD/TDD LTE-A/3G WCDMA,Sub6,GNSS)SIC Module,Domestic&Overseas Version
hh3cevtModuleRt-RSU-400                    OBJECT IDENTIFIER ::= { hh3cevtModuleRouterType 1068 } -- Router Switch Unit 400
hh3cevtModuleRt-HRIC-XP8-H                 OBJECT IDENTIFIER ::= { hh3cevtModuleRouterType 1069 } -- 8-Port 10-GigabitEthernet Optical Interface HRIC-Module
hh3cevtModuleRt-BBU3120-MCBM2LMCMB1        OBJECT IDENTIFIER ::= { hh3cevtModuleRouterType 1072 } -- BBU Processing Unit
hh3cevtModuleRt-BBU3120-MCBM2LBBMB1        OBJECT IDENTIFIER ::= { hh3cevtModuleRouterType 1073 } -- BBU Processing Unit
hh3cevtModuleRt-HMIM-2POS                  OBJECT IDENTIFIER ::= { hh3cevtModuleRouterType 1074 } -- 2 Port POS-STM1/4 Interface














-- 1000 to 4999 for united assignment
--


--
-- reserved for other brands from 5000
--
hpevtModuleRt-SIC-EPRI                     OBJECT IDENTIFIER ::= { hh3cevtModuleRouterType 5000 } -- 1-Port E1/CE1/PRI Interface Card
hpevtModuleRt-MIM-1E1-V2                   OBJECT IDENTIFIER ::= { hh3cevtModuleRouterType 5001 } -- 1-Port CE1/PRI Interface Module
hpevtModuleRt-MIM-1E1-F-V2                 OBJECT IDENTIFIER ::= { hh3cevtModuleRouterType 5002 } -- 1-Port E1 & Fractional E1 Interface Module
hpevtModuleRt-MIM-2E1-F-V2                 OBJECT IDENTIFIER ::= { hh3cevtModuleRouterType 5003 } -- 2-Port E1 & Fractional E1 Interface Module
hpevtModuleRt-MIM-4E1-F-V2                 OBJECT IDENTIFIER ::= { hh3cevtModuleRouterType 5004 } -- 4-Port E1 & Fractional E1 Interface Module
hpevtModuleRt-MIM-8E1-75                   OBJECT IDENTIFIER ::= { hh3cevtModuleRouterType 5005 } -- 8-port E1/CE1/PRI Module(75ohm)
hpevtModuleRt-MIM-8E1-75-F                 OBJECT IDENTIFIER ::= { hh3cevtModuleRouterType 5006 } -- 8-Port E1 Module-Fractional(75ohm)
hpevtModuleRt-MIM-8T1                      OBJECT IDENTIFIER ::= { hh3cevtModuleRouterType 5007 } -- 8-Port T1 Interface Module
hpevtModuleRt-MIM-8T1-F                    OBJECT IDENTIFIER ::= { hh3cevtModuleRouterType 5008 } -- 8-Port T1 Module-Fractional
hpevtModuleRt-MIM-IMA-8E1-75               OBJECT IDENTIFIER ::= { hh3cevtModuleRouterType 5009 } -- 8-Port E1 ATM IMA Interface Module(75ohm)
hpevtModuleRt-FIC-2E1-V3                   OBJECT IDENTIFIER ::= { hh3cevtModuleRouterType 5010 } -- 2-Port E1/CE1/PRI Interface FIC Module
hpevtModuleRt-FIC-IMA-8T1-V2               OBJECT IDENTIFIER ::= { hh3cevtModuleRouterType 5011 } -- 8-Port T1 ATM IMA Interface FIC Module
hh3cevtModuleRtCN-MSU-X3                   OBJECT IDENTIFIER ::= { hh3cevtModuleRouterType 5012 } -- Mainboard Switch Unit X3
hh3cevtModuleRtCN-FSP-660                  OBJECT IDENTIFIER ::= { hh3cevtModuleRouterType 5013 } -- Flexible Service Platform 660
hh3cevtModuleRtCN-MIC-X-XP4W               OBJECT IDENTIFIER ::= { hh3cevtModuleRouterType 5014 } -- 4-Port 1000BASE-R-SFP+ Optical Multi-functional Interface Card
hh3cevtModuleRtCN-MIC-X-GP8                OBJECT IDENTIFIER ::= { hh3cevtModuleRouterType 5015 } -- 8-Port 1000BASE-X Optical Multi-functional Interface Card
hh3cevtModuleRtCN-MIC-X-GT8                OBJECT IDENTIFIER ::= { hh3cevtModuleRouterType 5016 } -- 8-Port 10/100/1000BASE-T Electronic Multi-functional Interface Card

-- hh3cevtModuleSwitchType cards are slot-cards specific to the Switch.
hh3cevtModuleSwitchType  OBJECT IDENTIFIER ::= { hh3cevtModule 4 }

--hh3cevtModuleNULL(0),
hh3cevtModuleSw-10OR100M                    OBJECT IDENTIFIER ::= { hh3cevtModuleSwitchType 1 }
hh3cevtModuleSw-1000BASE-LX-SM              OBJECT IDENTIFIER ::= { hh3cevtModuleSwitchType 2 }
hh3cevtModuleSw-1000BASE-SX-MM              OBJECT IDENTIFIER ::= { hh3cevtModuleSwitchType 3 }
hh3cevtModuleSw-1000BASE-TX                 OBJECT IDENTIFIER ::= { hh3cevtModuleSwitchType 4 }
hh3cevtModuleSw-100M-SINGLEMODE-FX          OBJECT IDENTIFIER ::= { hh3cevtModuleSwitchType 5 }
hh3cevtModuleSw-100M-MULTIMODE-FX           OBJECT IDENTIFIER ::= { hh3cevtModuleSwitchType 6 }
hh3cevtModuleSw-100M-100BASE-TX             OBJECT IDENTIFIER ::= { hh3cevtModuleSwitchType 7 }
hh3cevtModuleSw-100M-HUB                    OBJECT IDENTIFIER ::= { hh3cevtModuleSwitchType 8 }
hh3cevtModuleSw-VDSL                        OBJECT IDENTIFIER ::= { hh3cevtModuleSwitchType 9 }
hh3cevtModuleSw-STACK                       OBJECT IDENTIFIER ::= { hh3cevtModuleSwitchType 10 }
hh3cevtModuleSw-1000BASE-ZENITH-FX          OBJECT IDENTIFIER ::= { hh3cevtModuleSwitchType 11 }
hh3cevtModuleSw-1000BASE-LONG-FX            OBJECT IDENTIFIER ::= { hh3cevtModuleSwitchType 12 }
hh3cevtModuleSw-ADSL                        OBJECT IDENTIFIER ::= { hh3cevtModuleSwitchType 13 }
hh3cevtModuleSw-4T10OR100-4FX100SM          OBJECT IDENTIFIER ::= { hh3cevtModuleSwitchType 14 }
hh3cevtModuleSw-4T10OR100-4FX100MM          OBJECT IDENTIFIER ::= { hh3cevtModuleSwitchType 15 }
hh3cevtModuleSw-VSPL                        OBJECT IDENTIFIER ::= { hh3cevtModuleSwitchType 16 }
hh3cevtModuleSw-ASPL                        OBJECT IDENTIFIER ::= { hh3cevtModuleSwitchType 17 }
hh3cevtModuleSw-1000M-SFP                   OBJECT IDENTIFIER ::= { hh3cevtModuleSwitchType 18 }
hh3cevtModuleSw-LS82O2CM                    OBJECT IDENTIFIER ::= { hh3cevtModuleSwitchType 19 }
hh3cevtModuleSw-LS82P2CM                    OBJECT IDENTIFIER ::= { hh3cevtModuleSwitchType 20 }
hh3cevtModuleSw-LS82O4GM                    OBJECT IDENTIFIER ::= { hh3cevtModuleSwitchType 21 }
hh3cevtModuleSw-LS82GB4C                    OBJECT IDENTIFIER ::= { hh3cevtModuleSwitchType 22 }
hh3cevtModuleSw-LS82GT4C                    OBJECT IDENTIFIER ::= { hh3cevtModuleSwitchType 23 }
hh3cevtModuleSw-LS82ST4C                    OBJECT IDENTIFIER ::= { hh3cevtModuleSwitchType 24 }
hh3cevtModuleSw-BOARD-LS82DSPU              OBJECT IDENTIFIER ::= { hh3cevtModuleSwitchType 25 }
hh3cevtModuleSw-BOARD-LS81GP8U              OBJECT IDENTIFIER ::= { hh3cevtModuleSwitchType 26 }
hh3cevtModuleSw-BOARD-LS82GT20              OBJECT IDENTIFIER ::= { hh3cevtModuleSwitchType 27 }
hh3cevtModuleSw-BOARD-LS82FE48              OBJECT IDENTIFIER ::= { hh3cevtModuleSwitchType 28 }
hh3cevtModuleSw-LS82T24B                    OBJECT IDENTIFIER ::= { hh3cevtModuleSwitchType 29 }
hh3cevtModuleSw-LSB1SRPA                    OBJECT IDENTIFIER ::= { hh3cevtModuleSwitchType 30 }
hh3cevtModuleSw-LSB1FT48A                   OBJECT IDENTIFIER ::= { hh3cevtModuleSwitchType 31 }
hh3cevtModuleSw-LSB1FT48B                   OBJECT IDENTIFIER ::= { hh3cevtModuleSwitchType 32 }
hh3cevtModuleSw-LSB1F48GA                   OBJECT IDENTIFIER ::= { hh3cevtModuleSwitchType 33 }
hh3cevtModuleSw-LSB1F48GB                   OBJECT IDENTIFIER ::= { hh3cevtModuleSwitchType 34 }
hh3cevtModuleSw-LSB1FP20A                   OBJECT IDENTIFIER ::= { hh3cevtModuleSwitchType 35 }
hh3cevtModuleSw-LSB1FP20B                   OBJECT IDENTIFIER ::= { hh3cevtModuleSwitchType 36 }
hh3cevtModuleSw-FT48A                       OBJECT IDENTIFIER ::= { hh3cevtModuleSwitchType 37 }
hh3cevtModuleSw-GP4U                        OBJECT IDENTIFIER ::= { hh3cevtModuleSwitchType 38 }
hh3cevtModuleSw-GP2U                        OBJECT IDENTIFIER ::= { hh3cevtModuleSwitchType 39 }
hh3cevtModuleSw-TGX1A                       OBJECT IDENTIFIER ::= { hh3cevtModuleSwitchType 40 }
hh3cevtModuleSw-1000BASE-LX-SM-IR-SC        OBJECT IDENTIFIER ::= { hh3cevtModuleSwitchType 41 }
hh3cevtModuleSw-1000BASE-SX-MM-SR-SC        OBJECT IDENTIFIER ::= { hh3cevtModuleSwitchType 42 }
hh3cevtModuleSw-1000BASE-T-RJ45             OBJECT IDENTIFIER ::= { hh3cevtModuleSwitchType 43 }
hh3cevtModuleSw-100BASE-FX-SM-IR-SC         OBJECT IDENTIFIER ::= { hh3cevtModuleSwitchType 44 }
hh3cevtModuleSw-100BASE-FX-MM-SR-SC         OBJECT IDENTIFIER ::= { hh3cevtModuleSwitchType 45 }
hh3cevtModuleSw-GIGA-STACK-1M-PC            OBJECT IDENTIFIER ::= { hh3cevtModuleSwitchType 46 }
hh3cevtModuleSw-1000BASE-LX-SM-VLR-LC       OBJECT IDENTIFIER ::= { hh3cevtModuleSwitchType 47 }
hh3cevtModuleSw-1000BASE-LX-SM-LR-LC        OBJECT IDENTIFIER ::= { hh3cevtModuleSwitchType 48 }
hh3cevtModuleSw-100BASE-FX-SM-LR-SC         OBJECT IDENTIFIER ::= { hh3cevtModuleSwitchType 49 }
hh3cevtModuleSw-1000BASE-X-GBIC             OBJECT IDENTIFIER ::= { hh3cevtModuleSwitchType 50 }
hh3cevtModuleSw-100M-SINGLEMODE-FX-LC       OBJECT IDENTIFIER ::= { hh3cevtModuleSwitchType 51 }
hh3cevtModuleSw-100M-MULTIMODE-FX-LC        OBJECT IDENTIFIER ::= { hh3cevtModuleSwitchType 52 }
hh3cevtModuleSw-1000BASE-4SFP               OBJECT IDENTIFIER ::= { hh3cevtModuleSwitchType 53 }
hh3cevtModuleSw-1000BASE-4GBIC              OBJECT IDENTIFIER ::= { hh3cevtModuleSwitchType 54 }
hh3cevtModuleSw-1000BASE-FIXED-4SFP         OBJECT IDENTIFIER ::= { hh3cevtModuleSwitchType 55 }
hh3cevtModuleSw-1000BASE-FIXED-4GBIC        OBJECT IDENTIFIER ::= { hh3cevtModuleSwitchType 56 }
hh3cevtModuleSw-LSB1GP12A                   OBJECT IDENTIFIER ::= { hh3cevtModuleSwitchType 57 }
hh3cevtModuleSw-LSB1GP12B                   OBJECT IDENTIFIER ::= { hh3cevtModuleSwitchType 58 }
hh3cevtModuleSw-LSB1TGX1A                   OBJECT IDENTIFIER ::= { hh3cevtModuleSwitchType 59 }
hh3cevtModuleSw-LSB1TGX1B                   OBJECT IDENTIFIER ::= { hh3cevtModuleSwitchType 60 }
hh3cevtModuleSw-LSB1P4G8A                   OBJECT IDENTIFIER ::= { hh3cevtModuleSwitchType 61 }
hh3cevtModuleSw-LSB1P4G8B                   OBJECT IDENTIFIER ::= { hh3cevtModuleSwitchType 62 }
hh3cevtModuleSw-LSB1A4G8A                   OBJECT IDENTIFIER ::= { hh3cevtModuleSwitchType 63 }
hh3cevtModuleSw-LSB1A4G8B                   OBJECT IDENTIFIER ::= { hh3cevtModuleSwitchType 64 }
hh3cevtModuleSw-FT48C                       OBJECT IDENTIFIER ::= { hh3cevtModuleSwitchType 65 }
hh3cevtModuleSw-FP20                        OBJECT IDENTIFIER ::= { hh3cevtModuleSwitchType 66 }
hh3cevtModuleSw-BOARD-LS81FT48              OBJECT IDENTIFIER ::= { hh3cevtModuleSwitchType 67 }
hh3cevtModuleSw-BOARD-LS81GB8U              OBJECT IDENTIFIER ::= { hh3cevtModuleSwitchType 68 }
hh3cevtModuleSw-BOARD-LS81GT8U              OBJECT IDENTIFIER ::= { hh3cevtModuleSwitchType 69 }
hh3cevtModuleSw-BOARD-LS81FS24              OBJECT IDENTIFIER ::= { hh3cevtModuleSwitchType 70 }
hh3cevtModuleSw-BOARD-LS81FM24              OBJECT IDENTIFIER ::= { hh3cevtModuleSwitchType 71 }
hh3cevtModuleSw-BOARD-LS82GP20              OBJECT IDENTIFIER ::= { hh3cevtModuleSwitchType 72 }
hh3cevtModuleSw-LSB1SRPB                    OBJECT IDENTIFIER ::= { hh3cevtModuleSwitchType 73 }
hh3cevtModuleSw-LSB1F32GA                   OBJECT IDENTIFIER ::= { hh3cevtModuleSwitchType 74 }
hh3cevtModuleSw-LSB1F32GB                   OBJECT IDENTIFIER ::= { hh3cevtModuleSwitchType 75 }
hh3cevtModuleSw-LSB2FT48A                   OBJECT IDENTIFIER ::= { hh3cevtModuleSwitchType 76 }
hh3cevtModuleSw-LSB2FT48B                   OBJECT IDENTIFIER ::= { hh3cevtModuleSwitchType 77 }
hh3cevtModuleSw-LSB1GT12A                   OBJECT IDENTIFIER ::= { hh3cevtModuleSwitchType 78 }
hh3cevtModuleSw-LSB1GT12B                   OBJECT IDENTIFIER ::= { hh3cevtModuleSwitchType 79 }
hh3cevtModuleSw-PC4U                        OBJECT IDENTIFIER ::= { hh3cevtModuleSwitchType 80 }
hh3cevtModuleSw-FT32A                       OBJECT IDENTIFIER ::= { hh3cevtModuleSwitchType 81 }
hh3cevtModuleSw-GT4U                        OBJECT IDENTIFIER ::= { hh3cevtModuleSwitchType 82 }
hh3cevtModuleSw-BOARD-LS83FP20A             OBJECT IDENTIFIER ::= { hh3cevtModuleSwitchType 83 }
hh3cevtModuleSw-BOARD-LS82HGMU              OBJECT IDENTIFIER ::= { hh3cevtModuleSwitchType 84 }
hh3cevtModuleSw-LSB1GP8TB                   OBJECT IDENTIFIER ::= { hh3cevtModuleSwitchType 85 }
hh3cevtModuleSw-LSB1GP8TC                   OBJECT IDENTIFIER ::= { hh3cevtModuleSwitchType 86 }
hh3cevtModuleSw-LSB1GT8PB                   OBJECT IDENTIFIER ::= { hh3cevtModuleSwitchType 87 }
hh3cevtModuleSw-LSB1GT8PC                   OBJECT IDENTIFIER ::= { hh3cevtModuleSwitchType 88 }
hh3cevtModuleSw-LSB1FT48C                   OBJECT IDENTIFIER ::= { hh3cevtModuleSwitchType 89 }
hh3cevtModuleSw-LSB1FP20C                   OBJECT IDENTIFIER ::= { hh3cevtModuleSwitchType 90 }
hh3cevtModuleSw-LSB1F32GC                   OBJECT IDENTIFIER ::= { hh3cevtModuleSwitchType 91 }
hh3cevtModuleSw-LSB1GT12C                   OBJECT IDENTIFIER ::= { hh3cevtModuleSwitchType 92 }
hh3cevtModuleSw-LSB1GP12C                   OBJECT IDENTIFIER ::= { hh3cevtModuleSwitchType 93 }
hh3cevtModuleSw-LSB1P4G8C                   OBJECT IDENTIFIER ::= { hh3cevtModuleSwitchType 94 }
hh3cevtModuleSw-LSB1TGX1C                   OBJECT IDENTIFIER ::= { hh3cevtModuleSwitchType 95 }
hh3cevtModuleSw-LSB1GT24B                   OBJECT IDENTIFIER ::= { hh3cevtModuleSwitchType 96 }
hh3cevtModuleSw-LSB1GT24C                   OBJECT IDENTIFIER ::= { hh3cevtModuleSwitchType 97 }
hh3cevtModuleSw-LSB1GP24B                   OBJECT IDENTIFIER ::= { hh3cevtModuleSwitchType 98 }
hh3cevtModuleSw-LSB1GP24C                   OBJECT IDENTIFIER ::= { hh3cevtModuleSwitchType 99 }
hh3cevtModuleSw-LSB1XP2B                    OBJECT IDENTIFIER ::= { hh3cevtModuleSwitchType 100 }
hh3cevtModuleSw-LSB1XP2C                    OBJECT IDENTIFIER ::= { hh3cevtModuleSwitchType 101 }
hh3cevtModuleSw-LSB1GV48B                   OBJECT IDENTIFIER ::= { hh3cevtModuleSwitchType 102 }
hh3cevtModuleSw-LSB1GV48C                   OBJECT IDENTIFIER ::= { hh3cevtModuleSwitchType 103 }
hh3cevtModuleSw-LSB1SRPC                    OBJECT IDENTIFIER ::= { hh3cevtModuleSwitchType 104 }
hh3cevtModuleSw-LSB1SRP1N0                  OBJECT IDENTIFIER ::= { hh3cevtModuleSwitchType 105 }
hh3cevtModuleSw-LSB1SRP1N1                  OBJECT IDENTIFIER ::= { hh3cevtModuleSwitchType 106 }
hh3cevtModuleSw-LSB1SRP1N2                  OBJECT IDENTIFIER ::= { hh3cevtModuleSwitchType 107 }
hh3cevtModuleSw-GT24                        OBJECT IDENTIFIER ::= { hh3cevtModuleSwitchType 108 }
hh3cevtModuleSw-GP24                        OBJECT IDENTIFIER ::= { hh3cevtModuleSwitchType 109 }
hh3cevtModuleSw-XP2                         OBJECT IDENTIFIER ::= { hh3cevtModuleSwitchType 110 }
hh3cevtModuleSw-GV48                        OBJECT IDENTIFIER ::= { hh3cevtModuleSwitchType 111 }
hh3cevtModuleSw-LSG1GP8U                    OBJECT IDENTIFIER ::= { hh3cevtModuleSwitchType 112 }
hh3cevtModuleSw-LSG1GT8U                    OBJECT IDENTIFIER ::= { hh3cevtModuleSwitchType 113 }
hh3cevtModuleSw-LSG1TG1U                    OBJECT IDENTIFIER ::= { hh3cevtModuleSwitchType 114 }
hh3cevtModuleSw-LSG1TD1U                    OBJECT IDENTIFIER ::= { hh3cevtModuleSwitchType 115 }
hh3cevtModuleSw-LSB2FT48C                   OBJECT IDENTIFIER ::= { hh3cevtModuleSwitchType 116 } -- 48-Ports 100Base-TX Ethernet Interface module C
hh3cevtModuleSw-LSB1GT48B                   OBJECT IDENTIFIER ::= { hh3cevtModuleSwitchType 117 } -- 48-Ports 10/100/1000Base-T Ethernet Interface Module B
hh3cevtModuleSw-LSB1GT48C                   OBJECT IDENTIFIER ::= { hh3cevtModuleSwitchType 118 } -- 48-Ports 10/100/1000Base-T Ethernet Interface Module C
hh3cevtModuleSw-LS81GT48                    OBJECT IDENTIFIER ::= { hh3cevtModuleSwitchType 119 } -- 48 Port Gigabit Ethernet Electric Interface Unit
hh3cevtModuleSw-LS81SRPG0                   OBJECT IDENTIFIER ::= { hh3cevtModuleSwitchType 120 } -- Salience III, Switch and Route Processing Board
hh3cevtModuleSw-LS81SRPG1                   OBJECT IDENTIFIER ::= { hh3cevtModuleSwitchType 121 } -- Salience III Plus
hh3cevtModuleSw-LS81SRPG2                   OBJECT IDENTIFIER ::= { hh3cevtModuleSwitchType 122 } -- Salience III Lite
hh3cevtModuleSw-LS81SRPG3                   OBJECT IDENTIFIER ::= { hh3cevtModuleSwitchType 123 } -- Salience III Edge

hh3cevtModuleSw-SR01SRPUB                   OBJECT IDENTIFIER ::= { hh3cevtModuleSwitchType 125 } -- Switching and Route Processing Unit
hh3cevtModuleSw-SR01SRPUA                   OBJECT IDENTIFIER ::= { hh3cevtModuleSwitchType 126 } -- Switching and Route Processing Unit
hh3cevtModuleSw-SR01GP12L                   OBJECT IDENTIFIER ::= { hh3cevtModuleSwitchType 127 } -- 12-Port 1000Base-X Ethernet SFP Optical Interface Line Card(L)
hh3cevtModuleSw-SR01GP12W                   OBJECT IDENTIFIER ::= { hh3cevtModuleSwitchType 128 } -- 12-Port 1000Base-X Ethernet SFP Optical Interface Line Card(W)
hh3cevtModuleSw-SR01FT48L                   OBJECT IDENTIFIER ::= { hh3cevtModuleSwitchType 129 } -- 48-Port 10/100Base-TX Ethernet RJ45 Electrical Interface Line Card (L)
hh3cevtModuleSw-SR01FT48W                   OBJECT IDENTIFIER ::= { hh3cevtModuleSwitchType 130 } -- 48-Port 10/100Base-TX Ethernet RJ45 Electrical Interface Line Card (W)
hh3cevtModuleSw-SR01XK1W                    OBJECT IDENTIFIER ::= { hh3cevtModuleSwitchType 131 } -- 1-Port 10GBase-R Ethernet XENPAK Optical Interface Line Card (W)
hh3cevtModuleSw-SR01FP20W                   OBJECT IDENTIFIER ::= { hh3cevtModuleSwitchType 132 } -- 20-Port 100Base-FX Ethernet SFP Optical Interface Line Card (W)
hh3cevtModuleSw-SR01GT12W                   OBJECT IDENTIFIER ::= { hh3cevtModuleSwitchType 133 } -- 12-Port 10/100/1000Base-T Ethernet RJ45 Electrical Interface Line Card (W)
hh3cevtModuleSw-SR01F32GL                   OBJECT IDENTIFIER ::= { hh3cevtModuleSwitchType 134 } -- 32-Port 10/100Base-TX Ethernet RJ45 Electrical Interface + 4-Port 1000Base-X Ethernet SFP Optical interface Line Card (L)
hh3cevtModuleSw-SR01F32GW                   OBJECT IDENTIFIER ::= { hh3cevtModuleSwitchType 135 } -- 32-Port 10/100Base-TX Ethernet RJ45 Electrical Interface  + 4-Port 1000Base-X  Ethernet SFP Optical interface Line Card (W)
hh3cevtModuleSw-SR01GT8PL                   OBJECT IDENTIFIER ::= { hh3cevtModuleSwitchType 136 } -- 8-Port 10/100/1000Base-T Ethernet RJ45 Electrical Interface + 4-Port 1000Base-X Ethernet SFP Optical Line Card (L)
hh3cevtModuleSw-SR01GT8PW                   OBJECT IDENTIFIER ::= { hh3cevtModuleSwitchType 137 } -- 8-Port 10/100/1000Base-T Ethernet RJ45 Electrical Interface + 4-Port 1000Base-X Ethernet SFP Optical Line Card (W)
hh3cevtModuleSw-SR01P4G8W                   OBJECT IDENTIFIER ::= { hh3cevtModuleSwitchType 138 } -- 4-Port 155M POS Optical Interface + 8-Port 1000Base-X Ethernet SFP Optical Interface Line Card (W)
hh3cevtModuleSw-LSA1FP8U                    OBJECT IDENTIFIER ::= { hh3cevtModuleSwitchType 139 } -- 8 Ports 100Base-FX Ethernet SFP Card
hh3cevtModuleSw-LSB1SP4B                    OBJECT IDENTIFIER ::= { hh3cevtModuleSwitchType 140 } -- 4-Port OC-48 POS SFP Optical Interface Board B
hh3cevtModuleSw-LSB1SP4C                    OBJECT IDENTIFIER ::= { hh3cevtModuleSwitchType 141 } -- 4-Port OC-48 POS SFP Optical Interface Board C
hh3cevtModuleSw-LSB1UP1B                    OBJECT IDENTIFIER ::= { hh3cevtModuleSwitchType 142 } -- 1-Port OC-192 POS XFP Optical Interface Board B
hh3cevtModuleSw-LSB1UP1C                    OBJECT IDENTIFIER ::= { hh3cevtModuleSwitchType 143 } -- 1-Port OC-192 POS XFP Optical Interface Board C
hh3cevtModuleSw-LSB1XP4B                    OBJECT IDENTIFIER ::= { hh3cevtModuleSwitchType 144 } -- 4-Port 10GBase Ethernet XFP Optical Interface Board B
hh3cevtModuleSw-LSB1XP4C                    OBJECT IDENTIFIER ::= { hh3cevtModuleSwitchType 145 } -- 4-Port 10GBase Ethernet XFP Optical Interface Board C
hh3cevtModuleSw-SP4                         OBJECT IDENTIFIER ::= { hh3cevtModuleSwitchType 146 } -- 4-Port OC-48 POS SFP Optical Interface Module
hh3cevtModuleSw-UP1                         OBJECT IDENTIFIER ::= { hh3cevtModuleSwitchType 147 } -- 1-Port OC-192 POS XFP Optical Interface Module
hh3cevtModuleSw-XP4                         OBJECT IDENTIFIER ::= { hh3cevtModuleSwitchType 148 } -- 4-Port 10GBase Ethernet XFP Optical Interface Module
hh3cevtModuleSw-LS81VSNP                    OBJECT IDENTIFIER ::= { hh3cevtModuleSwitchType 149 } -- VerSatile Network Processing Board
hh3cevtModuleSw-LS81T12P                    OBJECT IDENTIFIER ::= { hh3cevtModuleSwitchType 150 } -- 12-Port 1000Base-T Gigabit Ethernet Interface(RJ45)+4-Port 1000BASE-X  Gigabit Ethernet Optical Interface Board(SFP,LC)
hh3cevtModuleSw-LS81P12T                    OBJECT IDENTIFIER ::= { hh3cevtModuleSwitchType 151 } -- 12-Port 1000BASE-X Gigabit Ethernet Optical Interface(SFP,LC)+4-Port 1000BASE-T Gigabit Ethernet Interface Board(RJ45)
hh3cevtModuleSw-LS81GP8UB                   OBJECT IDENTIFIER ::= { hh3cevtModuleSwitchType 152 } -- 8-Port 1000M Ethernet Optical Interface Board(SFP,LC),LC Connector
hh3cevtModuleSw-LS81FT48E                   OBJECT IDENTIFIER ::= { hh3cevtModuleSwitchType 153 } -- 48-Port 100M Ethernet Electrical Interface Switch Unit(RJ45)
hh3cevtModuleSw-LS81GP4UB                   OBJECT IDENTIFIER ::= { hh3cevtModuleSwitchType 154 } -- 4-Port 1000M Ethernet Optical Interface Board(SFP,LC)
hh3cevtModuleSw-LS81GT8UE                   OBJECT IDENTIFIER ::= { hh3cevtModuleSwitchType 155 } -- 8-Port 1000M Ethernet Electrical Interface Switch Unit (RJ45)
hh3cevtModuleSw-LS81GT48A                   OBJECT IDENTIFIER ::= { hh3cevtModuleSwitchType 156 } -- 48 Port Gigabit Ethernet Electric Interface Unit
hh3cevtModuleSw-LS81FP48                    OBJECT IDENTIFIER ::= { hh3cevtModuleSwitchType 157 } -- 48 Port 100M Ethernet Optical Interface Board(SFP,LC)
hh3cevtModuleSw-LSB1XK1B                    OBJECT IDENTIFIER ::= { hh3cevtModuleSwitchType 158 } -- 1-Port 10GBase-R Ethernet XENPAK Optical Interface Board B
hh3cevtModuleSw-LSB1XK1C                    OBJECT IDENTIFIER ::= { hh3cevtModuleSwitchType 159 } -- 1-Port 10GBase-R Ethernet XENPAK Optical Interface Board C
hh3cevtModuleSw-SR01SRPUC                   OBJECT IDENTIFIER ::= { hh3cevtModuleSwitchType 160 } -- Switching and Route Processing Unit C
hh3cevtModuleSw-SR01SRPUD                   OBJECT IDENTIFIER ::= { hh3cevtModuleSwitchType 161 } -- Switching and Route Processing Unit D
hh3cevtModuleSw-SR01SRPUE                   OBJECT IDENTIFIER ::= { hh3cevtModuleSwitchType 162 } -- Switching and Route Processing Unit E
hh3cevtModuleSw-LSB1SRP1N3                  OBJECT IDENTIFIER ::= { hh3cevtModuleSwitchType 163 } -- Switching and Route Process Unit, Clock Module
hh3cevtModuleSw-LSB1VP2B                    OBJECT IDENTIFIER ::= { hh3cevtModuleSwitchType 164 } -- 2*10G Resilient Packet Ring Interface Line Card
hh3cevtModuleSw-LSB1NATB                    OBJECT IDENTIFIER ::= { hh3cevtModuleSwitchType 165 } -- NAT Service Processing Card (B)
hh3cevtModuleSw-LSB1VPNB                    OBJECT IDENTIFIER ::= { hh3cevtModuleSwitchType 166 } -- VPN Service Processing Card (B)
hh3cevtModuleSw-LSGP8P                      OBJECT IDENTIFIER ::= { hh3cevtModuleSwitchType 167 } -- 8-Port 1000M SFP Module
hh3cevtModuleSw-LSXK1P                      OBJECT IDENTIFIER ::= { hh3cevtModuleSwitchType 168 } -- 1-Port 10G Xenpak Module
hh3cevtModuleSw-LSXP2P                      OBJECT IDENTIFIER ::= { hh3cevtModuleSwitchType 169 } -- 2-Port 10G XFP Module
hh3cevtModuleSw-LS81FT48F                   OBJECT IDENTIFIER ::= { hh3cevtModuleSwitchType 170 } -- 48-Port 100M Ethernet Electrical Interface Switch Unit(RJ45)
hh3cevtModuleSw-LS81PT8G                    OBJECT IDENTIFIER ::= { hh3cevtModuleSwitchType 171 } -- 8 Port 1000BASE-X Gigabit Passive Optical Line Interface Board
hh3cevtModuleSw-LS81PT4G                    OBJECT IDENTIFIER ::= { hh3cevtModuleSwitchType 172 } -- 4 Port 1000BASE-X Gigabit Passive Optical Line Interface Board
hh3cevtModuleSw-LSSTK24G                    OBJECT IDENTIFIER ::= { hh3cevtModuleSwitchType 173 } -- 24G Stacking Ports Module
hh3cevtModuleSw-LS82GT20A                   OBJECT IDENTIFIER ::= { hh3cevtModuleSwitchType 174 } -- 20-Port 1000Base-T Gigabit Ethernet Electrical Interface Board(RJ45), BCM5697
hh3cevtModuleSw-LS82GP20A                   OBJECT IDENTIFIER ::= { hh3cevtModuleSwitchType 175 } -- 20-Port 1000BASE-X Gigabit Ethernet Optical Interface Board(SFP,LC), BCM5697
hh3cevtModuleSw-LS81TGX1C                   OBJECT IDENTIFIER ::= { hh3cevtModuleSwitchType 176 } -- 1-Port 10G Base-R Ethernet Board
hh3cevtModuleSw-VP2                         OBJECT IDENTIFIER ::= { hh3cevtModuleSwitchType 177 } -- 2*10G Resilient Packet Ring Interface Module
hh3cevtModuleSw-LSA1FB8U                    OBJECT IDENTIFIER ::= { hh3cevtModuleSwitchType 178 } -- 8-Port 100Base-Fx BIDI Ethernet Board
hh3cevtModuleSw-LS81T12PE                   OBJECT IDENTIFIER ::= { hh3cevtModuleSwitchType 179 } -- 12-Port 1000Base-T GE Interface+4-Port 1000BASE-X GE Optical Interface Board(SFP,LC)
hh3cevtModuleSw-LS81P12TE                   OBJECT IDENTIFIER ::= { hh3cevtModuleSwitchType 180 } -- 12-Port 1000BASE-X GE Optical Interface(SFP,LC)+4-Port 1000 BASE-T GE Interface Board(RJ45)
hh3cevtModuleSw-LSB1SRP2N0                  OBJECT IDENTIFIER ::= { hh3cevtModuleSwitchType 181 } -- Switching and Route Process Unit,12*LPU
hh3cevtModuleSw-LSB1SRP2N3                  OBJECT IDENTIFIER ::= { hh3cevtModuleSwitchType 182 } -- Switching and Route Process Unit, Clock Module
hh3cevtModuleSw-LSB1GV48DB                  OBJECT IDENTIFIER ::= { hh3cevtModuleSwitchType 183 } -- 48 Ports 1000Base-T Ethernet Interface Line Card with POE(DB)
hh3cevtModuleSw-LSB1FW8B                    OBJECT IDENTIFIER ::= { hh3cevtModuleSwitchType 184 } -- Firewall Service Processing Board with 8GE (B)
hh3cevtModuleSw-LSB1IPSEC8B                 OBJECT IDENTIFIER ::= { hh3cevtModuleSwitchType 185 } -- VPN Service Processing Board with 8GE (B)
hh3cevtModuleSw-LSB1IDSB                    OBJECT IDENTIFIER ::= { hh3cevtModuleSwitchType 186 } -- IDS Service Processing Board (B)
hh3cevtModuleSw-LSB1IPSB                    OBJECT IDENTIFIER ::= { hh3cevtModuleSwitchType 187 } -- IPS Service Processing Board (B)
hh3cevtModuleSw-LSB2FT48CA                  OBJECT IDENTIFIER ::= { hh3cevtModuleSwitchType 188 } -- 48 Ports 100Base-TX Ethernet Line Card (CA)
hh3cevtModuleSw-LSB1FP20CA                  OBJECT IDENTIFIER ::= { hh3cevtModuleSwitchType 189 } -- 20 Ports 100Base-FX Ethernet Interface Service Card (CA)
hh3cevtModuleSw-LSB1F32GCA                  OBJECT IDENTIFIER ::= { hh3cevtModuleSwitchType 190 } -- 32 Ports FE and 4 Ports GE Line Card(CA)
hh3cevtModuleSw-LSB1P4G8CA                  OBJECT IDENTIFIER ::= { hh3cevtModuleSwitchType 191 } -- 4 Ports OC-3c POS and 8 Ports GE Line Card(CA)
hh3cevtModuleSw-LSB1GT12CA                  OBJECT IDENTIFIER ::= { hh3cevtModuleSwitchType 192 } -- 12 Ports 1000Base-T Ethernet Interface Line Card(CA)
hh3cevtModuleSw-LSB1GT24CA                  OBJECT IDENTIFIER ::= { hh3cevtModuleSwitchType 193 } -- 24 Ports 1000Base-T Ethernet Interface Line Card(CA)
hh3cevtModuleSw-LSB1GP12CA                  OBJECT IDENTIFIER ::= { hh3cevtModuleSwitchType 194 } -- 12 Ports 1000Base Ethernet Optical Interface Service Card(CA)
hh3cevtModuleSw-LSB1GP24CA                  OBJECT IDENTIFIER ::= { hh3cevtModuleSwitchType 195 } -- 24 Ports 1000Base-X Ethernet Interface Line Card (CA)
hh3cevtModuleSw-LSB1GT8PCA                  OBJECT IDENTIFIER ::= { hh3cevtModuleSwitchType 196 } -- 8 Ports 1000Base-T Ethernet Interface & 4 Ports 1000Base-X Ethernet SFP Interface Line Card(CA)
hh3cevtModuleSw-LSB1XP2CA                   OBJECT IDENTIFIER ::= { hh3cevtModuleSwitchType 197 } -- 2-Port 10GBase-R/W Ethernet XFP Optical Interface Card(CA)
hh3cevtModuleSw-LSB1XK1CA                   OBJECT IDENTIFIER ::= { hh3cevtModuleSwitchType 198 } -- 10GBase-R Ethernet XENPAK Optical Interface Line Card(CA)
hh3cevtModuleSw-LSB1XP4CA                   OBJECT IDENTIFIER ::= { hh3cevtModuleSwitchType 199 } -- 4-Port 10GBase-R/X Ethernet Optical Interface Line Card(CA)
hh3cevtModuleSw-LSB1UP1CA                   OBJECT IDENTIFIER ::= { hh3cevtModuleSwitchType 200 } -- Single Port OC-192c POS XFP Optical Interface Card(CA)
hh3cevtModuleSw-LSB1SP4CA                   OBJECT IDENTIFIER ::= { hh3cevtModuleSwitchType 201 } -- 4-Port OC-48c POS SFP Optical Interface Card(CA)
hh3cevtModuleSw-LSB1VP2CA                   OBJECT IDENTIFIER ::= { hh3cevtModuleSwitchType 202 } -- 2*10G RPR Process Unit(CA)
hh3cevtModuleSw-SR01FT48WA                  OBJECT IDENTIFIER ::= { hh3cevtModuleSwitchType 203 } -- 48 Ports 100Base-TX Ethernet Line Card (WA)
hh3cevtModuleSw-SR01FP20WA                  OBJECT IDENTIFIER ::= { hh3cevtModuleSwitchType 204 } -- 20 Ports 100Base-FX Ethernet Interface Service Card (WA)
hh3cevtModuleSw-SR01F32GWA                  OBJECT IDENTIFIER ::= { hh3cevtModuleSwitchType 205 } -- 32 Ports FE and 4 Ports GE Line Card(WA)
hh3cevtModuleSw-SR01P4G8WA                  OBJECT IDENTIFIER ::= { hh3cevtModuleSwitchType 206 } -- 4 Ports OC-3c POS and 8 Ports GE Line Card(WA)
hh3cevtModuleSw-SR01GT12WA                  OBJECT IDENTIFIER ::= { hh3cevtModuleSwitchType 207 } -- 12 Ports 1000Base-T Ethernet Interface Line Card(WA)
hh3cevtModuleSw-SR01GT24WA                  OBJECT IDENTIFIER ::= { hh3cevtModuleSwitchType 208 } -- 24 Ports 1000Base-T Ethernet Interface Line Card(WA)
hh3cevtModuleSw-SR01GP12WA                  OBJECT IDENTIFIER ::= { hh3cevtModuleSwitchType 209 } -- 12 Ports 1000Base Ethernet Optical Interface Service Card(WA)
hh3cevtModuleSw-SR01GP24WA                  OBJECT IDENTIFIER ::= { hh3cevtModuleSwitchType 210 } -- 24 Ports 1000Base-X Ethernet Interface Line Card (WA)
hh3cevtModuleSw-SR01GT8PWA                  OBJECT IDENTIFIER ::= { hh3cevtModuleSwitchType 211 } -- 8 Ports 1000Base-T Ethernet Interface & 4 Ports 1000Base-X Ethernet SFP Interface Line Card(WA)
hh3cevtModuleSw-SR01XP2WA                   OBJECT IDENTIFIER ::= { hh3cevtModuleSwitchType 212 } -- 2-Port 10GBase-R/W Ethernet XFP Optical Interface Card(WA)
hh3cevtModuleSw-SR01XK1WA                   OBJECT IDENTIFIER ::= { hh3cevtModuleSwitchType 213 } -- 10GBase-R Ethernet XENPAK Optical Interface Line Card(WA)
hh3cevtModuleSw-SR01UP1WA                   OBJECT IDENTIFIER ::= { hh3cevtModuleSwitchType 214 } -- Single Port OC-192c POS XFP Optical Interface Card(WA)
hh3cevtModuleSw-SR01SP4WA                   OBJECT IDENTIFIER ::= { hh3cevtModuleSwitchType 215 } -- 4-Port OC-48c POS SFP Optical Interface Card(WA)
hh3cevtModuleSw-GP8U                        OBJECT IDENTIFIER ::= { hh3cevtModuleSwitchType 216 } -- 8-Port 1000Base-X SFP Optical Interface Module
hh3cevtModuleSw-LSEXP1P                     OBJECT IDENTIFIER ::= { hh3cevtModuleSwitchType 217 } -- Single 10G SFP Optical Interface Module
hh3cevtModuleSw-LSEXK1P                     OBJECT IDENTIFIER ::= { hh3cevtModuleSwitchType 218 } -- Single 10G XENPAK Interface Module
hh3cevtModuleSw-LSEXS1P                     OBJECT IDENTIFIER ::= { hh3cevtModuleSwitchType 219 } -- Single 10G STACK Interface Module
hh3cevtModuleSw-LS81GP48                    OBJECT IDENTIFIER ::= { hh3cevtModuleSwitchType 220 } -- 48-Port 1000M Ethernet Optical Interface Board(SFP,LC),LC Connector
hh3cevtModuleSw-LS81GT48B                   OBJECT IDENTIFIER ::= { hh3cevtModuleSwitchType 221 } -- 48-Port 1000Base-T Gigabit Ethernet Interface Board(RJ45)
hh3cevtModuleSw-LS81T16P                    OBJECT IDENTIFIER ::= { hh3cevtModuleSwitchType 222 } -- 16-Port 1000Base-T Gigabit Ethernet Interface(RJ45) + 8-Port 1000BASE-X Gigabit Ethernet Optical Interface Board(SFP,LC)
hh3cevtModuleSw-LS81T32P                    OBJECT IDENTIFIER ::= { hh3cevtModuleSwitchType 223 } -- 32-Port 1000Base-T Gigabit Ethernet Interface(RJ45) + 16-Port 1000BASE-X Gigabit Ethernet Optical Interface Board(SFP,LC)
hh3cevtModuleSw-LS81TGX2                    OBJECT IDENTIFIER ::= { hh3cevtModuleSwitchType 224 } -- 2-Port 10GBASE Ethernet Interface Board(XFP,LC)
hh3cevtModuleSw-LS81TGX4                    OBJECT IDENTIFIER ::= { hh3cevtModuleSwitchType 225 } -- 4-Port 10GBASE Ethernet Interface Module(XFP,LC),XG
hh3cevtModuleSw-LSB1GV48DA                  OBJECT IDENTIFIER ::= { hh3cevtModuleSwitchType 226 } -- 48 Ports 1000Base-T Ethernet Interface Line Card with POE(DA)
hh3cevtModuleSw-SR01GV48VB                  OBJECT IDENTIFIER ::= { hh3cevtModuleSwitchType 227 } -- 48 Ports 1000Base-T Ethernet Interface Line Card with POE(VB)
hh3cevtModuleSw-LSB1GT24DB                  OBJECT IDENTIFIER ::= { hh3cevtModuleSwitchType 228 } -- 24 Ports 1000Base-T Ethernet Interface Line Card(DB)
hh3cevtModuleSw-LSB1GP24DB                  OBJECT IDENTIFIER ::= { hh3cevtModuleSwitchType 229 } -- 24 Ports 1000Base-X Ethernet Interface Line Card(DB)
hh3cevtModuleSw-LSB1GP24DC                  OBJECT IDENTIFIER ::= { hh3cevtModuleSwitchType 230 } -- 24 Ports 1000Base-X Ethernet Interface Line Card(DC)
hh3cevtModuleSw-LSB1FW8DB                   OBJECT IDENTIFIER ::= { hh3cevtModuleSwitchType 231 } -- 8-port 1000BASE-X (SFP) Firewall Service Card(DB)
hh3cevtModuleSw-LSB1IPSEC8DB                OBJECT IDENTIFIER ::= { hh3cevtModuleSwitchType 232 } -- 8-port 1000BASE-X (SFP) IPSEC Service Card(DB)
hh3cevtModuleSw-SR01GT24VB                  OBJECT IDENTIFIER ::= { hh3cevtModuleSwitchType 233 } -- 24 Ports 1000Base-T Ethernet Interface Line Card(VB)
hh3cevtModuleSw-SR01GP24VC                  OBJECT IDENTIFIER ::= { hh3cevtModuleSwitchType 234 } -- 24 Ports 1000Base-X Ethernet Interface Line Card(VC)
hh3cevtModuleSw-SR01VP2WA                   OBJECT IDENTIFIER ::= { hh3cevtModuleSwitchType 235 } -- 2*10G RPR Process Unit(WA)
hh3cevtModuleSw-SR01FW8VB                   OBJECT IDENTIFIER ::= { hh3cevtModuleSwitchType 236 } -- 8-port 1000BASE-X (SFP) Firewall Service Card(VB)
hh3cevtModuleSw-SR01IPSEC8VB                OBJECT IDENTIFIER ::= { hh3cevtModuleSwitchType 237 } -- 8-port 1000BASE-X (SFP) IPSEC Service Card(VB)
hh3cevtModuleSw-SR01NATL                    OBJECT IDENTIFIER ::= { hh3cevtModuleSwitchType 238 } -- NAT Service Processing Card (L)
hh3cevtModuleSw-SR01VPNL                    OBJECT IDENTIFIER ::= { hh3cevtModuleSwitchType 239 } -- VPN Service Processing Card (L)
hh3cevtModuleSw-LSB1GP24CB                  OBJECT IDENTIFIER ::= { hh3cevtModuleSwitchType 240 } -- 24 Ports 1000Base-X Ethernet Interface Line Card(CB)
hh3cevtModuleSw-LSB1GP48DB                  OBJECT IDENTIFIER ::= { hh3cevtModuleSwitchType 241 } -- 48-Port Gigabit Ethernet Optical Interface Line Card(DB)
hh3cevtModuleSw-LSB1XP2CB                   OBJECT IDENTIFIER ::= { hh3cevtModuleSwitchType 242 } -- 2-Port 10Gigabit Ethernet Optical Interface Card(CB)
hh3cevtModuleSw-XP4L                        OBJECT IDENTIFIER ::= { hh3cevtModuleSwitchType 243 } -- 4 Port 1000BASE Optic Interface Module (XFP)
hh3cevtModuleSw-LSB1XP4LDB                  OBJECT IDENTIFIER ::= { hh3cevtModuleSwitchType 244 } -- 4-Port 10GBase-R/W Ethernet XFP Optical Interface Line Speed Card(DB)
hh3cevtModuleSw-LSB1XP4LDC                  OBJECT IDENTIFIER ::= { hh3cevtModuleSwitchType 245 } -- 4-Port 10GBase-R/W Ethernet XFP Optical Interface Line Speed Card(DC)
hh3cevtModuleSw-AHP4                        OBJECT IDENTIFIER ::= { hh3cevtModuleSwitchType 246 } -- 2-Port OC-3 ATM and 2-Port OC-3/12 ATM Interface Module (SFP)
hh3cevtModuleSw-LSB1AHP4GCA                 OBJECT IDENTIFIER ::= { hh3cevtModuleSwitchType 247 } -- 2-Port OC-3 ATM and 2-Port OC-3/12 ATM and 8-Port 1000Base-X Ethernet Optical Interface Line Card(CA)
hh3cevtModuleSw-CLP4                        OBJECT IDENTIFIER ::= { hh3cevtModuleSwitchType 248 } -- 4 Ports OC-3/STM-1 CPOS Optical Interface Module (SFP)
hh3cevtModuleSw-LSB1CLP4GCA                 OBJECT IDENTIFIER ::= { hh3cevtModuleSwitchType 249 } -- 4 Ports OC-3/STM-1 CPOS Optical Interface and 4-Port 1000Base-X Ethernet Optical Interface Line Card(CA)
hh3cevtModuleSw-ET32                        OBJECT IDENTIFIER ::= { hh3cevtModuleSwitchType 250 } -- 32-Port Channelized E1/T1 Interface Module
hh3cevtModuleSw-LSB1ET32GCA                 OBJECT IDENTIFIER ::= { hh3cevtModuleSwitchType 251 } -- 32-Port Channelized E1/T1 Interface and 4-Port 1000Base-X Ethernet Optical Interface Line Card(CA)
hh3cevtModuleSw-LSB1IDSDB                   OBJECT IDENTIFIER ::= { hh3cevtModuleSwitchType 252 } -- Intrusion Detection Service Card(DB)
hh3cevtModuleSw-LSB1SRP2N1                  OBJECT IDENTIFIER ::= { hh3cevtModuleSwitchType 253 } -- Switching and Route Processing Board,8*LPU
hh3cevtModuleSw-BOARD-LS82SRPB              OBJECT IDENTIFIER ::= { hh3cevtModuleSwitchType 254 }
hh3cevtModuleSw-BORAD-LS83SRPC              OBJECT IDENTIFIER ::= { hh3cevtModuleSwitchType 255 }
hh3cevtModuleSw-Main                        OBJECT IDENTIFIER ::= { hh3cevtModuleSwitchType 256 }
hh3cevtModuleSw-LSB1SRP2N2                  OBJECT IDENTIFIER ::= { hh3cevtModuleSwitchType 257 } -- Switching and Route Processing Board,5*LPU
hh3cevtModuleSw-LSB1NAMB                    OBJECT IDENTIFIER ::= { hh3cevtModuleSwitchType 258 } -- NAM Service Processing Card (B)
hh3cevtModuleSw-RSP2                        OBJECT IDENTIFIER ::= { hh3cevtModuleSwitchType 259 } -- 2*2.5G Resilient Packet Ring Interface
hh3cevtModuleSw-LSB1RSP2CA                  OBJECT IDENTIFIER ::= { hh3cevtModuleSwitchType 260 } -- 2*2.5G Resilient Packet Ring Interface Line Card(CA)
hh3cevtModuleSw-SR01XP4LVC                  OBJECT IDENTIFIER ::= { hh3cevtModuleSwitchType 261 } -- 4-Port 10GBase-R/W Ethernet XFP Optical Interface Line Speed Card(VC)
hh3cevtModuleSw-SR01AHP4GWA                 OBJECT IDENTIFIER ::= { hh3cevtModuleSwitchType 262 } -- 2-Port OC-3 ATM and 2-Port OC-3/12 ATM and 8-Port 1000Base-X Ethernet Optical Interface Line Card(WA)
hh3cevtModuleSw-SR01CLP4GWA                 OBJECT IDENTIFIER ::= { hh3cevtModuleSwitchType 263 } -- 4 Ports OC-3/STM-1 CPOS Optical Interface and 4-Port 1000Base-X Ethernet Optical Interface Line Card(WA)
hh3cevtModuleSw-SR01ET32GWA                 OBJECT IDENTIFIER ::= { hh3cevtModuleSwitchType 264 } -- 32-Port Channelized E1/T1 Interface and 4-Port 1000Base-X Ethernet Optical Interface Line Card(WA)
hh3cevtModuleSw-SR01IDSVB                   OBJECT IDENTIFIER ::= { hh3cevtModuleSwitchType 265 } -- Intrusion Detection Service Card(VB)
hh3cevtModuleSw-SR01SRPUF                   OBJECT IDENTIFIER ::= { hh3cevtModuleSwitchType 266 } -- Switching and Route Processing Board,12*LPU
hh3cevtModuleSw-SR01NAML                    OBJECT IDENTIFIER ::= { hh3cevtModuleSwitchType 267 } -- NAM Service Processing Card (L)
hh3cevtModuleSw-SR01RSP2WA                  OBJECT IDENTIFIER ::= { hh3cevtModuleSwitchType 268 } -- 2*2.5G Resilient Packet Ring Interface Line Card(WA)
hh3cevtModuleSw-LSPM1XP1P                   OBJECT IDENTIFIER ::= { hh3cevtModuleSwitchType 269 } -- 1-Port 10G XFP Module
hh3cevtModuleSw-LSPM1XP2P                   OBJECT IDENTIFIER ::= { hh3cevtModuleSwitchType 270 } -- 2-Port 10G XFP Module
hh3cevtModuleSw-LSPM1CX2P                   OBJECT IDENTIFIER ::= { hh3cevtModuleSwitchType 271 } -- 2-Port 10G CX4 Module
hh3cevtModuleSw-STK-1000BASE-T              OBJECT IDENTIFIER ::= { hh3cevtModuleSwitchType 272 } -- Single Port 1000BASE-T Stack Ethernet Interface Card

--
-- 273 to 299 reserved for other product
--


--
-- 300 to 499 reserved for advanced switches part I
--
hh3cevtModuleSw-LSB1SRP1M0                  OBJECT IDENTIFIER ::= { hh3cevtModuleSwitchType 300 } -- Switching and Route Process Unit,2*LPU or 3*LPU
hh3cevtModuleSw-LSB1SRP1M1                  OBJECT IDENTIFIER ::= { hh3cevtModuleSwitchType 301 } -- Switching and Route Process Unit
hh3cevtModuleSw-LSB1GP12DB                  OBJECT IDENTIFIER ::= { hh3cevtModuleSwitchType 302 } -- 12 Ports 1000Base Ethernet Optical Interface Service Card(DB)
hh3cevtModuleSw-LSB1GT12DB                  OBJECT IDENTIFIER ::= { hh3cevtModuleSwitchType 303 } -- 12 Ports 1000Base-T Ethernet Interface Line Card(DB)
hh3cevtModuleSw-LSB1XK1DB                   OBJECT IDENTIFIER ::= { hh3cevtModuleSwitchType 304 } -- 10GBase-R Ethernet XENPAK Optical Interface Line Card(DB)
hh3cevtModuleSw-LSB1XP2DB                   OBJECT IDENTIFIER ::= { hh3cevtModuleSwitchType 305 } -- 2-Port 10GBase-R/W Ethernet XFP Optical Interface Card(DB)
hh3cevtModuleSw-LSB1XP2DC                   OBJECT IDENTIFIER ::= { hh3cevtModuleSwitchType 306 } -- 2-Port 10GBase-R/W Ethernet XFP Optical Interface Card(DC)
hh3cevtModuleSw-LSB1GT48LDB                 OBJECT IDENTIFIER ::= { hh3cevtModuleSwitchType 307 } -- 48-Port Gigabit Ethernet RJ45 Electrical Interface Card (DB)
hh3cevtModuleSw-LSB1XP4TDB                  OBJECT IDENTIFIER ::= { hh3cevtModuleSwitchType 308 } -- 4-Port 10GBase-R/W Ethernet XFP Optical Interface Line Speed Test Card(DB)
hh3cevtModuleSw-LSB1XP4TDC                  OBJECT IDENTIFIER ::= { hh3cevtModuleSwitchType 309 } -- 4-Port 10GBase-R/W Ethernet XFP Optical Interface Line Speed Test Card(DC)
hh3cevtModuleSw-LSB1RSP2DC                  OBJECT IDENTIFIER ::= { hh3cevtModuleSwitchType 310 } -- 2*2.5G Resilient Packet Ring Interface Line Card(DC)
hh3cevtModuleSw-LSB1VP2DC                   OBJECT IDENTIFIER ::= { hh3cevtModuleSwitchType 311 } -- 2*10G Resilient Packet Ring Process Unit(DC)
hh3cevtModuleSw-LSB1XP4DB                   OBJECT IDENTIFIER ::= { hh3cevtModuleSwitchType 312 } -- 4-Port 10GBase-R/X Ethernet Optical Interface Line Card(DB)
hh3cevtModuleSw-LSB1SRP2E0                  OBJECT IDENTIFIER ::= { hh3cevtModuleSwitchType 313 } -- Switching and Route Process Unit,12*LPU
hh3cevtModuleSw-LSB1SRP2E1                  OBJECT IDENTIFIER ::= { hh3cevtModuleSwitchType 314 } -- Switching and Route Process Unit,8*LPU
hh3cevtModuleSw-LSB1SRP2E2                  OBJECT IDENTIFIER ::= { hh3cevtModuleSwitchType 315 } -- Switching and Route Process Unit,5*LPU
hh3cevtModuleSw-LSB1SRP2E3                  OBJECT IDENTIFIER ::= { hh3cevtModuleSwitchType 316 } -- Switching and Route Process Unit, Clock module
hh3cevtModuleSw-SR01SRPUQ                   OBJECT IDENTIFIER ::= { hh3cevtModuleSwitchType 317 } -- Switching and Route Processing Unit Q
hh3cevtModuleSw-AHP1                        OBJECT IDENTIFIER ::= { hh3cevtModuleSwitchType 318 } -- 1-Port OC-12c(3c)/STM-4(1) ATM Optical Interface Module(SFP)
hh3cevtModuleSw-AHP2                        OBJECT IDENTIFIER ::= { hh3cevtModuleSwitchType 319 } -- 2-Port OC-12c(3c)/STM-4(1) ATM Optical Interface Module(SFP)
hh3cevtModuleSw-CLP1                        OBJECT IDENTIFIER ::= { hh3cevtModuleSwitchType 320 } -- 1-Port OC-3/STM-1 CPOS Optical Interface Module(SFP)
hh3cevtModuleSw-CLP2                        OBJECT IDENTIFIER ::= { hh3cevtModuleSwitchType 321 } -- 2-Port OC-3/STM-1 CPOS Optical Interface Module(SFP)
hh3cevtModuleSw-ET16                        OBJECT IDENTIFIER ::= { hh3cevtModuleSwitchType 322 } -- 16-Port Channelized E1/T1 Interface Module
hh3cevtModuleSw-LSB1SRP1NA0                 OBJECT IDENTIFIER ::= { hh3cevtModuleSwitchType 323 } -- Switching and Route Process Unit,12*LPU
hh3cevtModuleSw-LSB1SRP1NA1                 OBJECT IDENTIFIER ::= { hh3cevtModuleSwitchType 324 } -- Switching and Route Process Unit,8*LPU
hh3cevtModuleSw-LSB1SRP1NA2                 OBJECT IDENTIFIER ::= { hh3cevtModuleSwitchType 325 } -- Switching and Route Process Unit,5*LPU
hh3cevtModuleSw-LSB1SRP1NA3                 OBJECT IDENTIFIER ::= { hh3cevtModuleSwitchType 326 } -- Switching and Route Process Unit, Clock module
hh3cevtModuleSw-SR01AHP1GWA                 OBJECT IDENTIFIER ::= { hh3cevtModuleSwitchType 327 } -- 1-Port OC-12c(3c)/STM-4(1) ATM Optical Interface and 4-Port 1000Base-X Ethernet Optical Interface Line Card(WA)
hh3cevtModuleSw-SR01AHP2GWA                 OBJECT IDENTIFIER ::= { hh3cevtModuleSwitchType 328 } -- 2-Port OC-12c(3c)/STM-4(1) ATM Optical Interface and 4-Port 1000Base-X Ethernet Optical Interface Line Card(WA)
hh3cevtModuleSw-SR01CLP1GWA                 OBJECT IDENTIFIER ::= { hh3cevtModuleSwitchType 329 } -- 1-Port OC-3/STM-1 CPOS Optical Interface and 4-Port 1000Base-X Ethernet Optical Interface Line Card(WA)
hh3cevtModuleSw-SR01CLP2GWA                 OBJECT IDENTIFIER ::= { hh3cevtModuleSwitchType 330 } -- 2-Port OC-3/STM-1 CPOS Optical Interface and 4-Port 1000Base-X Ethernet Optical Interface Line Card(WA)
hh3cevtModuleSw-SR01ET16GWA                 OBJECT IDENTIFIER ::= { hh3cevtModuleSwitchType 331 } -- 16-Port Channelized E1/T1 Interface and  4-Port 1000Base-X Ethernet Optical Interface Line Card(WA)
hh3cevtModuleSw-SR01GP12VB                  OBJECT IDENTIFIER ::= { hh3cevtModuleSwitchType 332 } -- 12-Port Gigabit Ethernet Optical Interface Card(VB)
hh3cevtModuleSw-SR01XK1VB                   OBJECT IDENTIFIER ::= { hh3cevtModuleSwitchType 333 } -- 1-Port 10Gigabit Ethernet Optical Interface Card(VB)
hh3cevtModuleSw-SR01XP2VC                   OBJECT IDENTIFIER ::= { hh3cevtModuleSwitchType 334 } -- 2-Port 10GBase-RW Ethernet XFP Optical Interface Line Card(VC)
hh3cevtModuleSw-SR01XP4LVB                  OBJECT IDENTIFIER ::= { hh3cevtModuleSwitchType 335 } -- 4-Port 10GBase-R/W Ethernet XFP Optical Interface Line Speed Card(VB)
hh3cevtModuleSw-SR01SRPUEA                  OBJECT IDENTIFIER ::= { hh3cevtModuleSwitchType 336 } -- Switching and Route Process Unit, Clock Module
hh3cevtModuleSw-LSB1SRP1N4                  OBJECT IDENTIFIER ::= { hh3cevtModuleSwitchType 337 } -- Switching and Route Process Unit, 12*LPU
hh3cevtModuleSw-LSB1SRP1N5                  OBJECT IDENTIFIER ::= { hh3cevtModuleSwitchType 338 } -- Switching and Route Process Unit, 8*LPU
hh3cevtModuleSw-LSB1SRP1N6                  OBJECT IDENTIFIER ::= { hh3cevtModuleSwitchType 339 } -- Switching and Route Process Unit, 5*LPU
hh3cevtModuleSw-LSB1SRP1N7                  OBJECT IDENTIFIER ::= { hh3cevtModuleSwitchType 340 } -- Switching and Route Process Unit, Clock Module
hh3cevtModuleSw-LSB1SRP2N4                  OBJECT IDENTIFIER ::= { hh3cevtModuleSwitchType 341 } -- Switching and Route Process Unit, 12*LPU
hh3cevtModuleSw-LSB1SRP2N5                  OBJECT IDENTIFIER ::= { hh3cevtModuleSwitchType 342 } -- Switching and Route Process Unit, 8*LPU
hh3cevtModuleSw-LSB1SRP2N6                  OBJECT IDENTIFIER ::= { hh3cevtModuleSwitchType 343 } -- Switching and Route Process Unit, 5*LPU
hh3cevtModuleSw-LSB1SRP2N7                  OBJECT IDENTIFIER ::= { hh3cevtModuleSwitchType 344 } -- Switching and Route Process Unit, Clock Module
hh3cevtModuleSw-LSB1SRP1NA4                 OBJECT IDENTIFIER ::= { hh3cevtModuleSwitchType 345 } -- Switching and Route Process Unit, 12*LPU
hh3cevtModuleSw-LSB1SRP1NA5                 OBJECT IDENTIFIER ::= { hh3cevtModuleSwitchType 346 } -- Switching and Route Process Unit, 8*LPU
hh3cevtModuleSw-LSB1SRP1NA6                 OBJECT IDENTIFIER ::= { hh3cevtModuleSwitchType 347 } -- Switching and Route Process Unit, 5*LPU
hh3cevtModuleSw-LSB1SRP1NA7                 OBJECT IDENTIFIER ::= { hh3cevtModuleSwitchType 348 } -- Switching and Route Process Unit, Clock Module
hh3cevtModuleSw-LSB2GV48DA                  OBJECT IDENTIFIER ::= { hh3cevtModuleSwitchType 349 } -- 48-Ports 1000Base-T Ethernet Interface Line Card with POE(DA)
hh3cevtModuleSw-LSB1RGP2GDB                 OBJECT IDENTIFIER ::= { hh3cevtModuleSwitchType 350 } -- 2-Port GE RPR and 8-Port GE Optical Interface Service Card(DB)
hh3cevtModuleSw-LSB1RGP4GDB                 OBJECT IDENTIFIER ::= { hh3cevtModuleSwitchType 351 } -- 4-Port GE RPR and 8-Port GE Optical Interface Service Card(DB)
hh3cevtModuleSw-LSB2GP24DB                  OBJECT IDENTIFIER ::= { hh3cevtModuleSwitchType 352 } -- 24-Port 1000BASE-X  Interface Module(DB),(SFP,LC)
hh3cevtModuleSw-LSB2GP24DC                  OBJECT IDENTIFIER ::= { hh3cevtModuleSwitchType 353 } -- 24-Port 1000BASE-X  Interface Module(DC),(SFP,LC)
hh3cevtModuleSw-LSB2GT24DB                  OBJECT IDENTIFIER ::= { hh3cevtModuleSwitchType 354 } -- 24-Port 10/100/1000BASE-T Interface Module(DB),(RJ45)
hh3cevtModuleSw-LSB2FW8DB                   OBJECT IDENTIFIER ::= { hh3cevtModuleSwitchType 355 } -- 8-Port 1000BASE-X Interface Firewall Service Module(DB),(SFP,LC)
hh3cevtModuleSw-LSB2IPSEC8DB                OBJECT IDENTIFIER ::= { hh3cevtModuleSwitchType 356 } -- 8-Port 1000BASE-X Interface IPSEC Service Module(DB),(SFP,LC)
hh3cevtModuleSw-LSB2GV48DB                  OBJECT IDENTIFIER ::= { hh3cevtModuleSwitchType 357 } -- 48-Port 10/100/1000BASE-T Interface Module(DB),(PoE,RJ45)
hh3cevtModuleSw-RGP2                        OBJECT IDENTIFIER ::= { hh3cevtModuleSwitchType 358 } -- 2-Port GE Resilient Packet Ring Interface Module
hh3cevtModuleSw-RGP4                        OBJECT IDENTIFIER ::= { hh3cevtModuleSwitchType 359 } -- 4-Port GE Resilient Packet Ring Interface Module
hh3cevtModuleSw-SR02FW8VB                   OBJECT IDENTIFIER ::= { hh3cevtModuleSwitchType 360 } -- 8-Port 1000BASE-X Interface Firewall Service Module(VB),(SFP,LC)
hh3cevtModuleSw-SR02IPSEC8VB                OBJECT IDENTIFIER ::= { hh3cevtModuleSwitchType 361 } -- 8-Port 1000BASE-X Interface IPSEC Service Module(VB),(SFP,LC)
hh3cevtModuleSw-LSB2SRP1N0                  OBJECT IDENTIFIER ::= { hh3cevtModuleSwitchType 362 } -- Switching and Route Process Unit, 12*LPU
hh3cevtModuleSw-LSB2SRP1N1                  OBJECT IDENTIFIER ::= { hh3cevtModuleSwitchType 363 } -- Switching and Route Process Unit, 8*LPU
hh3cevtModuleSw-LSB2SRP1N2                  OBJECT IDENTIFIER ::= { hh3cevtModuleSwitchType 364 } -- Switching and Route Process Unit, 5*LPU
hh3cevtModuleSw-LSB2SRP1N3                  OBJECT IDENTIFIER ::= { hh3cevtModuleSwitchType 365 } -- Switching and Route Process Unit, Clock module
hh3cevtModuleSw-LSB2SRP1N4                  OBJECT IDENTIFIER ::= { hh3cevtModuleSwitchType 366 } -- Switching and Route Process Unit, 12*LPU
hh3cevtModuleSw-LSB2SRP1N5                  OBJECT IDENTIFIER ::= { hh3cevtModuleSwitchType 367 } -- Switching and Route Process Unit, 8*LPU
hh3cevtModuleSw-LSB2SRP1N6                  OBJECT IDENTIFIER ::= { hh3cevtModuleSwitchType 368 } -- Switching and Route Process Unit, 5*LPU
hh3cevtModuleSw-LSB2SRP1N7                  OBJECT IDENTIFIER ::= { hh3cevtModuleSwitchType 369 } -- Switching and Route Process Unit, Clock module
hh3cevtModuleSw-SR02SRPUE                   OBJECT IDENTIFIER ::= { hh3cevtModuleSwitchType 370 } -- Switching and Route Process Unit, Clock module
hh3cevtModuleSw-SR01LN1BQH0                 OBJECT IDENTIFIER ::= { hh3cevtModuleSwitchType 371 } -- Single XG Service Board(BQH)
hh3cevtModuleSw-SR01DXP1L                   OBJECT IDENTIFIER ::= { hh3cevtModuleSwitchType 372 } -- 1-Port 10GBASE-R/W Ethernet Optical Interface Card,(XFP,LC)
hh3cevtModuleSw-SR01DGP10L                  OBJECT IDENTIFIER ::= { hh3cevtModuleSwitchType 373 } -- 10-Port 1000BASE-X Optical Interface Card,(SFP,LC)
hh3cevtModuleSw-SR01DRSP2L                  OBJECT IDENTIFIER ::= { hh3cevtModuleSwitchType 374 } -- 2-Port 2.5G RPR Optical Interface Card,(SFP,LC)
hh3cevtModuleSw-SR01DRUP1L                  OBJECT IDENTIFIER ::= { hh3cevtModuleSwitchType 375 } -- 1-Port 10G RPR Optical Interface Card,(XFP,LC)
hh3cevtModuleSw-SR01DGP20R                  OBJECT IDENTIFIER ::= { hh3cevtModuleSwitchType 376 } -- 20-Port 1000BASE-X Optical Interface Card,(SFP,LC)
hh3cevtModuleSw-SR01DPLP8L                  OBJECT IDENTIFIER ::= { hh3cevtModuleSwitchType 377 } -- 8-Port 155M POS Optical Interface Card,(SFP,LC)
hh3cevtModuleSw-SR01DXP2R                   OBJECT IDENTIFIER ::= { hh3cevtModuleSwitchType 378 } -- 2-Port 10GBASE-R/W Ethernet Optical Interface Card,(XFP,LC)
hh3cevtModuleSw-LSB1FW2A0                   OBJECT IDENTIFIER ::= { hh3cevtModuleSwitchType 379 } -- Gigabit Firewall Card, 4 Gigabit Port for Management
hh3cevtModuleSw-LSB1GP48LDB                 OBJECT IDENTIFIER ::= { hh3cevtModuleSwitchType 380 } -- 48-Port Line Rate Gigabit Ethernet Optical Interface Card(DB)
hh3cevtModuleSw-SR01LN1BNA0                 OBJECT IDENTIFIER ::= { hh3cevtModuleSwitchType 381 } -- Single XG Service Board(BNA)
hh3cevtModuleSw-SR01LN2BQH0                 OBJECT IDENTIFIER ::= { hh3cevtModuleSwitchType 382 } -- Dual XG Service Board(BQH)
hh3cevtModuleSw-SR01LN2BNA0                 OBJECT IDENTIFIER ::= { hh3cevtModuleSwitchType 383 } -- Dual XG Service Board(BNA)
hh3cevtModuleSw-SR01DGT20R                  OBJECT IDENTIFIER ::= { hh3cevtModuleSwitchType 384 } -- 20-Port 10/100/1000BASE-T Electrical Interface Card,(RJ45)
hh3cevtModuleSw-SR01DPSP4L                  OBJECT IDENTIFIER ::= { hh3cevtModuleSwitchType 385 } -- 4-Port 2.5G POS Optical Interface Card(SFP,LC)
hh3cevtModuleSw-SR01DPUP1L                  OBJECT IDENTIFIER ::= { hh3cevtModuleSwitchType 386 } -- 1-Port 10G POS Optical Interface Card,(XFP,LC)
hh3cevtModuleSw-SR01DPL2G6L                 OBJECT IDENTIFIER ::= { hh3cevtModuleSwitchType 387 } -- 2-Port 155M POS Optical Interface(SFP,LC)+6-Port 1000BASE-X Optical Interface Card(SFP,LC)
hh3cevtModuleSw-SR01DPH2G6L                 OBJECT IDENTIFIER ::= { hh3cevtModuleSwitchType 388 } -- 2-Port 622M POS Optical Interface(SFP,LC)+6-Port 1000BASE-X Optical Interface Card(SFP,LC)
hh3cevtModuleSw-SR01DPS2G4L                 OBJECT IDENTIFIER ::= { hh3cevtModuleSwitchType 389 } -- 2-Port 2.5G POS Optical Interface(SFP,LC)+4-Port 1000BASE-X Optical Interface Card(SFP,LC)
hh3cevtModuleSw-SR01DCL1G8L                 OBJECT IDENTIFIER ::= { hh3cevtModuleSwitchType 390 } -- 1-Port 155M CPOS Optical Interface(SFP,LC)+8-Port 1000BASE-X Optical Interface Card(SFP,LC)
hh3cevtModuleSw-SR01DCL2G8L                 OBJECT IDENTIFIER ::= { hh3cevtModuleSwitchType 391 } -- 2-Port 155M CPOS Optical Interface(SFP,LC)+8-Port 1000BASE-X Optical Interface Card(SFP,LC)
hh3cevtModuleSw-SR01DET8G8L                 OBJECT IDENTIFIER ::= { hh3cevtModuleSwitchType 392 } -- 8-Port E1/T1 Electrical Interface(RJ45)+8-Port 1000BASE-X Optical Interface Card(SFP,LC)
hh3cevtModuleSw-SR02SRP2E3                  OBJECT IDENTIFIER ::= { hh3cevtModuleSwitchType 393 } -- Switching and Route Process Unit, Clock module
hh3cevtModuleSw-SR02SRP1E3                  OBJECT IDENTIFIER ::= { hh3cevtModuleSwitchType 394 } -- Switching and Route Process Unit, Clock module
hh3cevtModuleSw-SR02SRP1M3                  OBJECT IDENTIFIER ::= { hh3cevtModuleSwitchType 395 } -- Switching and Route Process Unit, Clock module
hh3cevtModuleSw-SR01DQCP4L                  OBJECT IDENTIFIER ::= { hh3cevtModuleSwitchType 396 } -- 4-Port OC-3c/OC-12c/OC-48c POS/GE Optical Interface Card,(SFP,LC)
hh3cevtModuleSw-SR01DTCP8L                  OBJECT IDENTIFIER ::= { hh3cevtModuleSwitchType 397 } -- 8-Port OC-3c/OC-12c POS/GE Optical Interface Card,(SFP,LC)
hh3cevtModuleSw-LSB1AFC1A0                  OBJECT IDENTIFIER ::= { hh3cevtModuleSwitchType 398 } -- Anomaly Flow Cleaner Board
hh3cevtModuleSw-LSB1SSL1A0                  OBJECT IDENTIFIER ::= { hh3cevtModuleSwitchType 399 } -- SSL VPN High-end Board
hh3cevtModuleSw-IMNAM                       OBJECT IDENTIFIER ::= { hh3cevtModuleSwitchType 400 } -- Net Analysis Service Processing Board
hh3cevtModuleSw-IMNAT                       OBJECT IDENTIFIER ::= { hh3cevtModuleSwitchType 401 } -- Network Address Translation Service Processing Board
hh3cevtModuleSw-PICAHP1L                    OBJECT IDENTIFIER ::= { hh3cevtModuleSwitchType 402 } -- 1-Port OC-12c/STM-4c ATM Optical Interface Card,(SFP,LC)
hh3cevtModuleSw-PICALP4L                    OBJECT IDENTIFIER ::= { hh3cevtModuleSwitchType 403 } -- 4-Port OC-3c/STM-1c ATM Optical Interface Card,(SFP,LC)
hh3cevtModuleSw-PICCHP4L                    OBJECT IDENTIFIER ::= { hh3cevtModuleSwitchType 404 } -- 4-Port 622M CPOS Optical Interface Card(SFP,LC)
hh3cevtModuleSw-PICCHS1G4L                  OBJECT IDENTIFIER ::= { hh3cevtModuleSwitchType 405 } -- 1-Port 622M CPOS Optical Interface(Channelized to E3/T3)+4-Port 1000BASE-X Optical Interface Card(SFP,LC)
hh3cevtModuleSw-PICCLS4G4L                  OBJECT IDENTIFIER ::= { hh3cevtModuleSwitchType 406 } -- 4-Port 155M CPOS Optical Interface(Channelized to E3/T3)+4-Port 1000BASE-X Optical Interface Card(SFP,LC)
hh3cevtModuleSw-PICCSP1L                    OBJECT IDENTIFIER ::= { hh3cevtModuleSwitchType 407 } -- 1-Port 2.5G CPOS Optical Interface Card(SFP,LC)
hh3cevtModuleSw-LSB1ACG1A0                  OBJECT IDENTIFIER ::= { hh3cevtModuleSwitchType 408 } -- Application Control Gateway Board
hh3cevtModuleSw-LST1MRPNC1                  OBJECT IDENTIFIER ::= { hh3cevtModuleSwitchType 409 } -- Management and Route Process Unit
hh3cevtModuleSw-LST1SF18B1                  OBJECT IDENTIFIER ::= { hh3cevtModuleSwitchType 410 } -- S12518 Switch Fabric Card
hh3cevtModuleSw-LST1SF08B1                  OBJECT IDENTIFIER ::= { hh3cevtModuleSwitchType 411 } -- S12508 Switch Fabric Card
hh3cevtModuleSw-LST1GT48LEC1                OBJECT IDENTIFIER ::= { hh3cevtModuleSwitchType 412 } -- 48-Port 10/100/1000BASE-T Interface Module(LEC),(RJ45)
hh3cevtModuleSw-LST1GP48LEC1                OBJECT IDENTIFIER ::= { hh3cevtModuleSwitchType 413 } -- 48-Port 1000BASE-X Interface Module (LEC),(SFP,LC)
hh3cevtModuleSw-LST1XP4LEC1                 OBJECT IDENTIFIER ::= { hh3cevtModuleSwitchType 414 } -- 4-Port 10GBASE-R/W Interface Module (LEC),(XFP,LC)
hh3cevtModuleSw-LST1XP8LEC1                 OBJECT IDENTIFIER ::= { hh3cevtModuleSwitchType 415 } -- 8-Port 10GBASE-R/W Interface Module (LEC),(XFP,LC)
hh3cevtModuleSw-LSR1SRP2B1                  OBJECT IDENTIFIER ::= { hh3cevtModuleSwitchType 416 } -- Switching and Route Process Unit
hh3cevtModuleSw-LSR1SRP2C1                  OBJECT IDENTIFIER ::= { hh3cevtModuleSwitchType 417 } -- Switching and Route Process Unit
hh3cevtModuleSw-LSR1SRP2B2                  OBJECT IDENTIFIER ::= { hh3cevtModuleSwitchType 418 } -- Switching and Route Process Unit
hh3cevtModuleSw-LSR1SRP2C2                  OBJECT IDENTIFIER ::= { hh3cevtModuleSwitchType 419 } -- Switching and Route Process Unit
hh3cevtModuleSw-LSR1GT24LEC1                OBJECT IDENTIFIER ::= { hh3cevtModuleSwitchType 420 } -- 16-Port 10/100/1000BASE-T Interface and 8-port 1000BASE-T/1000BASE-X Combo Interface Service Card(LEC)
hh3cevtModuleSw-LSR1GP24LEB1                OBJECT IDENTIFIER ::= { hh3cevtModuleSwitchType 421 } -- 16-Port 1000BASE-X Interface and 8-port 1000BASE-T/1000BASE-X Combo Interface Service Card(LEB)
hh3cevtModuleSw-LSR1GP24LEC1                OBJECT IDENTIFIER ::= { hh3cevtModuleSwitchType 422 } -- 16-Port 1000BASE-X Interface and 8-port 1000BASE-T/1000BASE-X Combo Interface Service Card(LEC)
hh3cevtModuleSw-LSR1GT48LEB1                OBJECT IDENTIFIER ::= { hh3cevtModuleSwitchType 423 } -- 48-Port 10/100/1000BASE-T Interface Module(LEB),(RJ45)
hh3cevtModuleSw-LSR1GT48LEC1                OBJECT IDENTIFIER ::= { hh3cevtModuleSwitchType 424 } -- 48-Port 10/100/1000BASE-T Interface Module(LEC),(RJ45)
hh3cevtModuleSw-LSR1GP48LEB1                OBJECT IDENTIFIER ::= { hh3cevtModuleSwitchType 425 } -- 48-Port 1000BASE-X Interface Module(LEB),(SFP,LC)
hh3cevtModuleSw-LSR1GP48LEC1                OBJECT IDENTIFIER ::= { hh3cevtModuleSwitchType 426 } -- 48-Port 1000BASE-X Interface Module(LEC),(SFP,LC)
hh3cevtModuleSw-LSR2GV48REB1                OBJECT IDENTIFIER ::= { hh3cevtModuleSwitchType 427 } -- 48-Port 10/100/1000BASE-T Interface Module(REB),(PoE,RJ45)
hh3cevtModuleSw-LSR1XP2LEB1                 OBJECT IDENTIFIER ::= { hh3cevtModuleSwitchType 428 } -- 2-Port 10GBase-R/W Interface Module (LEB),(XFP,LC)
hh3cevtModuleSw-LSR1XP2LEC1                 OBJECT IDENTIFIER ::= { hh3cevtModuleSwitchType 429 } -- 2-Port 10GBase-R/W Interface Module (LEC),(XFP,LC)
hh3cevtModuleSw-LSR1XP4LEB1                 OBJECT IDENTIFIER ::= { hh3cevtModuleSwitchType 430 } -- 4-Port 10GBase-R/W Interface Module (LEB),(XFP,LC)
hh3cevtModuleSw-LSR1XP4LEC1                 OBJECT IDENTIFIER ::= { hh3cevtModuleSwitchType 431 } -- 4-Port 10GBase-R/W Interface Module (LEC),(XFP,LC)
hh3cevtModuleSw-IMFW                        OBJECT IDENTIFIER ::= { hh3cevtModuleSwitchType 432 } -- Firewall Service Processing Board
hh3cevtModuleSw-LSB1LB1A0                   OBJECT IDENTIFIER ::= { hh3cevtModuleSwitchType 433 } -- Load Balance Board
hh3cevtModuleSw-LSB1IPS1A0                  OBJECT IDENTIFIER ::= { hh3cevtModuleSwitchType 434 } -- Gigabit IPS Card
hh3cevtModuleSw-LST1GT48LEB1                OBJECT IDENTIFIER ::= { hh3cevtModuleSwitchType 435 } -- 48-Port 10/100/1000BASE-T Interface Module(LEB),(RJ45)
hh3cevtModuleSw-LST1GP48LEB1                OBJECT IDENTIFIER ::= { hh3cevtModuleSwitchType 436 } -- 48-Port 1000BASE-X Interface Module (LEB),(SFP,LC)
hh3cevtModuleSw-LST1XP4LEB1                 OBJECT IDENTIFIER ::= { hh3cevtModuleSwitchType 437 } -- 4-Port 10GBASE-R/W Interface Module (LEB),(XFP,LC)
hh3cevtModuleSw-LST1XP8LEB1                 OBJECT IDENTIFIER ::= { hh3cevtModuleSwitchType 438 } -- 8-Port 10GBASE-R/W Interface Module (LEB),(XFP,LC)
hh3cevtModuleSw-LST1XP32REB1                OBJECT IDENTIFIER ::= { hh3cevtModuleSwitchType 439 } -- 32-Port 10GBASE-R Interface Module (REB),(SFP+,LC)
hh3cevtModuleSw-LST1XP32REC1                OBJECT IDENTIFIER ::= { hh3cevtModuleSwitchType 440 } -- 32-Port 10GBASE-R Interface Module (REC),(SFP+,LC)
hh3cevtModuleSw-LSR1FW2A1                   OBJECT IDENTIFIER ::= { hh3cevtModuleSwitchType 441 } -- Firewall Service Module
hh3cevtModuleSw-LSR1SSL1A1                  OBJECT IDENTIFIER ::= { hh3cevtModuleSwitchType 442 } -- SSL VPN Service Module
hh3cevtModuleSw-SR01DET32G2L                OBJECT IDENTIFIER ::= { hh3cevtModuleSwitchType 443 } -- 32-Port E1/T1 75ohm Electrical Interface(DB56 Female Socket)+2-Port 1000BASE-X Optical Interface Card(SFP,LC)
hh3cevtModuleSw-LSR1GP24LEF1                OBJECT IDENTIFIER ::= { hh3cevtModuleSwitchType 444 } -- 16-Port 1000BASE-X Interface and 8-port 1000BASE-T/1000BASE-X Combo Interface Service Card(LEF)
hh3cevtModuleSw-LSR1XP4LEF1                 OBJECT IDENTIFIER ::= { hh3cevtModuleSwitchType 445 } -- 4-Port 10GBASE-R/W Interface Module (LEF),(XFP,LC)
hh3cevtModuleSw-LSR1LB1A1                   OBJECT IDENTIFIER ::= { hh3cevtModuleSwitchType 446 } -- Load Balance Module
hh3cevtModuleSw-LSR1NSM1A1                  OBJECT IDENTIFIER ::= { hh3cevtModuleSwitchType 447 } -- NetStream Module
hh3cevtModuleSw-LSR1ACG1A1                  OBJECT IDENTIFIER ::= { hh3cevtModuleSwitchType 448 } -- Application Control Gateway Service Module
hh3cevtModuleSw-LSR1IPS1A1                  OBJECT IDENTIFIER ::= { hh3cevtModuleSwitchType 449 } -- Intrusion Protection System Service Module
hh3cevtModuleSw-LSR2GP24LEB1                OBJECT IDENTIFIER ::= { hh3cevtModuleSwitchType 450 } -- 16-Port 1000BASE-X Interface and 8-port 1000BASE-T/1000BASE-X Combo Interface Service Card(LEB)
hh3cevtModuleSw-LSR2GT24LEB1                OBJECT IDENTIFIER ::= { hh3cevtModuleSwitchType 451 } -- 16-Port 10/100/1000BASE-T Interface and 8-port 1000BASE-T/1000BASE-X Combo Interface Service Card(LEB)
hh3cevtModuleSw-LSR2GT48LEB1                OBJECT IDENTIFIER ::= { hh3cevtModuleSwitchType 452 } -- 48-Port 10/100/1000BASE-T Interface Module(LEB),(RJ45)
hh3cevtModuleSw-SPC-GP24L                   OBJECT IDENTIFIER ::= { hh3cevtModuleSwitchType 453 } -- 24-Port 1000BASE-X Interface Service Card,(SFP,LC)
hh3cevtModuleSw-SPC-GT48L                   OBJECT IDENTIFIER ::= { hh3cevtModuleSwitchType 454 } -- 48-Port 10/100/1000BASE-T Interface Module,(RJ45)
hh3cevtModuleSw-SPC-GP48L                   OBJECT IDENTIFIER ::= { hh3cevtModuleSwitchType 455 } -- 48-Port 1000BASE-X Interface Module,(SFP,LC)
hh3cevtModuleSw-SPC-XP2L                    OBJECT IDENTIFIER ::= { hh3cevtModuleSwitchType 456 } -- 2-Port 10GBASE-R/W Interface Service Card,(XFP,LC)
hh3cevtModuleSw-SPC-XP4L                    OBJECT IDENTIFIER ::= { hh3cevtModuleSwitchType 457 } -- 4-Port 10GBase-R/W Interface Module,(XFP,LC)
hh3cevtModuleSw-SR06SRP2E3                  OBJECT IDENTIFIER ::= { hh3cevtModuleSwitchType 458 } -- SDI,Routing Switch Processing Board
hh3cevtModuleSw-SPE-2010-E                  OBJECT IDENTIFIER ::= { hh3cevtModuleSwitchType 459 } -- SDI,Single XG Service Board
hh3cevtModuleSw-SPE-2020-E                  OBJECT IDENTIFIER ::= { hh3cevtModuleSwitchType 460 } -- SDI,Dual XG Service Board
hh3cevtModuleSw-SPC-XP4L-S-SDI              OBJECT IDENTIFIER ::= { hh3cevtModuleSwitchType 461 } -- SDI 4-Port 10GBase-R/W Interface Module,(XFP,LC)
hh3cevtModuleSw-SPC-GT48L-SDI               OBJECT IDENTIFIER ::= { hh3cevtModuleSwitchType 462 } -- SDI 48-Port 10/100/1000BASE-T Interface Module,(RJ45)
hh3cevtModuleSw-SPC-GP48L-S-SDI             OBJECT IDENTIFIER ::= { hh3cevtModuleSwitchType 463 } -- SDI 48-Port 1000BASE-X Interface Module,(SFP,LC)
hh3cevtModuleSw-SPC-SR02OPMA0               OBJECT IDENTIFIER ::= { hh3cevtModuleSwitchType 464 } -- Single Mode 1310&1550nm Optical Protect Board(LC)
hh3cevtModuleSw-LSR1XP16REB1                OBJECT IDENTIFIER ::= { hh3cevtModuleSwitchType 465 } -- 16-Port 10GBASE-R Interface Module (REB),(SFP+,LC)
hh3cevtModuleSw-LSR1GP48LEF1                OBJECT IDENTIFIER ::= { hh3cevtModuleSwitchType 466 } -- 48-Port 1000BASE-X Interface Module (LEF),(SFP,LC)
hh3cevtModuleSw-LST1GP48LEF1                OBJECT IDENTIFIER ::= { hh3cevtModuleSwitchType 467 } -- 48-Port 1000BASE-X Interface Module (LEF),(SFP,LC)
hh3cevtModuleSw-LST1XP8LEF1                 OBJECT IDENTIFIER ::= { hh3cevtModuleSwitchType 468 } -- 8-Port 10GBASE-R/W Interface Module (LEF),(XFP,LC)
hh3cevtModuleSw-SPE-1010-II                 OBJECT IDENTIFIER ::= { hh3cevtModuleSwitchType 469 } -- Single XG Service Board-II
hh3cevtModuleSw-SPE-1010-E-II               OBJECT IDENTIFIER ::= { hh3cevtModuleSwitchType 470 } -- Enhanced Single XG Service Board-II
hh3cevtModuleSw-SPE-1020-II                 OBJECT IDENTIFIER ::= { hh3cevtModuleSwitchType 471 } -- Double XG Service Board-II
hh3cevtModuleSw-SPE-1020-E-II               OBJECT IDENTIFIER ::= { hh3cevtModuleSwitchType 472 } -- Enhanced Double XG Service Board-II
hh3cevtModuleSw-LST1FW2A1                   OBJECT IDENTIFIER ::= { hh3cevtModuleSwitchType 473 } -- Firewall Board (LEC)
hh3cevtModuleSw-LST1NSM1A1                  OBJECT IDENTIFIER ::= { hh3cevtModuleSwitchType 474 } -- NetStream Service Board (LEC)
hh3cevtModuleSw-LST1LB1A1                   OBJECT IDENTIFIER ::= { hh3cevtModuleSwitchType 475 } -- Load Balancing Board (LEC)
hh3cevtModuleSw-LST1ACG1A1                  OBJECT IDENTIFIER ::= { hh3cevtModuleSwitchType 476 } -- Application Control Gateway Board Module (LEC)
hh3cevtModuleSw-LST1IPS1A1                  OBJECT IDENTIFIER ::= { hh3cevtModuleSwitchType 477 } -- Gigabit Intrusion Prevention System Module (LEC)
hh3cevtModuleSw-LSR1DRUP1L1                 OBJECT IDENTIFIER ::= { hh3cevtModuleSwitchType 478 } -- 1-Port OC-192c/STM-64c RPR Optical Interface Card,(XFP,LC)
hh3cevtModuleSw-LSR1DPUP1L1                 OBJECT IDENTIFIER ::= { hh3cevtModuleSwitchType 479 } -- 1-Port OC-192c/STM-64c POS Optical Interface Card,(XFP,LC)
hh3cevtModuleSw-LSR1DPSP4L1                 OBJECT IDENTIFIER ::= { hh3cevtModuleSwitchType 480 } -- 4-Port OC-48c/STM-16c POS Optical Interface Card,(SFP,LC)
hh3cevtModuleSw-LSR1DTCP8L1                 OBJECT IDENTIFIER ::= { hh3cevtModuleSwitchType 481 } -- 8-Port OC-3c/OC-12c POS/GE Optical Interface Card,(SFP,LC)
hh3cevtModuleSw-LSR1DXP1L1                  OBJECT IDENTIFIER ::= { hh3cevtModuleSwitchType 482 } -- 1-Port 10GBASE-R/W Ethernet Optical Interface Card,(XPF,LC)
hh3cevtModuleSw-LSR1DGP10L1                 OBJECT IDENTIFIER ::= { hh3cevtModuleSwitchType 483 } -- 10-Port 1000BASE-X Optical Interface Card,(SFP,LC)
hh3cevtModuleSw-LSR1LN1BNL1                 OBJECT IDENTIFIER ::= { hh3cevtModuleSwitchType 484 } -- Single Service Processing Board
hh3cevtModuleSw-LSR1LN2BL1                  OBJECT IDENTIFIER ::= { hh3cevtModuleSwitchType 485 } -- Dual Serivice Processing Board
hh3cevtModuleSw-LSR1SRP2D1                  OBJECT IDENTIFIER ::= { hh3cevtModuleSwitchType 486 } -- Switching and Route Process Unit With Clock
hh3cevtModuleSw-IM-NAT-II                   OBJECT IDENTIFIER ::= { hh3cevtModuleSwitchType 487 } -- Network Address Translation Service Processing Board,II
hh3cevtModuleSw-IM-NAM-II                   OBJECT IDENTIFIER ::= { hh3cevtModuleSwitchType 488 } -- Net Analysis Service Processing Board,II
hh3cevtModuleSw-CR-MRP-I                    OBJECT IDENTIFIER ::= { hh3cevtModuleSwitchType 489 } -- Management and Route Unit With OAM Module and Clock Module
hh3cevtModuleSw-CR-SF18C                    OBJECT IDENTIFIER ::= { hh3cevtModuleSwitchType 490 } -- Switch Fabric Card
hh3cevtModuleSw-CR-SF08C                    OBJECT IDENTIFIER ::= { hh3cevtModuleSwitchType 491 } -- Switch Fabric Card
hh3cevtModuleSw-CR-SPC-XP8LEF               OBJECT IDENTIFIER ::= { hh3cevtModuleSwitchType 492 } -- 8-Port 10GBASE-R/W Interface Module,(XFP,LC)
hh3cevtModuleSw-CR-SPC-XP4LEF               OBJECT IDENTIFIER ::= { hh3cevtModuleSwitchType 493 } -- 4-Port 10GBASE-R/W Interface Module,(XFP,LC)
hh3cevtModuleSw-CR-SPC-GP48LEF              OBJECT IDENTIFIER ::= { hh3cevtModuleSwitchType 494 } -- 48-Port 1000BASE-X Interface Module,(SFP,LC)
hh3cevtModuleSw-CR-SPC-GT48LEF              OBJECT IDENTIFIER ::= { hh3cevtModuleSwitchType 495 } -- 48-Port 10/100/1000BASE-T Interface Module
hh3cevtModuleSw-CR-SPE-3020-E               OBJECT IDENTIFIER ::= { hh3cevtModuleSwitchType 496 } -- Double XG Service Board (Enhanced)
hh3cevtModuleSw-CR-SPC-PUP4L-E              OBJECT IDENTIFIER ::= { hh3cevtModuleSwitchType 497 } -- 4-Port 10G POS Optical Interface Module,(XFP,LC)
hh3cevtModuleSw-LST1SF08C1                  OBJECT IDENTIFIER ::= { hh3cevtModuleSwitchType 498 } -- Switch Fabric Card
hh3cevtModuleSw-LST1SF18C1                  OBJECT IDENTIFIER ::= { hh3cevtModuleSwitchType 499 } -- Switch Fabric Card

--
-- 500 to 699 reserved for secondary switches part I
--
hh3cevtModuleSw-LS81GP16TM                  OBJECT IDENTIFIER ::= { hh3cevtModuleSwitchType 500 } -- 12-port 1000BASE-X SFP Interface and 4-port 1000BASE-T/1000BASE-X Combo Interface Metro Switch and Route Processing Board
hh3cevtModuleSw-LS81VP4C                    OBJECT IDENTIFIER ::= { hh3cevtModuleSwitchType 501 } -- 4-port 1000BASE-X SFP Interface Virtual Daughter Card
hh3cevtModuleSw-LS8M1PT8P0                  OBJECT IDENTIFIER ::= { hh3cevtModuleSwitchType 502 } -- 8-Port 1000BASE-PX Optical Line Interface Board, SFP Req
hh3cevtModuleSw-LS8M1PT8GB0                 OBJECT IDENTIFIER ::= { hh3cevtModuleSwitchType 503 } -- 8-Port 1000BASE-PX20 Gigabit Passive Optical Line Interface Board B(20km, SFF), SC Connector
hh3cevtModuleSw-LS8M1PT4GB0                 OBJECT IDENTIFIER ::= { hh3cevtModuleSwitchType 504 } -- 4-Port 1000BASE-PX20 Gigabit Passive Optical Line Interface Board B(20km, SFF), SC Connector
hh3cevtModuleSw-LS81GP2R                    OBJECT IDENTIFIER ::= { hh3cevtModuleSwitchType 505 } -- 2-port 1000M Ethernet Optical Interface RPR Board
hh3cevtModuleSw-LS81GP4R                    OBJECT IDENTIFIER ::= { hh3cevtModuleSwitchType 506 } -- 4-port 1000M Ethernet Optical Interface RPR Board
hh3cevtModuleSw-LS81IPSECA                  OBJECT IDENTIFIER ::= { hh3cevtModuleSwitchType 507 } -- IPSec Service Board
hh3cevtModuleSw-LS81FWA                     OBJECT IDENTIFIER ::= { hh3cevtModuleSwitchType 508 } -- Firewall Service Board
hh3cevtModuleSw-LS82VSNP                    OBJECT IDENTIFIER ::= { hh3cevtModuleSwitchType 509 } -- Versatile Network Processing Service Module (PBR/NAT/NetStream) with 12-port 1000BASE-X SFP, XGBUS Uplink
hh3cevtModuleSw-LSQ1GV48SA                  OBJECT IDENTIFIER ::= { hh3cevtModuleSwitchType 510 } -- 48-Port 1000Base-T Gigabit Ethernet Interface Board(RJ45)
hh3cevtModuleSw-LSQ1SRPB                    OBJECT IDENTIFIER ::= { hh3cevtModuleSwitchType 511 } -- Salience VI
hh3cevtModuleSw-LSQ1SRP2XB                  OBJECT IDENTIFIER ::= { hh3cevtModuleSwitchType 512 } -- Salience VI-10GE
hh3cevtModuleSw-LSQ1SRP1CB                  OBJECT IDENTIFIER ::= { hh3cevtModuleSwitchType 513 } -- Salience VI-Turbo
hh3cevtModuleSw-LSQ1FV48SA                  OBJECT IDENTIFIER ::= { hh3cevtModuleSwitchType 514 } -- 48-Port 100M Ethernet Electrical Interface Switch Unit(RJ45)
hh3cevtModuleSw-LSD1MPUA                    OBJECT IDENTIFIER ::= { hh3cevtModuleSwitchType 515 } -- Main Control Unit
hh3cevtModuleSw-LSD1GP20A0                  OBJECT IDENTIFIER ::= { hh3cevtModuleSwitchType 516 } -- 16-port 1000BASE-X SFP Interface and 4-port 1000BASE-T/1000BASE-X Combo Interface Line Card
hh3cevtModuleSw-LSD1GP20TA0                 OBJECT IDENTIFIER ::= { hh3cevtModuleSwitchType 517 } -- 16-port 1000BASE-X SFP Interface and 4-port 1000BASE-T/1000BASE-X Combo Interface and 16 1000BASE-T Interface Line Card
hh3cevtModuleSw-LSD1GP36A0                  OBJECT IDENTIFIER ::= { hh3cevtModuleSwitchType 518 } -- 32-port 1000BASE-X SFP Interface and 4-port 1000BASE-T/1000BASE-X Combo Interface Line Card
hh3cevtModuleSw-LSD1GP20XA0                 OBJECT IDENTIFIER ::= { hh3cevtModuleSwitchType 519 } -- 16-port 1000BASE-X SFP Interface and 4-port 1000BASE-T/1000BASE-X Combo Interface and 2-port 10GBASE-X XFP Interface Line Card
hh3cevtModuleSw-LSD1GP20EA0                 OBJECT IDENTIFIER ::= { hh3cevtModuleSwitchType 520 } -- 16-port 1000BASE-X SFP Interface and 4-port 1000BASE-T/1000BASE-X Combo Interface and 2-port GE RPR Interface Line Card
hh3cevtModuleSw-LSD1GP20RA0                 OBJECT IDENTIFIER ::= { hh3cevtModuleSwitchType 521 } -- 16-port 1000BASE-X SFP Interface and 4-port 1000BASE-T/1000BASE-X Combo Interface and 2-port OC48 RPR Interface Line Card
hh3cevtModuleSw-LSD1GP16A0                  OBJECT IDENTIFIER ::= { hh3cevtModuleSwitchType 522 } -- 16-port 1000BASE-X SFP Ethernet Interface SubCard
hh3cevtModuleSw-LSD1GT16A0                  OBJECT IDENTIFIER ::= { hh3cevtModuleSwitchType 523 } -- 16-port 1000BASE-T Ethernet Interface SubCard
hh3cevtModuleSw-LSD1XP2A0                   OBJECT IDENTIFIER ::= { hh3cevtModuleSwitchType 524 } -- 2-port 10GBASE-X XFP Ethernet Interface SubCard
hh3cevtModuleSw-LSD1EP2A0                   OBJECT IDENTIFIER ::= { hh3cevtModuleSwitchType 525 } -- 2-port 1000BASE-T Ethernet RPR Interface SubCard
hh3cevtModuleSw-LSD1RP2A0                   OBJECT IDENTIFIER ::= { hh3cevtModuleSwitchType 526 } -- 2-port OC48 RPR Interface SubCard
hh3cevtModuleSw-LSQ1GV48SC                  OBJECT IDENTIFIER ::= { hh3cevtModuleSwitchType 527 } -- 48-Port 1000Base-T Gigabit Ethernet Interface Board(RJ45)-POE
hh3cevtModuleSw-LSQ1FP48SA                  OBJECT IDENTIFIER ::= { hh3cevtModuleSwitchType 528 } -- 48 Port 100M Ethernet Optical Interface Board(SFP,LC)
hh3cevtModuleSw-LSQ1GP24SC                  OBJECT IDENTIFIER ::= { hh3cevtModuleSwitchType 529 } -- 24 Port 1000BASE-X Ethernet Optical Interface Board(SFP,LC)
hh3cevtModuleSw-LSQ1GT24SC                  OBJECT IDENTIFIER ::= { hh3cevtModuleSwitchType 530 } -- 24-Port 1000BASE-T Ethernet Interface Board (RJ45)
hh3cevtModuleSw-LSQ1TGX2SC                  OBJECT IDENTIFIER ::= { hh3cevtModuleSwitchType 531 } -- 2-Port 10GBASE Ethernet Optical Interface Board(XFP,LC)
hh3cevtModuleSw-LSQ1GP12EA                  OBJECT IDENTIFIER ::= { hh3cevtModuleSwitchType 532 } -- 12-Port 1000BASE-X Ethernet Optical Interface Board(SFP,LC)
hh3cevtModuleSw-LSQ1TGX1EA                  OBJECT IDENTIFIER ::= { hh3cevtModuleSwitchType 533 } -- 1-Port 10GBASE Ethernet Optical Interface Module(XFP,LC)
hh3cevtModuleSw-LSQ1P24XGSC                 OBJECT IDENTIFIER ::= { hh3cevtModuleSwitchType 534 } -- 24-Port 1000BASE-X Gigabit Ethernet Optical Interface(SFP,LC)+2-Port 10GBASE Ethernet Optical Interface Board(XFP,LC)
hh3cevtModuleSw-LSQ1T24XGSC                 OBJECT IDENTIFIER ::= { hh3cevtModuleSwitchType 535 } -- 24-Port 1000BASE-T Gigabit Ethernet Interface(RJ45)+2-Port 10GBASE Ethernet Optical Interface Board(XFP,LC)
hh3cevtModuleSw-LS81TGX1B                   OBJECT IDENTIFIER ::= { hh3cevtModuleSwitchType 536 } -- 1 Port 10GBase-R Ethernet Interface Board(XENPAK,SC)
hh3cevtModuleSw-LSQ1PT4PSC0                 OBJECT IDENTIFIER ::= { hh3cevtModuleSwitchType 537 } -- 4-Port 1000Base-PX Optical Line Terminal(EPON OLT SFP,SC)+8-Port 1000BASE-X Optical Interface Board(SFP,LC)
hh3cevtModuleSw-LS81SRPG13                  OBJECT IDENTIFIER ::= { hh3cevtModuleSwitchType 538 } -- Salience V, Switch and Route Processing Board
hh3cevtModuleSw-LS81SRPG14                  OBJECT IDENTIFIER ::= { hh3cevtModuleSwitchType 539 } -- Salience V Edge
hh3cevtModuleSw-LS81SRPG15                  OBJECT IDENTIFIER ::= { hh3cevtModuleSwitchType 540 } -- Salience V Plus
hh3cevtModuleSw-LSQ1GP48SC0                 OBJECT IDENTIFIER ::= { hh3cevtModuleSwitchType 541 } -- 48-Port 1000BASE Ethernet Optical Interface Board(SFP,LC)
hh3cevtModuleSw-LSQ1GP12SC0                 OBJECT IDENTIFIER ::= { hh3cevtModuleSwitchType 542 } -- 12-Port 1000BASE-X Ethernet Optical Interface Board(SFP,LC)
hh3cevtModuleSw-LSD1SRPA                    OBJECT IDENTIFIER ::= { hh3cevtModuleSwitchType 543 } -- Salience VIII 160
hh3cevtModuleSw-LSD1SRPB                    OBJECT IDENTIFIER ::= { hh3cevtModuleSwitchType 544 } -- Salience VIII 480
hh3cevtModuleSw-LSD1SRPC                    OBJECT IDENTIFIER ::= { hh3cevtModuleSwitchType 545 } -- Salience VIII 800
hh3cevtModuleSw-LSD1GT16PES0                OBJECT IDENTIFIER ::= { hh3cevtModuleSwitchType 546 } -- 16-Port 10/100/1000BASE-T and 8-Port 100/1000BASE-X SFP Interface Card
hh3cevtModuleSw-LSD1GP24ES0                 OBJECT IDENTIFIER ::= { hh3cevtModuleSwitchType 547 } -- 24-Port 1000BASE-X Ethernet SFP Interface Card
hh3cevtModuleSw-LSD1GT24XES0                OBJECT IDENTIFIER ::= { hh3cevtModuleSwitchType 548 } -- 24-Port 10/100/1000BASE-T and 2-port 10GBASE-X Ethernet XFP Optical Interface Card
hh3cevtModuleSw-LSD1GP24XES0                OBJECT IDENTIFIER ::= { hh3cevtModuleSwitchType 549 } -- 24-Port 1000BASE-X Ethernet SFP interface and 2-port 10GBASE-X Ethernet XFP Optical Interface Card
hh3cevtModuleSw-LSD1XP2ES0                  OBJECT IDENTIFIER ::= { hh3cevtModuleSwitchType 550 } -- 2-Port 10GBASE-X Ethernet XFP Optical Interface Card
hh3cevtModuleSw-LSD1GP48ES0                 OBJECT IDENTIFIER ::= { hh3cevtModuleSwitchType 551 } -- 48-Port 1000BASE-X Ethernet SFP Interface Card
hh3cevtModuleSw-LSQ1MPUA0                   OBJECT IDENTIFIER ::= { hh3cevtModuleSwitchType 552 } -- Master Process Board
hh3cevtModuleSw-LSQ1MPUA1                   OBJECT IDENTIFIER ::= { hh3cevtModuleSwitchType 553 } -- Master Process Unit
hh3cevtModuleSw-LSQ1FWBSC0                  OBJECT IDENTIFIER ::= { hh3cevtModuleSwitchType 554 } -- Gigabit Firewall Card, 4 Gigabit Port for Management
hh3cevtModuleSw-LSQ1PT8PSC0                 OBJECT IDENTIFIER ::= { hh3cevtModuleSwitchType 555 } -- 8-Port 1000Base-PX Optical Line Terminal(EPON OLT SFP,SC)+8-Port 1000BASE-X Optical Interface Board(SFP,LC)
hh3cevtModuleSw-LSQ1PT16PSC0                OBJECT IDENTIFIER ::= { hh3cevtModuleSwitchType 556 } -- 16-Port 1000Base-PX Optical Line Terminal(EPON OLT SFP,SC)+8-Port 1000BASE-X Optical Interface Board(SFP,LC)
hh3cevtModuleSw-SA11MPUA0                   OBJECT IDENTIFIER ::= { hh3cevtModuleSwitchType 557 } -- SmartEngine I-Lite
hh3cevtModuleSw-SA11MPUB0                   OBJECT IDENTIFIER ::= { hh3cevtModuleSwitchType 558 } -- SmartEngine I
hh3cevtModuleSw-LSQ1AFCBSC0                 OBJECT IDENTIFIER ::= { hh3cevtModuleSwitchType 559 } -- Anomaly Flow Cleaner Board Interface Board(SFP,LC)
hh3cevtModuleSw-LSQ1MPUB0                   OBJECT IDENTIFIER ::= { hh3cevtModuleSwitchType 560 } -- Salience VI-Lite
hh3cevtModuleSw-LSQ1MPUB1                   OBJECT IDENTIFIER ::= { hh3cevtModuleSwitchType 561 } -- Salience VI-Lite
hh3cevtModuleSw-LSQ1PT4PSC1                 OBJECT IDENTIFIER ::= { hh3cevtModuleSwitchType 562 } -- 4-Port 1000Base-PX Optical Line Terminal(EPON OLT SFP,SC)+8-Port 1000BASE-X Optical Interface Board(SFP,LC)
hh3cevtModuleSw-LSQ1PT8PSC1                 OBJECT IDENTIFIER ::= { hh3cevtModuleSwitchType 563 } -- 8-Port 1000Base-PX Optical Line Terminal(EPON OLT SFP,SC)+8-Port 1000BASE-X Optical Interface Board(SFP,LC)
hh3cevtModuleSw-LSQ1PT16PSC1                OBJECT IDENTIFIER ::= { hh3cevtModuleSwitchType 564 } -- 16-Port 1000Base-PX Optical Line Terminal(EPON OLT SFP,SC)+8-Port 1000BASE-X Optical Interface Board(SFP,LC)
hh3cevtModuleSw-LSQ1FP48USA0                OBJECT IDENTIFIER ::= { hh3cevtModuleSwitchType 565 } -- 48-Port 100M Ethernet Optical Interface Switch Unit(SFP,LC)
hh3cevtModuleSw-LSQ1FP48USA1                OBJECT IDENTIFIER ::= { hh3cevtModuleSwitchType 566 } -- 48-Port 100M Ethernet Optical Interface Switch Unit(SFP,LC)
hh3cevtModuleSw-LSQ1FV48USA0                OBJECT IDENTIFIER ::= { hh3cevtModuleSwitchType 567 } -- 48-Port 100M Ethernet Electrical Interface Switch Unit(RJ45),PoE
hh3cevtModuleSw-LSQ1FV48USA1                OBJECT IDENTIFIER ::= { hh3cevtModuleSwitchType 568 } -- 48-Port 100M Ethernet Electrical Interface Switch Unit(RJ45),PoE
hh3cevtModuleSw-LSQ1SRPD0                   OBJECT IDENTIFIER ::= { hh3cevtModuleSwitchType 569 } -- Switch and Route Processing Unit, Salience VI-Plus
hh3cevtModuleSw-LSQ1CGP24TSC0               OBJECT IDENTIFIER ::= { hh3cevtModuleSwitchType 570 } -- Switching and Routing Processing Unit with 24 1000BASE-X Gigabit Ethernet Optical Ports,including 8 Combo Ports,SFP Req.
hh3cevtModuleSw-LSQ1GP24TSC0                OBJECT IDENTIFIER ::= { hh3cevtModuleSwitchType 571 } -- 16-Port 1000BASE-X Gigabit Ethernet Optical(SFP,LC) And 8-Port 10/100/1000BASE-T RJ45/1000BASE-X SFP Combo Interface Board
hh3cevtModuleSw-LSQ1ACGASC0                 OBJECT IDENTIFIER ::= { hh3cevtModuleSwitchType 572 } -- Application Control Gateway Board
hh3cevtModuleSw-LSD1XP1ES0                  OBJECT IDENTIFIER ::= { hh3cevtModuleSwitchType 573 } -- 1-Port 10GBASE-X Ethernet XFP Optical Interface Card
hh3cevtModuleSw-LSD1GP12ES0                 OBJECT IDENTIFIER ::= { hh3cevtModuleSwitchType 574 } -- 12-Port 1000BASE-X Ethernet SFP Interface Card
hh3cevtModuleSw-LSQ1SRP12GB0                OBJECT IDENTIFIER ::= { hh3cevtModuleSwitchType 575 } -- Switch And Route Processing Unit with 12 1000BASE Ethernet Optical Interfaces(SFP,LC),Salience VI-GE
hh3cevtModuleSw-LSQ1GV40PSC0                OBJECT IDENTIFIER ::= { hh3cevtModuleSwitchType 576 } -- 40-Port 10/100/1000BASE-T Electrical(RJ45) And 8-Port 1000BASE-X Optical Ethernet Interface Board(SFP,LC),PoE
hh3cevtModuleSw-LSQ1FWBSC1                  OBJECT IDENTIFIER ::= { hh3cevtModuleSwitchType 577 } -- Firewall Board
hh3cevtModuleSw-LSQ1NSMSC0                  OBJECT IDENTIFIER ::= { hh3cevtModuleSwitchType 578 } -- NetStream Board
hh3cevtModuleSw-LSQ1NSMSC1                  OBJECT IDENTIFIER ::= { hh3cevtModuleSwitchType 579 } -- NetStream Board
hh3cevtModuleSw-LSQ1AFDBSC0                 OBJECT IDENTIFIER ::= { hh3cevtModuleSwitchType 580 } -- Anomaly Flow Detector Board
hh3cevtModuleSw-LS81MPUB                    OBJECT IDENTIFIER ::= { hh3cevtModuleSwitchType 581 } -- Salience IV
hh3cevtModuleSw-LS81FP48XL                  OBJECT IDENTIFIER ::= { hh3cevtModuleSwitchType 582 } -- 48-Port 100M Ethernet Optical Interface Module,(SFP,LC)
hh3cevtModuleSw-LS81FT48XL                  OBJECT IDENTIFIER ::= { hh3cevtModuleSwitchType 583 } -- 48-Port 10/100M Ethernet Electrical Interface Module(RJ45)
hh3cevtModuleSw-LS81GP12XL                  OBJECT IDENTIFIER ::= { hh3cevtModuleSwitchType 584 } -- 12-Port 1000/100M Ethernet Optical Interface Module(SFP,LC)
hh3cevtModuleSw-LS81GP24XL                  OBJECT IDENTIFIER ::= { hh3cevtModuleSwitchType 585 } -- 24-Port 1000/100M Ethernet Optical Interface Module(SFP,LC)
hh3cevtModuleSw-LS81GP48XL                  OBJECT IDENTIFIER ::= { hh3cevtModuleSwitchType 586 } -- 48-Port 1000/100M Ethernet Optical Interface Module(SFP,LC)
hh3cevtModuleSw-LS81GT24XL                  OBJECT IDENTIFIER ::= { hh3cevtModuleSwitchType 587 } -- 24-Port 10/100/1000M Ethernet Electrical Interface Module(RJ45)
hh3cevtModuleSw-LS81GT48XL                  OBJECT IDENTIFIER ::= { hh3cevtModuleSwitchType 588 } -- 48-Port 10/100/1000M Ethernet Electrical Interface Module(RJ45)
hh3cevtModuleSw-LS81TGX2XL                  OBJECT IDENTIFIER ::= { hh3cevtModuleSwitchType 589 } -- 2-Port 10GBASE Ethernet Optical Interface Module(XFP,LC)
hh3cevtModuleSw-LSQ1GV48SD0                 OBJECT IDENTIFIER ::= { hh3cevtModuleSwitchType 590 } -- 48-Port 1000Base-T Gigabit Ethernet Interface Board(RJ45),PoE
hh3cevtModuleSw-LSQ1GP48EB0                 OBJECT IDENTIFIER ::= { hh3cevtModuleSwitchType 591 } -- 48-Port Enhanced 1000BASE-X Ethernet Optical Interface Board(SFP,LC)
hh3cevtModuleSw-LSQ1IPSSC0                  OBJECT IDENTIFIER ::= { hh3cevtModuleSwitchType 592 } -- Gigabit IPS Card
hh3cevtModuleSw-LSQ1GV48SD1                 OBJECT IDENTIFIER ::= { hh3cevtModuleSwitchType 593 } -- 48-Port 1000Base-T Gigabit Ethernet Interface Board(RJ45),PoE
hh3cevtModuleSw-LSQ1GP48SD0                 OBJECT IDENTIFIER ::= { hh3cevtModuleSwitchType 594 } -- 48-Port 1000BASE-X Gigabit Ethernet Optical Interface(SFP,LC) Interface Board
hh3cevtModuleSw-LSQ1GP48SD1                 OBJECT IDENTIFIER ::= { hh3cevtModuleSwitchType 595 } -- 48-Port 1000BASE-X Gigabit Ethernet Optical Interface(SFP,LC) Interface Board
hh3cevtModuleSw-LSQ1SRPA0                   OBJECT IDENTIFIER ::= { hh3cevtModuleSwitchType 596 } -- Salience VI-Smart
hh3cevtModuleSw-LSQ1SRPA1                   OBJECT IDENTIFIER ::= { hh3cevtModuleSwitchType 597 } -- Salience VI-Smart
hh3cevtModuleSw-LSQ2FP48SA0                 OBJECT IDENTIFIER ::= { hh3cevtModuleSwitchType 598 } -- 48 Port 100M Ethernet Optical Interface Board(SFP,LC)
hh3cevtModuleSw-LSQ2FP48SA1                 OBJECT IDENTIFIER ::= { hh3cevtModuleSwitchType 599 } -- 48 Port 100M Ethernet Optical Interface Board(SFP,LC)
hh3cevtModuleSw-LSQ2FT48SA0                 OBJECT IDENTIFIER ::= { hh3cevtModuleSwitchType 600 } -- 48-Port 100M Ethernet Electrical Interface Switch Unit(RJ45)
hh3cevtModuleSw-LSQ2FT48SA1                 OBJECT IDENTIFIER ::= { hh3cevtModuleSwitchType 601 } -- 48-Port 100M Ethernet Electrical Interface Switch Unit(RJ45)
hh3cevtModuleSw-LSQ1GV24PSC0                OBJECT IDENTIFIER ::= { hh3cevtModuleSwitchType 602 } -- 24-Port 10/100/1000BASE-T Electrical(RJ45) Interface Board,including 4 Combo Ports,SFP Req,PoE,No Spell
hh3cevtModuleSw-LSQ1GV24PSC1                OBJECT IDENTIFIER ::= { hh3cevtModuleSwitchType 603 } -- 24-Port 10/100/1000BASE-T Electrical(RJ45) Interface Board,including 4 Combo Ports,SFP Req,PoE,No Spell
hh3cevtModuleSw-LSQ1CGV24PSC0               OBJECT IDENTIFIER ::= { hh3cevtModuleSwitchType 604 } -- Switching and Routing Processing Unit with 24 10/100/1000BASE-T Electrical Ports(RJ45),including 4 Combo Ports,SFP Req,PoE,No Spell
hh3cevtModuleSw-LSQ1CGV24PSC1               OBJECT IDENTIFIER ::= { hh3cevtModuleSwitchType 605 } -- Switching and Routing Processing Unit with 24 10/100/1000BASE-T Electrical Ports(RJ45),including 4 Combo Ports,SFP Req,PoE,No Spell
hh3cevtModuleSw-LSQ1GP24TEB0                OBJECT IDENTIFIER ::= { hh3cevtModuleSwitchType 606 } -- 16-Port 1000BASE-X Gigabit Ethernet Optical Interface(SFP,LC)+8-Port Combo Interface Board
hh3cevtModuleSw-LSQ1GP24TEB1                OBJECT IDENTIFIER ::= { hh3cevtModuleSwitchType 607 } -- 16-Port 1000BASE-X Gigabit Ethernet Optical Interface(SFP,LC)+8-Port Combo Interface Board
hh3cevtModuleSw-LSQ1GP24TSD0                OBJECT IDENTIFIER ::= { hh3cevtModuleSwitchType 608 } -- 16-Port 1000BASE-X Gigabit Ethernet Optical Interface(SFP,LC)+8-Port Combo Interface Board
hh3cevtModuleSw-LSQ1GP24TSD1                OBJECT IDENTIFIER ::= { hh3cevtModuleSwitchType 609 } -- 16-Port 1000BASE-X Gigabit Ethernet Optical Interface(SFP,LC)+8-Port Combo Interface Board
hh3cevtModuleSw-LSQ1GP24TXSD0               OBJECT IDENTIFIER ::= { hh3cevtModuleSwitchType 610 } -- 16-Port GE Optical Interface(SFP,LC)+8-Port Combo Interface+2-Port 10GE Optical Interface Board(XFP,LC)
hh3cevtModuleSw-LSQ1GP24TXSD1               OBJECT IDENTIFIER ::= { hh3cevtModuleSwitchType 611 } -- 16-Port GE Optical Interface(SFP,LC)+8-Port Combo Interface+2-Port 10GE Optical Interface Board(XFP,LC)
hh3cevtModuleSw-LSQ1TGX2EB0                 OBJECT IDENTIFIER ::= { hh3cevtModuleSwitchType 612 } -- 2-Port 10GBASE Ethernet Optical Interface Board(XFP,LC)
hh3cevtModuleSw-LSQ1TGX2EB1                 OBJECT IDENTIFIER ::= { hh3cevtModuleSwitchType 613 } -- 2-Port 10GBASE Ethernet Optical Interface Board(XFP,LC)
hh3cevtModuleSw-LSQ1TGX2SD0                 OBJECT IDENTIFIER ::= { hh3cevtModuleSwitchType 614 } -- 2-Port 10GBASE Ethernet Optical Interface Board(XFP,LC)
hh3cevtModuleSw-LSQ1TGX2SD1                 OBJECT IDENTIFIER ::= { hh3cevtModuleSwitchType 615 } -- 2-Port 10GBASE Ethernet Optical Interface Board(XFP,LC)
hh3cevtModuleSw-LSQ1TGX4SD0                 OBJECT IDENTIFIER ::= { hh3cevtModuleSwitchType 616 } -- 4-Port 10GBASE Ethernet Optical Interface Board(XFP,LC)
hh3cevtModuleSw-LSQ1TGX4SD1                 OBJECT IDENTIFIER ::= { hh3cevtModuleSwitchType 617 } -- 4-Port 10GBASE Ethernet Optical Interface Board(XFP,LC)
hh3cevtModuleSw-LSQ1TGX8SD0                 OBJECT IDENTIFIER ::= { hh3cevtModuleSwitchType 618 } -- 8-Port 10GBASE Ethernet Optical Interface Board(XFP,LC)
hh3cevtModuleSw-LSQ1TGX8SD1                 OBJECT IDENTIFIER ::= { hh3cevtModuleSwitchType 619 } -- 8-Port 10GBASE Ethernet Optical Interface Board(XFP,LC)
hh3cevtModuleSw-LSQ1GP48EB1                 OBJECT IDENTIFIER ::= { hh3cevtModuleSwitchType 620 } -- 48-Port Enhanced 1000BASE-X Ethernet Optical Interface Board(SFP,LC)
hh3cevtModuleSw-LSQ1TGX4EB0                 OBJECT IDENTIFIER ::= { hh3cevtModuleSwitchType 621 } -- 4-Port 10GBASE Ethernet Optical Interface Board(XFP,LC)
hh3cevtModuleSw-LSQ1TGX4EB1                 OBJECT IDENTIFIER ::= { hh3cevtModuleSwitchType 622 } -- 4-Port 10GBASE Ethernet Optical Interface Board(XFP,LC)
hh3cevtModuleSw-LSQ1GP12SC3                 OBJECT IDENTIFIER ::= { hh3cevtModuleSwitchType 623 } -- 12-Port 1000BASE-X Ethernet Optical Interface Board(SFP,LC)
hh3cevtModuleSw-LSQ1GP24TSC3                OBJECT IDENTIFIER ::= { hh3cevtModuleSwitchType 624 } -- 16-Port 1000BASE-X Gigabit Ethernet Optical(SFP,LC) And 8-Port 10/100/1000BASE-T RJ45/1000BASE-X SFP Combo Interface Board
hh3cevtModuleSw-LSQ1GP48SC3                 OBJECT IDENTIFIER ::= { hh3cevtModuleSwitchType 625 } -- 48-Port 1000BASE Ethernet Optical Interface Board(SFP,LC)
hh3cevtModuleSw-LSQ1GV48SC3                 OBJECT IDENTIFIER ::= { hh3cevtModuleSwitchType 626 } -- 48-Port 1000Base-T Gigabit Ethernet Interface Board(RJ45),PoE
hh3cevtModuleSw-LSQ1MPUA3                   OBJECT IDENTIFIER ::= { hh3cevtModuleSwitchType 627 } -- Master Process Board
hh3cevtModuleSw-LSQ1SRP1CB3                 OBJECT IDENTIFIER ::= { hh3cevtModuleSwitchType 628 } -- Salience VI-Turbo
hh3cevtModuleSw-LSQ1SRPA3                   OBJECT IDENTIFIER ::= { hh3cevtModuleSwitchType 629 } -- Salience VI-Smart
hh3cevtModuleSw-LSQ2FP48SA3                 OBJECT IDENTIFIER ::= { hh3cevtModuleSwitchType 630 } -- 48 Port 100M Ethernet Optical Interface Board(SFP,LC)
hh3cevtModuleSw-LSQ2FT48SA3                 OBJECT IDENTIFIER ::= { hh3cevtModuleSwitchType 631 } -- 48-Port 100M Ethernet Electrical Interface Switch Unit(RJ45)
hh3cevtModuleSw-LSQ1MPUB3                   OBJECT IDENTIFIER ::= { hh3cevtModuleSwitchType 632 } -- Salience VI-Lite
hh3cevtModuleSw-LSQ1CGP24TSC3               OBJECT IDENTIFIER ::= { hh3cevtModuleSwitchType 633 } -- Switching and Routing Processing Unit with 24 1000BASE-X Gigabit Ethernet Optical Ports,including 8 Combo Ports,SFP Req.
hh3cevtModuleSw-LSQ1MPUB4                   OBJECT IDENTIFIER ::= { hh3cevtModuleSwitchType 634 } -- Salience VI-Lite
hh3cevtModuleSw-LSQ1SRPD4                   OBJECT IDENTIFIER ::= { hh3cevtModuleSwitchType 635 } -- Salience VI-Plus
hh3cevtModuleSw-LSQ1SSLSC0                  OBJECT IDENTIFIER ::= { hh3cevtModuleSwitchType 636 } -- SSL VPN Service Board(B)
hh3cevtModuleSw-LSQ1LBSC0                   OBJECT IDENTIFIER ::= { hh3cevtModuleSwitchType 637 } -- Gigabit Load Balancing Card
hh3cevtModuleSw-LSQ1NAT24SC0                OBJECT IDENTIFIER ::= { hh3cevtModuleSwitchType 638 } -- NAT/NetStream-Supported Line Processing Unit with 24 10/100/1000BASE-T Electrical Ports(RJ45),including Combo Ports,Upgradeable to PoE
hh3cevtModuleSw-LSQ1SRP12GB4                OBJECT IDENTIFIER ::= { hh3cevtModuleSwitchType 639 } -- Salience VI-GE
hh3cevtModuleSw-LSQ1TGS8SC0                 OBJECT IDENTIFIER ::= { hh3cevtModuleSwitchType 640 } -- 8-Port 10GBASE Ethernet SFP+ Optical Interface Board
hh3cevtModuleSw-LSQ3PT4PSC0                 OBJECT IDENTIFIER ::= { hh3cevtModuleSwitchType 641 } -- 4-Port 1000Base-PX Optical Line Terminal(EPON OLT SFP,SC)+8-Port 1000BASE-X Optical Interface Board(SFP,LC)
hh3cevtModuleSw-EWPXM2MPUB0                 OBJECT IDENTIFIER ::= { hh3cevtModuleSwitchType 642 } -- Salience VI-Lite
hh3cevtModuleSw-EWPXM2SRP12GB0              OBJECT IDENTIFIER ::= { hh3cevtModuleSwitchType 643 } -- Salience VI-GE
hh3cevtModuleSw-EWPXM2SRPD0                 OBJECT IDENTIFIER ::= { hh3cevtModuleSwitchType 644 } -- Salience VI-Plus
hh3cevtModuleSw-EWPXM2GP24TSD0              OBJECT IDENTIFIER ::= { hh3cevtModuleSwitchType 645 } -- 16-Port 1000BASE-X Ethernet Optical Interface(SFP Req.)+8-Port Combo Interface Module
hh3cevtModuleSw-EWPXM2GP24TXSD0             OBJECT IDENTIFIER ::= { hh3cevtModuleSwitchType 646 } -- 16-Port 1000BASE-X Ethernet Optical Interface(SFP Req.)+8-Port Combo Interface+2-Port 10GE Optical Interface(XFP Req.) Module
hh3cevtModuleSw-EWPXM2TGX4SD0               OBJECT IDENTIFIER ::= { hh3cevtModuleSwitchType 647 } -- 4-Port 10GBASE Ethernet Optical Interface Module,XFP Req
hh3cevtModuleSw-EWPXM2GP48SD0               OBJECT IDENTIFIER ::= { hh3cevtModuleSwitchType 648 } -- 48-Port 1000BASE-X Gigabit Ethernet Optical Interface Module,SFP Req
hh3cevtModuleSw-EWPXM2GP24TSC0              OBJECT IDENTIFIER ::= { hh3cevtModuleSwitchType 649 } -- 24-Port 1000BASE-X/100BASE-FX Optical  Interface Module,including 8 Combo Ports,SFP Req
hh3cevtModuleSw-EWPXM2TGX2SC0               OBJECT IDENTIFIER ::= { hh3cevtModuleSwitchType 650 } -- 2-Port 10GBASE Ethernet Optical Interface Module,XFP Req
hh3cevtModuleSw-EWPXM2GP48SC0               OBJECT IDENTIFIER ::= { hh3cevtModuleSwitchType 651 } -- 48-Port 1000BASE-X/100BASE-FX Ethernet Optical Interface Module,SFP Req
hh3cevtModuleSw-LS7500-GP48-SC              OBJECT IDENTIFIER ::= { hh3cevtModuleSwitchType 652 } -- 48-Port 1000BASE-X/100BASE-FX Ethernet Optical Interface Module(SFP,LC)
hh3cevtModuleSw-LS7500-GP48-SD              OBJECT IDENTIFIER ::= { hh3cevtModuleSwitchType 653 } -- 48-Port 1000BASE-X Gigabit Ethernet Optical Interface Module(SFP,LC)
hh3cevtModuleSw-LS7500-GT48-SC              OBJECT IDENTIFIER ::= { hh3cevtModuleSwitchType 654 } -- 48-Port 10/100/1000BASE-TX Ethernet Interface Module(RJ45)
hh3cevtModuleSw-LS7500-GT48-SD              OBJECT IDENTIFIER ::= { hh3cevtModuleSwitchType 655 } -- 48-Port 10/100/1000BASE-T Ethernet Interface Module(RJ45)
hh3cevtModuleSw-LS7500-SRPG1                OBJECT IDENTIFIER ::= { hh3cevtModuleSwitchType 656 } -- Main Control Unit
hh3cevtModuleSw-LS7500-SRPG2                OBJECT IDENTIFIER ::= { hh3cevtModuleSwitchType 657 } -- Salience VI-Lite
hh3cevtModuleSw-LS7500-XP4-SD               OBJECT IDENTIFIER ::= { hh3cevtModuleSwitchType 658 } -- 4-Port 10GBASE Ethernet Optical Interface Module(XFP,LC)
hh3cevtModuleSw-LS7500-XP8-SD               OBJECT IDENTIFIER ::= { hh3cevtModuleSwitchType 659 } -- 8-Port 10GBASE Ethernet Optical Interface Module(XFP,LC)
hh3cevtModuleSw-LSQ4PT4PSC0                 OBJECT IDENTIFIER ::= { hh3cevtModuleSwitchType 660 } -- 4-Port 1000Base-PX Optical Line Terminal(EPON OLT SFP,SC)+8-Port 1000BASE-X Optical Interface Board(SFP,LC)
hh3cevtModuleSw-LSQ4PT8PSC0                 OBJECT IDENTIFIER ::= { hh3cevtModuleSwitchType 661 } -- 8-Port 1000Base-PX Optical Line Terminal(EPON OLT SFP,SC)+8-Port 1000BASE-X Optical Interface Board(SFP,LC)
hh3cevtModuleSw-LSQ4PT16PSC0                OBJECT IDENTIFIER ::= { hh3cevtModuleSwitchType 662 } -- 16-Port 1000Base-PX Optical Line Terminal(EPON OLT SFP,SC)+8-Port 1000BASE-X Optical Interface Board(SFP,LC)
hh3cevtModuleSw-LSQ1GP24TSA0                OBJECT IDENTIFIER ::= { hh3cevtModuleSwitchType 663 } -- 16-Port 1000BASE-X Gigabit Ethernet Optical(SFP,LC) And 8-Port 10/100/1000BASE-T RJ45/1000BASE-X SFP Combo Interface Board
hh3cevtModuleSw-LSQ1GV24PSA0                OBJECT IDENTIFIER ::= { hh3cevtModuleSwitchType 664 } -- 24-Port 10/100/1000BASE-T Electrical(RJ45) Interface Board,including 4 Combo Ports,SFP Req,Upgradeable to PoE
hh3cevtModuleSw-LSQ1SRPD3                   OBJECT IDENTIFIER ::= { hh3cevtModuleSwitchType 665 } -- Salience VI-Plus
hh3cevtModuleSw-LSQ1SUPA0                   OBJECT IDENTIFIER ::= { hh3cevtModuleSwitchType 666 } -- Supervisor Engine Board
hh3cevtModuleSw-LSU1FAB04A0                 OBJECT IDENTIFIER ::= { hh3cevtModuleSwitchType 667 } -- Switch Fabric Board
hh3cevtModuleSw-LSU1FAB08A0                 OBJECT IDENTIFIER ::= { hh3cevtModuleSwitchType 668 } -- Switch Fabric Board
hh3cevtModuleSw-LSU1TGS8EA0                 OBJECT IDENTIFIER ::= { hh3cevtModuleSwitchType 669 } -- 8-Port 10GBASE Ethernet SFP+ Optical Interface Board(EA)
hh3cevtModuleSw-LSU1TGS8EB0                 OBJECT IDENTIFIER ::= { hh3cevtModuleSwitchType 670 } -- 8-Port 10GBASE Ethernet SFP+ Optical Interface Board
hh3cevtModuleSw-LSU1TGS8SE0                 OBJECT IDENTIFIER ::= { hh3cevtModuleSwitchType 671 } -- 8-Port 10GBASE Ethernet SFP+ Optical Interface Board(SE)
hh3cevtModuleSw-LSUTGS16SC0                 OBJECT IDENTIFIER ::= { hh3cevtModuleSwitchType 672 } -- 16-Port 10GBASE Ethernet SFP+ Optical Interface Board
hh3cevtModuleSw-LSU1SUPA0                   OBJECT IDENTIFIER ::= { hh3cevtModuleSwitchType 673 } -- Supervisor Engine Board
hh3cevtModuleSw-LSU1GP24TXEA0               OBJECT IDENTIFIER ::= { hh3cevtModuleSwitchType 674 } -- 16-Port 1000BASE-X Optical Interface(SFP,LC)+8-Port Combo Interface+2-Port 10GE Optical Interface Board(XFP,LC)(EA)
hh3cevtModuleSw-LSU1GP24TXEB0               OBJECT IDENTIFIER ::= { hh3cevtModuleSwitchType 675 } -- 16-Port 1000BASE-X Optical Interface(SFP,LC)+8-Port Combo Interface+2-Port 10GE Optical Interface Board(XFP,LC)(EB)
hh3cevtModuleSw-LSU1GP24TXSE0               OBJECT IDENTIFIER ::= { hh3cevtModuleSwitchType 676 } -- 16-Port 1000BASE-X Optical Interface(SFP,LC)+8-Port Combo Interface+2-Port 10GE Optical Interface Board(XFP,LC)(SE)
hh3cevtModuleSw-LSU1GP48EA0                 OBJECT IDENTIFIER ::= { hh3cevtModuleSwitchType 677 } -- 48-Port 1000BASE-X Gigabit Ethernet Optical Interface(SFP,LC) Interface Board(EA)
hh3cevtModuleSw-LSU1GP48EB0                 OBJECT IDENTIFIER ::= { hh3cevtModuleSwitchType 678 } -- 48-Port Enhanced 1000BASE-X Ethernet Optical Interface Board(SFP,LC)(EB)
hh3cevtModuleSw-LSU1GP48SE0                 OBJECT IDENTIFIER ::= { hh3cevtModuleSwitchType 679 } -- 48-Port 1000BASE Ethernet Optical Interface Board(SFP,LC)(SE)
hh3cevtModuleSw-LSU1GT48EA0                 OBJECT IDENTIFIER ::= { hh3cevtModuleSwitchType 680 } -- 48-Port 1000Base-T Gigabit Ethernet Interface Board(RJ45)(EA)
hh3cevtModuleSw-LSU1GT48SE0                 OBJECT IDENTIFIER ::= { hh3cevtModuleSwitchType 681 } -- 48-Port 1000Base-T Gigabit Ethernet Interface Board(RJ45)(SE)
hh3cevtModuleSw-LSU1TGX4EA0                 OBJECT IDENTIFIER ::= { hh3cevtModuleSwitchType 682 } -- 4-Port 10GBASE Ethernet Optical Interface Board(XFP,LC)(EA)
hh3cevtModuleSw-LSU1TGX4EB0                 OBJECT IDENTIFIER ::= { hh3cevtModuleSwitchType 683 } -- 4-Port 10GBASE Ethernet Optical Interface Board(XFP,LC)(EB)
hh3cevtModuleSw-LSU1TGX4SE0                 OBJECT IDENTIFIER ::= { hh3cevtModuleSwitchType 684 } -- 4-Port 10GBASE Ethernet Optical Interface Board(XFP,LC)(SE)
hh3cevtModuleSw-LSQ1FAB08A0                 OBJECT IDENTIFIER ::= { hh3cevtModuleSwitchType 685 } -- Switching Fabric Board
hh3cevtModuleSw-EWPX2WCMD0                  OBJECT IDENTIFIER ::= { hh3cevtModuleSwitchType 686 } -- Access Controller Card
hh3cevtModuleSw-LSQ1WCMD0                   OBJECT IDENTIFIER ::= { hh3cevtModuleSwitchType 687 } -- Access Controller Card
hh3cevtModuleSw-LSQ1IAGSC0                  OBJECT IDENTIFIER ::= { hh3cevtModuleSwitchType 688 } -- Wireless&IAG Service Card
hh3cevtModuleSw-LSU1GP24TSE0                OBJECT IDENTIFIER ::= { hh3cevtModuleSwitchType 689 } -- 16-Port 1000BASE-X Optical Interface(SFP,LC)+8-Port Combo Interface Board(SE)
hh3cevtModuleSw-LSQ1TGS16SC0                OBJECT IDENTIFIER ::= { hh3cevtModuleSwitchType 690 } -- 16-Port 10GBASE Ethernet SFP+ Optical Interface Board
hh3cevtModuleSw-EWPX2TGS16SC0               OBJECT IDENTIFIER ::= { hh3cevtModuleSwitchType 691 } -- 16-Port 10GBASE Ethernet SFP+ Optical Interface Board
hh3cevtModuleSw-LSQ1SUPA3                   OBJECT IDENTIFIER ::= { hh3cevtModuleSwitchType 692 } -- Supervisor Engine Board
hh3cevtModuleSw-LSQ1FAB04A3                 OBJECT IDENTIFIER ::= { hh3cevtModuleSwitchType 693 } -- 320G Switch Fabric Board
hh3cevtModuleSw-LSQ1FAB08A3                 OBJECT IDENTIFIER ::= { hh3cevtModuleSwitchType 694 } -- 640G Switch Fabric Board
hh3cevtModuleSw-LSQ1GT48SC0                 OBJECT IDENTIFIER ::= { hh3cevtModuleSwitchType 695 } -- 48-Port 1000Base-T Gigabit Ethernet Interface Board(RJ45)
hh3cevtModuleSw-LSR2SRP2C1                  OBJECT IDENTIFIER ::= { hh3cevtModuleSwitchType 696 } -- Management and Route Process Unit
hh3cevtModuleSw-LSR2SRP2C2                  OBJECT IDENTIFIER ::= { hh3cevtModuleSwitchType 697 } -- Management and Route Process Unit

--
-- 700 to 799 reserved for primary switches
--
hh3cevtModuleSw-1000BASE-X-COMBO            OBJECT IDENTIFIER ::= { hh3cevtModuleSwitchType 701 } -- Single port 10/100/1000BASE-T/1000BASE-X Combo Interface Board
hh3cevtModuleSw-EPON-1000M                  OBJECT IDENTIFIER ::= { hh3cevtModuleSwitchType 702 } -- Optical Network Unit Interface Board
hh3cevtModuleSw-1000BASE-FIXED-2SFP-T-2RJ45         OBJECT IDENTIFIER ::= { hh3cevtModuleSwitchType 703 } -- 2 port 10/100/1000BASE-T and 2 port 1000BASE-X Interface Board
hh3cevtModuleSw-100M-1550-BIDI              OBJECT IDENTIFIER ::= { hh3cevtModuleSwitchType 704 }  -- 100BASE-X BIDI Interface Board, Tx 1550nm, Rx 1310nm
hh3cevtModuleSw-100M-1310-BIDI              OBJECT IDENTIFIER ::= { hh3cevtModuleSwitchType 705 }  -- 100BASE-X reverse Interface Board, Tx 1310nm, Rx 1550nm
hh3cevtModuleSw-1000BASE-FIXED-4RJ45-4SFP-COMBO     OBJECT IDENTIFIER ::= { hh3cevtModuleSwitchType 706 } -- 4 port 10/100/1000BASE-T and 4 port 1000BASE-X COMBO Interface Board
hh3cevtModuleSw-LSH1PK2T                    OBJECT IDENTIFIER ::= { hh3cevtModuleSwitchType 707 } -- OSM Interface Board
hh3cevtModuleSw-LSPM2GP2P                   OBJECT IDENTIFIER ::= { hh3cevtModuleSwitchType 708 } -- 2-Port 1000BASE-X SFP Module
hh3cevtModuleSw-LSWM1GT16P                  OBJECT IDENTIFIER ::= { hh3cevtModuleSwitchType 709 } -- 16-Port 10/100/1000BASE-T Ethernet Electrical Interface Module
hh3cevtModuleSw-LSWM1GP16P                  OBJECT IDENTIFIER ::= { hh3cevtModuleSwitchType 710 } -- 16-Port 100/1000BASE-X Ethernet Optical Interface Module
hh3cevtModuleSw-LSWM1XP2P                   OBJECT IDENTIFIER ::= { hh3cevtModuleSwitchType 711 } -- 2-Port 10G Ethernet XFP Optical Interface Module
hh3cevtModuleSw-LSWM1XP4P                   OBJECT IDENTIFIER ::= { hh3cevtModuleSwitchType 712 } -- 4-Port 10G Ethernet XFP Optical Interface Module
hh3cevtModuleSw-LSWM1SP2P                   OBJECT IDENTIFIER ::= { hh3cevtModuleSwitchType 713 } -- 2-Port 10G Ethernet SFP PLUS Optical Interface Module
hh3cevtModuleSw-LSWM1SP4P                   OBJECT IDENTIFIER ::= { hh3cevtModuleSwitchType 714 } -- 4-Port 10G Ethernet SFP PLUS Optical Interface Module
hh3cevtModuleSw-LSWM148POEM                 OBJECT IDENTIFIER ::= { hh3cevtModuleSwitchType 715 } -- 48 Port Mid Power PoE Module
hh3cevtModuleSw-LSWM1FW10                   OBJECT IDENTIFIER ::= { hh3cevtModuleSwitchType 716 } -- RMI CPU XLR 732, with Firewall software
hh3cevtModuleSw-LSWM1WCM10                  OBJECT IDENTIFIER ::= { hh3cevtModuleSwitchType 717 } -- RMI CPU XLR 732, with Wireless Access Controller software
hh3cevtModuleSw-LSWM1IPS10                  OBJECT IDENTIFIER ::= { hh3cevtModuleSwitchType 718 } -- RMI CPU XLR 732, with IPS/AV software
hh3cevtModuleSw-LSWM1WCM20                  OBJECT IDENTIFIER ::= { hh3cevtModuleSwitchType 719 } -- RMI CPU XLR 408, with Wireless Access Controller software
hh3cevtModuleSw-IPS-T1000-M                 OBJECT IDENTIFIER ::= { hh3cevtModuleSwitchType 720 } -- IPS for T1000-M mainboard module
hh3cevtModuleSw-IPS-T1000-A                 OBJECT IDENTIFIER ::= { hh3cevtModuleSwitchType 721 } -- IPS for T1000-A mainboard module
hh3cevtModuleSw-IPS-T1000-S                 OBJECT IDENTIFIER ::= { hh3cevtModuleSwitchType 722 } -- IPS for T1000-S mainboard module
hh3cevtModuleSw-IPS-GX4C                    OBJECT IDENTIFIER ::= { hh3cevtModuleSwitchType 723 } -- four-port-gigabit-fiber-boardmodule
hh3cevtModuleSw-IPS-GT4C                    OBJECT IDENTIFIER ::= { hh3cevtModuleSwitchType 724 } -- four-port-1000BASET-boardmodule
hh3cevtModuleSw-LSPM2SP2P                   OBJECT IDENTIFIER ::= { hh3cevtModuleSwitchType 725 } -- 2-Port 10G Ethernet SFP PLUS Optical Interface Module
hh3cevtModuleSw-LSPM2SP2PA                  OBJECT IDENTIFIER ::= { hh3cevtModuleSwitchType 726 } -- 2-Port Second Version SFP+ Module
hh3cevtModuleSw-LSP5GP8P                    OBJECT IDENTIFIER ::= { hh3cevtModuleSwitchType 727 } -- 8-Port 1G Ethernet SFP Optical Interface Module
hh3cevtModuleSw-LSP5GT8P                    OBJECT IDENTIFIER ::= { hh3cevtModuleSwitchType 728 } -- 8-Port 10/100/1000BASE-T Ethernet Electrical Interface Module
hh3cevtModuleSw-LSWM1FC4P                   OBJECT IDENTIFIER ::= { hh3cevtModuleSwitchType 729 } -- 4-Port 8G Fibre Channel Interface Module
hh3cevtModuleSw-LSW1XGT4P0                  OBJECT IDENTIFIER ::= { hh3cevtModuleSwitchType 730 } -- 4-Port 10G Ethernet Copper Interface Module
hh3cevtModuleSw-LSW1XGT2P0                  OBJECT IDENTIFIER ::= { hh3cevtModuleSwitchType 731 } -- 2-Port 10G Ethernet Copper Interface Module
hh3cevtModuleSw-LSP1XGT2P                   OBJECT IDENTIFIER ::= { hh3cevtModuleSwitchType 732 } -- 2-Port 10G Ethernet Copper Interface Board
hh3cevtModuleSw-LSPM3XGT2P                  OBJECT IDENTIFIER ::= { hh3cevtModuleSwitchType 733 } -- 2-Port 1/10G BASE-T Ethernet Copper Interface Module
hh3cevtModuleSw-LSWM2QP2P                   OBJECT IDENTIFIER ::= { hh3cevtModuleSwitchType 734 } -- 2-Port QSFP+ Interface Module
hh3cevtModuleSw-LSWM2XGT2PM                 OBJECT IDENTIFIER ::= { hh3cevtModuleSwitchType 735 } -- 2-Port 10G Ethernet Copper Interface Module with MACsec
hh3cevtModuleSw-LSWM2SP2PM                  OBJECT IDENTIFIER ::= { hh3cevtModuleSwitchType 736 } -- 2-Port SFP+ Interface Module with MACsec
hh3cevtModuleSw-LSWM2SP8PM                  OBJECT IDENTIFIER ::= { hh3cevtModuleSwitchType 737 } -- 8-Port SFP+ Interface Module with MACsec
hh3cevtModuleSw-LSWM2SP8P                   OBJECT IDENTIFIER ::= { hh3cevtModuleSwitchType 738 } -- 8-Port SFP+ Interface Module
hh3cevtModuleSw-LSWM2XGT8PM                 OBJECT IDENTIFIER ::= { hh3cevtModuleSwitchType 739 } -- 8-Port 10G Ethernet Copper Interface Module with MACsec
hh3cevtModuleSw-LSWM18QC                    OBJECT IDENTIFIER ::= { hh3cevtModuleSwitchType 740 } -- 8-Port QSFP+ Module
hh3cevtModuleSw-LSWM124XG2Q                 OBJECT IDENTIFIER ::= { hh3cevtModuleSwitchType 741 } -- 24-Port SFP+ and 2-Port QSFP+ Module
hh3cevtModuleSw-LSWM124XGT2Q                OBJECT IDENTIFIER ::= { hh3cevtModuleSwitchType 742 } -- 24-Port 10G BASE-T and 2-Port QSFP+ Module
hh3cevtModuleSw-LSWM124XG2QL                OBJECT IDENTIFIER ::= { hh3cevtModuleSwitchType 743 } -- 24-Port SFP+ and 2-Port QSFP+ Module
hh3cevtModuleSw-LSWM124XG2QFC               OBJECT IDENTIFIER ::= { hh3cevtModuleSwitchType 744 } -- 24-Port 8G Fibre Channel Interface and 2-Port QSFP+ Module
hh3cevtModuleSw-LSWM18QC0                   OBJECT IDENTIFIER ::= { hh3cevtModuleSwitchType 745 } -- 8-Port QSFP+ Module
hh3cevtModuleSw-LSWM124XGT2Q0               OBJECT IDENTIFIER ::= { hh3cevtModuleSwitchType 746 } -- 24-Port 10G BASE-T and 2-Port QSFP+ Module
hh3cevtModuleSw-LSWM124XG2QL0               OBJECT IDENTIFIER ::= { hh3cevtModuleSwitchType 747 } -- 24-Port SFP+ and 2-Port QSFP+ Module
hh3cevtModuleSw-LSP6G4T6P                   OBJECT IDENTIFIER ::= { hh3cevtModuleSwitchType 748 } -- 6-Port SFP and 2-port 10/100/1000BASE-T COMBO and 2 port 10/100/1000BASE-T Interface Module
hh3cevtModuleSw-LSPM6QP2PS                  OBJECT IDENTIFIER ::= { hh3cevtModuleSwitchType 749 } -- 2-Port QSFP+ Stack Interface Module
hh3cevtModuleSw-LSWM12H2Q                   OBJECT IDENTIFIER ::= { hh3cevtModuleSwitchType 750 } -- 2-Port QSFP28 and 2-Port QSFP+ Module
hh3cevtModuleSw-LSWM18CQ                    OBJECT IDENTIFIER ::= { hh3cevtModuleSwitchType 751 } -- 8-Port QSFP28 Module
hh3cevtModuleSw-LSWM116Q                    OBJECT IDENTIFIER ::= { hh3cevtModuleSwitchType 752 } -- 16-Port QSFP+ Module
hh3cevtModuleSw-LSPM6FWD                    OBJECT IDENTIFIER ::= { hh3cevtModuleSwitchType 753 } -- Next Generation Firewall Module
hh3cevtModuleSw-DS-3E-2XT-H                 OBJECT IDENTIFIER ::= { hh3cevtModuleSwitchType 754 } -- 2-Port 10G Ethernet Copper Interface Module with MACsec
hh3cevtModuleSw-DS-3E-2XF-H                 OBJECT IDENTIFIER ::= { hh3cevtModuleSwitchType 755 } -- 2-Port SFP+ Interface Module with MACsec
hh3cevtModuleSw-DS-3E-2QX-H                 OBJECT IDENTIFIER ::= { hh3cevtModuleSwitchType 756 } -- 2-Port QSFP+ Stack Interface Module
hh3cevtModuleSw-LSPM4G4T6P                  OBJECT IDENTIFIER ::= { hh3cevtModuleSwitchType 757 } -- 6-Port SFP and 2-port 10/100/1000BASE-T COMBO and 2 port 10/100/1000BASE-T Interface Module
hh3cevtModuleSw-LSWM4SP8PM                  OBJECT IDENTIFIER ::= { hh3cevtModuleSwitchType 758 } -- 8-Port SFP+ Interface Module with MACsec
hh3cevtModuleSw-LSWM124TG2H                 OBJECT IDENTIFIER ::= { hh3cevtModuleSwitchType 759 } -- 24-Port SFP28 and 2-Port QSFP28 Module
hh3cevtModuleSw-LSWM18CQ0                   OBJECT IDENTIFIER ::= { hh3cevtModuleSwitchType 760 } -- 8-Port QSFP28 Module
hh3cevtModuleSw-LSWM116Q0                   OBJECT IDENTIFIER ::= { hh3cevtModuleSwitchType 761 } -- 16-Port QSFP+ Module
hh3cevtModuleSw-LSWM124TG2H0                OBJECT IDENTIFIER ::= { hh3cevtModuleSwitchType 762 } -- 24-Port SFP28 and 2-Port QSFP28 Module
hh3cevtModuleSw-LSWM2ZQP2P                  OBJECT IDENTIFIER ::= { hh3cevtModuleSwitchType 763 } -- 2-Port QSFP28 Module
hh3cevtModuleSw-LSWM2ZSP8P                  OBJECT IDENTIFIER ::= { hh3cevtModuleSwitchType 764 } -- 8-Port SFP28 Module
hh3cevtModuleSw-LSWM18CQMSEC                OBJECT IDENTIFIER ::= { hh3cevtModuleSwitchType 765 } -- 8-Port QSFP28 MACSEC Module
hh3cevtModuleSw-LSWM2MGT8P                  OBJECT IDENTIFIER ::= { hh3cevtModuleSwitchType 766 } -- 8-Port SmartGE (5/2.5/1G) Interface Module
hh3cevtModuleSw-LSWM2XMGT8P                 OBJECT IDENTIFIER ::= { hh3cevtModuleSwitchType 767 } -- 8-Port SmartGE (10/5/2.5/1G) Interface Module
hh3cevtModuleSw-LSWM2ZSP2P                  OBJECT IDENTIFIER ::= { hh3cevtModuleSwitchType 768 } -- 2-Port SFP28 Interface Module
hh3cevtModuleSw-LSWM116FC                   OBJECT IDENTIFIER ::= { hh3cevtModuleSwitchType 769 } -- 16-Ports SFP28 Ethernet Optical Interface Module with 16G/32G FC
hh3cevtModuleSw-LSWM216FC                   OBJECT IDENTIFIER ::= { hh3cevtModuleSwitchType 770 } -- 16-Ports SFP28 Ethernet Optical Interface Module with 16G/32G FC
hh3cevtModuleSw-LSWM2SP2PB                  OBJECT IDENTIFIER ::= { hh3cevtModuleSwitchType 771 } -- 2-Port SFP+ Interface Module
hh3cevtModuleSw-LSWM2SP4PB                  OBJECT IDENTIFIER ::= { hh3cevtModuleSwitchType 772 } -- 4-Port SFP+ Interface Module
hh3cevtModuleSw-LSWM2SP24P                  OBJECT IDENTIFIER ::= { hh3cevtModuleSwitchType 773 } -- 24-Port SFP+ Interface Module
hh3cevtModuleSw-LSWM2SP12P2Q                OBJECT IDENTIFIER ::= { hh3cevtModuleSwitchType 774 } -- 12-Port SFP+ and 2-Port QSFP+ Interface Module
hh3cevtModuleSw-LSWM2SP12P2QA               OBJECT IDENTIFIER ::= { hh3cevtModuleSwitchType 775 } -- 12-Port SFP+ and 2-Port QSFP+ Interface Module with wider size
hh3cevtModuleSw-DS-3E-2QX-HB                OBJECT IDENTIFIER ::= { hh3cevtModuleSwitchType 776 } -- 2-Port QSFP+ Interface Module
hh3cevtModuleSw-DS-3E-8XF-H                 OBJECT IDENTIFIER ::= { hh3cevtModuleSwitchType 777 } -- 8-Port SFP+ Interface Module
hh3cevtModuleSw-LSWM116HC                   OBJECT IDENTIFIER ::= { hh3cevtModuleSwitchType 781 } -- 16-Port QSFP28 Ethernet Optical Interface Module
--
-- 800 to 899 reserved for WLAN products
--
hh3cevtModuleSw-WX5002MPU                   OBJECT IDENTIFIER ::= { hh3cevtModuleSwitchType 800 } -- Wireless Lan Control Board with 2-port 1000BASE-T/1000BASE-X Combo Interface
hh3cevtModuleSw-LS8M1WCMA                   OBJECT IDENTIFIER ::= { hh3cevtModuleSwitchType 801 } -- Wireless Lan Service Board
hh3cevtModuleSw-EWPX1G24XA0                 OBJECT IDENTIFIER ::= { hh3cevtModuleSwitchType 802 } -- 24-Port 1000BASE-T Gigabit Ethernet Interface(RJ45) and 4-port 1000BASE-T/1000BASE-X Combo Interface and 2-port 10GBASE Interface Line Card
hh3cevtModuleSw-LSQ1WCMB0                   OBJECT IDENTIFIER ::= { hh3cevtModuleSwitchType 803 } -- 1 Port 10GBASE Interface Board
hh3cevtModuleSw-LSB1WCM2A0                  OBJECT IDENTIFIER ::= { hh3cevtModuleSwitchType 804 } -- Wireless Controller Module Board
hh3cevtModuleSw-EWPX1WCMB0                  OBJECT IDENTIFIER ::= { hh3cevtModuleSwitchType 805 } -- 1 Port 10GBASE Interface Board
hh3cevtModuleSw-EWPX1G24XC0                 OBJECT IDENTIFIER ::= { hh3cevtModuleSwitchType 806 } -- 24-Port 1000BASE-T Gigabit Ethernet Interface(RJ45) and 4-port 1000BASE-T/1000BASE-X Combo Interface Line Card
hh3cevtModuleSw-EWPX1WCMC0                  OBJECT IDENTIFIER ::= { hh3cevtModuleSwitchType 807 } -- 1-Port 1000BASE-T Gigabit Ethernet of wireless Lan Service Board
hh3cevtModuleSw-EWPX1FWA0                   OBJECT IDENTIFIER ::= { hh3cevtModuleSwitchType 808 } -- Firewall Service Board
hh3cevtModuleSw-EWPX1G10XC0                 OBJECT IDENTIFIER ::= { hh3cevtModuleSwitchType 809 } -- 8-Port 1000BASE-T Gigabit Ethernet Interface(RJ45) and 2-port 1000BASE-X SFP Interface Line Card
hh3cevtModuleSw-EWPX1WCM10C0                OBJECT IDENTIFIER ::= { hh3cevtModuleSwitchType 810 } -- 1-Port 1000BASE-T Gigabit Ethernet of wireless Lan Service Board
hh3cevtModuleSw-LSR1WCM2A1                  OBJECT IDENTIFIER ::= { hh3cevtModuleSwitchType 811 } -- 1-Port 1000BASE-T Gigabit Ethernet of wireless Lan Service Board
hh3cevtModuleSw-EWPX1WAP0                   OBJECT IDENTIFIER ::= { hh3cevtModuleSwitchType 812 } -- Encryption Card
hh3cevtModuleSw-EWPX1WCMD0                  OBJECT IDENTIFIER ::= { hh3cevtModuleSwitchType 813 } -- 2 Port 10GBASE Interface Board
hh3cevtModuleSw-EWPX1G24XCE0                OBJECT IDENTIFIER ::= { hh3cevtModuleSwitchType 814 } -- 24-Port 1000BASE-T Gigabit Ethernet Interface(RJ45) and 4-port 1000BASE-T/1000BASE-X Combo Interface Line Card
hh3cevtModuleSw-EWPX1WCMCE0                 OBJECT IDENTIFIER ::= { hh3cevtModuleSwitchType 815 } -- 2-Port 1000BASE-T Gigabit Ethernet of wireless Lan Service Board
hh3cevtModuleSw-EWPX1G24XD0                 OBJECT IDENTIFIER ::= { hh3cevtModuleSwitchType 816 } -- 4-Port 10GBASE-T and 24-Port 1000BASE-T Gigabit Ethernet of wireless Lan Service Board
hh3cevtModuleSw-EWPXM1XG03                  OBJECT IDENTIFIER ::= { hh3cevtModuleSwitchType 817 } -- 8GE and 2SFP Plus Interface Board  of wireless Lan Service Board
hh3cevtModuleSw-EWPXM2X                     OBJECT IDENTIFIER ::= { hh3cevtModuleSwitchType 818 } -- 2SFP Plus Interface Board  of wireless Lan Service Board
hh3cevtModuleSw-EWPXM8G                     OBJECT IDENTIFIER ::= { hh3cevtModuleSwitchType 819 } -- 8GE Interface Board  of wireless Lan Service Board
hh3cevtModuleSw-IOT-CARD-C1K                OBJECT IDENTIFIER ::= { hh3cevtModuleSwitchType 820 } -- IoT Service Board for Wireless Controller
hh3cevtModuleSw-EWPXM1BSTX80                OBJECT IDENTIFIER ::= { hh3cevtModuleSwitchType 821 } -- 8GE and 8*SFP Plusor 2*40Ge Interface Board  of wireless Lan Service Board
--
-- 900 to 1199 reserved for advanced switches part II
--
hh3cevtModuleSw-LSR1DRSP2L1                 OBJECT IDENTIFIER ::= { hh3cevtModuleSwitchType 900 } -- 2-Port OC-48c/STM-16c RPR Optical Interface Card,(SFP,LC)
hh3cevtModuleSw-PIC-CLF2G8L                 OBJECT IDENTIFIER ::= { hh3cevtModuleSwitchType 901 } -- 2-Port 155M CPOS Optical Interface(SFP,LC)+8-Port 1000BASE-X Optical Interface Card(SFP,LC)
hh3cevtModuleSw-PIC-CLF4G8L                 OBJECT IDENTIFIER ::= { hh3cevtModuleSwitchType 902 } -- 4-Port 155M CPOS Optical Interface(SFP,LC)+8-Port 1000BASE-X Optical Interface Card(SFP,LC)
hh3cevtModuleSw-SR02SRP2F3                  OBJECT IDENTIFIER ::= { hh3cevtModuleSwitchType 903 } -- Routing Switch Processing Board(2F)
hh3cevtModuleSw-SR02SRP1F3                  OBJECT IDENTIFIER ::= { hh3cevtModuleSwitchType 904 } -- Routing Switch Processing Board(1F)
hh3cevtModuleSw-LST1GT48LEA1                OBJECT IDENTIFIER ::= { hh3cevtModuleSwitchType 905 } -- 48-Port 10/100/1000BASE-T Interface Module(LEA),(RJ45)
hh3cevtModuleSw-LST1GP48LEA1                OBJECT IDENTIFIER ::= { hh3cevtModuleSwitchType 906 } -- 48-Port 1000BASE-X Interface Module(LEA),(SFP,LC)
hh3cevtModuleSw-LST2XP8LEA1                 OBJECT IDENTIFIER ::= { hh3cevtModuleSwitchType 907 } -- 8-Port 10GBASE-R Interface Module(LEA),(SFP+,LC)
hh3cevtModuleSw-LST1GT48LEY1                OBJECT IDENTIFIER ::= { hh3cevtModuleSwitchType 908 } -- 48-Port 10/100/1000BASE-T Interface Module(LEY),(RJ45)
hh3cevtModuleSw-LST1GP48LEY1                OBJECT IDENTIFIER ::= { hh3cevtModuleSwitchType 909 } -- 48-Port 1000BASE-X Interface Module(LEY),(SFP,LC)
hh3cevtModuleSw-LST1XP32REY1                OBJECT IDENTIFIER ::= { hh3cevtModuleSwitchType 910 } -- 32-Port 10GBASE-R Interface Module(REY),(SFP+,LC)
hh3cevtModuleSw-LST1XP8LEY1                 OBJECT IDENTIFIER ::= { hh3cevtModuleSwitchType 911 } -- 8-Port 10GBASE-R/W Interface Module(LEY),(XFP,LC)
hh3cevtModuleSw-LST1GP48LEZ1                OBJECT IDENTIFIER ::= { hh3cevtModuleSwitchType 912 } -- 48-Port 1000BASE-X Interface Module(LEZ),(SFP,LC)
hh3cevtModuleSw-LST1XP8LEZ1                 OBJECT IDENTIFIER ::= { hh3cevtModuleSwitchType 913 } -- 8-Port 10GBASE-R/W Interface Module(LEZ),(XFP,LC)
hh3cevtModuleSw-IM-FW-II                    OBJECT IDENTIFIER ::= { hh3cevtModuleSwitchType 914 } -- Firewall Service Processing Board-II
hh3cevtModuleSw-IM-IPS                      OBJECT IDENTIFIER ::= { hh3cevtModuleSwitchType 915 } -- Intrusion Prevention System Service Processing Board
hh3cevtModuleSw-IM-SSL                      OBJECT IDENTIFIER ::= { hh3cevtModuleSwitchType 916 } -- SSL VPN Service Processing Board
hh3cevtModuleSw-IM-LB                       OBJECT IDENTIFIER ::= { hh3cevtModuleSwitchType 917 } -- Load Balance Service Processing Board
hh3cevtModuleSw-IM-ACG                      OBJECT IDENTIFIER ::= { hh3cevtModuleSwitchType 918 } -- Application Control Gateway Service Processing Board
hh3cevtModuleSw-LSR1XP16REC1                OBJECT IDENTIFIER ::= { hh3cevtModuleSwitchType 919 } -- 16-Port 10GBASE-R Interface Module(REC),(SFP+,LC)
hh3cevtModuleSw-LST2XP8LEB1                 OBJECT IDENTIFIER ::= { hh3cevtModuleSwitchType 920 } -- 8-Port 10GBASE-R/W Interface Module(LEB),(XFP,LC)
hh3cevtModuleSw-LST2XP8LEC1                 OBJECT IDENTIFIER ::= { hh3cevtModuleSwitchType 921 } -- 8-Port 10GBASE-R/W Interface Module(LEC),(XFP,LC)
hh3cevtModuleSw-LST2XP8LEF1                 OBJECT IDENTIFIER ::= { hh3cevtModuleSwitchType 922 } -- 8-Port 10GBASE-R/W Interface Module(LEF),(XFP,LC)
hh3cevtModuleSw-LSR2XP4LEB1                 OBJECT IDENTIFIER ::= { hh3cevtModuleSwitchType 923 } -- 4-Port 10GBase-R/W Interface Module(LEB),(XFP,LC)
hh3cevtModuleSw-LSR2XP4LEC1                 OBJECT IDENTIFIER ::= { hh3cevtModuleSwitchType 924 } -- 4-Port 10GBase-R/W Interface Module(LEC),(XFP,LC)
hh3cevtModuleSw-LST2XP32REB1                OBJECT IDENTIFIER ::= { hh3cevtModuleSwitchType 925 } -- 32-Port 10GBASE-R Interface Module(REB),(SFP+,LC)
hh3cevtModuleSw-LST2XP32REC1                OBJECT IDENTIFIER ::= { hh3cevtModuleSwitchType 926 } -- 32-Port 10GBASE-R Interface Module(REC),(SFP+,LC)
hh3cevtModuleSw-LSR1WCM3A1                  OBJECT IDENTIFIER ::= { hh3cevtModuleSwitchType 927 } -- Access Controller Module
hh3cevtModuleSw-LST1XP16LEB1                OBJECT IDENTIFIER ::= { hh3cevtModuleSwitchType 928 } -- 16-Port 10GBASE-R Interface Module (LEB),(SFP+,LC)
hh3cevtModuleSw-LST1XP16LEC1                OBJECT IDENTIFIER ::= { hh3cevtModuleSwitchType 929 } -- 16-Port 10GBASE-R Interface Module (LEC),(SFP+,LC)
hh3cevtModuleSw-CR-SPC-XP4L-E-I             OBJECT IDENTIFIER ::= { hh3cevtModuleSwitchType 930 } -- 4-Port 10GBASE-R/W Optical Interface Module,(XFP,LC)
hh3cevtModuleSw-LST2MRPNC1                  OBJECT IDENTIFIER ::= { hh3cevtModuleSwitchType 931 } -- Management and Route Process Unit
hh3cevtModuleSw-LST2SF08C1                  OBJECT IDENTIFIER ::= { hh3cevtModuleSwitchType 932 } -- Switch Fabric Card
hh3cevtModuleSw-LST2SF18C1                  OBJECT IDENTIFIER ::= { hh3cevtModuleSwitchType 933 } -- Switch Fabric Card
hh3cevtModuleSw-SR02SRP2G3                  OBJECT IDENTIFIER ::= { hh3cevtModuleSwitchType 934 } -- Routing Switch Processing Board(2G)
hh3cevtModuleSw-CR-SPE-3020-E-I             OBJECT IDENTIFIER ::= { hh3cevtModuleSwitchType 935 } -- CR15LN3CNA1, Dual Service Processing Board
hh3cevtModuleSw-CR-SPC-PUP4L-E-I            OBJECT IDENTIFIER ::= { hh3cevtModuleSwitchType 936 } -- 4-Port 10G POS Optical Interface Board(Enhanced),(XFP,LC)
hh3cevtModuleSw-CR-SPC-XP4LEF-I             OBJECT IDENTIFIER ::= { hh3cevtModuleSwitchType 937 } -- 4-Port 10GBASE-R/W Interface Module (LEF),(XFP,LC)
hh3cevtModuleSw-CR-SPC-XP8LEF-I             OBJECT IDENTIFIER ::= { hh3cevtModuleSwitchType 938 } -- 8-Port 10GBASE-R/W Interface Module (LEF),(XFP,LC)
hh3cevtModuleSw-LST3XP8LEB1                 OBJECT IDENTIFIER ::= { hh3cevtModuleSwitchType 939 } -- 8-Port 10GBASE-R Interface Module (LEB),(XFP,LC)
hh3cevtModuleSw-LST3XP8LEC1                 OBJECT IDENTIFIER ::= { hh3cevtModuleSwitchType 940 } -- 8-Port 10GBASE-R Interface Module (LEC),(XFP,LC)
hh3cevtModuleSw-LST1FW3A1                   OBJECT IDENTIFIER ::= { hh3cevtModuleSwitchType 941 } -- Firewall Board
hh3cevtModuleSw-CR-IM-NAM1A                 OBJECT IDENTIFIER ::= { hh3cevtModuleSwitchType 942 } -- CR1M1NAM1A1, Network Analysis Service Module, Domestic&Overseas Version
hh3cevtModuleSw-LSR2SRP2B1                  OBJECT IDENTIFIER ::= { hh3cevtModuleSwitchType 943 } -- Management and Route Process Unit
hh3cevtModuleSw-LSR2SRP2B2                  OBJECT IDENTIFIER ::= { hh3cevtModuleSwitchType 944 } -- Management and Route Process Unit
hh3cevtModuleSw-LSR2SRP2D1                  OBJECT IDENTIFIER ::= { hh3cevtModuleSwitchType 945 } -- Management and Route Process Unit
hh3cevtModuleSw-LST3XP8LEY1                 OBJECT IDENTIFIER ::= { hh3cevtModuleSwitchType 946 } -- 8-Port 10GBASE-R/W Interface Module (LEY),(XFP,LC)
hh3cevtModuleSw-LST2XP32REY1                OBJECT IDENTIFIER ::= { hh3cevtModuleSwitchType 947 } -- 32-Port 10GBASE-R Interface Module(REY),(SFP+,LC)
hh3cevtModuleSw-LST1XP16LEY1                OBJECT IDENTIFIER ::= { hh3cevtModuleSwitchType 948 } -- 16-Port 10GBASE-R Interface Module (LEY),(SFP+,LC)
hh3cevtModuleSw-SR0M2SRP2G3                 OBJECT IDENTIFIER ::= { hh3cevtModuleSwitchType 949 } -- Routing Switch Processing Board(2G)
hh3cevtModuleSw-SR0M2SRP1G3                 OBJECT IDENTIFIER ::= { hh3cevtModuleSwitchType 950 } -- Routing Switch Processing Board(1G)
hh3cevtModuleSw-SPC-GP48LA                  OBJECT IDENTIFIER ::= { hh3cevtModuleSwitchType 951 } -- 48-Port 1000BASE-X Interface Service Module,(SFP,LC)
hh3cevtModuleSw-SPC-GT48LA                  OBJECT IDENTIFIER ::= { hh3cevtModuleSwitchType 952 } -- 48-Port 10/100/1000BASE-T Interface Service Module,(RJ45)
hh3cevtModuleSw-SPC-XP4LA                   OBJECT IDENTIFIER ::= { hh3cevtModuleSwitchType 953 } -- 4-Port 10GBase-R/W Interface Service Module,(XFP,LC)
hh3cevtModuleSw-SPC-XP2LA                   OBJECT IDENTIFIER ::= { hh3cevtModuleSwitchType 954 } -- 2-Port 10GBASE-R/W Interface Service Module,(XFP,LC)
hh3cevtModuleSw-SPC-GP24LA                  OBJECT IDENTIFIER ::= { hh3cevtModuleSwitchType 955 } -- 16-Port 1000BASE-X Interface(SFP,LC)+8-Port Combo Interface Service Module
hh3cevtModuleSw-SPC-XP16RA                  OBJECT IDENTIFIER ::= { hh3cevtModuleSwitchType 956 } -- 16-Port 10GBASE-R Optical Interface Service Module(RA),(SFP+,LC)
hh3cevtModuleSw-CR-IM-FW1A                  OBJECT IDENTIFIER ::= { hh3cevtModuleSwitchType 957 } -- Firewall Service Processing Board
hh3cevtModuleSw-SPC-XP16R                   OBJECT IDENTIFIER ::= { hh3cevtModuleSwitchType 958 } -- 16-Port 10GBASE-R Optical Interface Service Module(R),(SFP+,LC)
hh3cevtModuleSw-CR-IM-LB1A                  OBJECT IDENTIFIER ::= { hh3cevtModuleSwitchType 959 } -- Load Balancing Service Processing Board
hh3cevtModuleSw-LST1GT48LEC2                OBJECT IDENTIFIER ::= { hh3cevtModuleSwitchType 960 } -- 48-Port 10/100/1000BASE-T Interface Module(LEC),(RJ45)
hh3cevtModuleSw-LST1GP48LEC2                OBJECT IDENTIFIER ::= { hh3cevtModuleSwitchType 961 } -- 48-Port 1000BASE-X Interface Module (LEC),(SFP,LC)
hh3cevtModuleSw-LST1XP16LEC2                OBJECT IDENTIFIER ::= { hh3cevtModuleSwitchType 962 } -- 16-Port 10GBASE-R Interface Module (LEC),(SFP+,LC)
hh3cevtModuleSw-LST2XP8LEC2                 OBJECT IDENTIFIER ::= { hh3cevtModuleSwitchType 963 } -- 8-Port 10GBASE-R/W Interface Module(LEC),(XFP,LC)
hh3cevtModuleSw-LST2XP32REC2                OBJECT IDENTIFIER ::= { hh3cevtModuleSwitchType 964 } -- 32-Port 10GBASE-R Interface Module(REC),(SFP+,LC)
hh3cevtModuleSw-CR-IM-MAC1A                 OBJECT IDENTIFIER ::= { hh3cevtModuleSwitchType 965 } -- Master Access Control Service Module
hh3cevtModuleSw-LST1XP48LFD1                OBJECT IDENTIFIER ::= { hh3cevtModuleSwitchType 966 } -- 48-Port 10GBASE-R Interface Module (LFD),(SFP+,LC)
hh3cevtModuleSw-LST1XP40RFD1                OBJECT IDENTIFIER ::= { hh3cevtModuleSwitchType 967 } -- 40-Port 10GBASE-R Interface Module (RFD),(SFP+,LC)
hh3cevtModuleSw-LST1XP40RFG1                OBJECT IDENTIFIER ::= { hh3cevtModuleSwitchType 968 } -- 40-Port 10GBASE-R/W Interface Module (RFG),(SFP+,LC)
hh3cevtModuleSw-LST1XLP16RFD1               OBJECT IDENTIFIER ::= { hh3cevtModuleSwitchType 969 } -- 16-Port 40GBASE-R Interface Module (RFD),(QSFP+,LC)
hh3cevtModuleSw-LST1CP4RFD1                 OBJECT IDENTIFIER ::= { hh3cevtModuleSwitchType 970 } -- 4-Port 100GBASE-R Interface Module (RFD),(CFP,LC)
hh3cevtModuleSw-LST1CP4RFG1                 OBJECT IDENTIFIER ::= { hh3cevtModuleSwitchType 971 } -- 4-Port 100GBASE-R Interface Module (RFG),(CFP,LC)
hh3cevtModuleSw-LST1SF08E1                  OBJECT IDENTIFIER ::= { hh3cevtModuleSwitchType 972 } -- Switch Fabric Card
hh3cevtModuleSw-LST1SF18E1                  OBJECT IDENTIFIER ::= { hh3cevtModuleSwitchType 973 } -- Switch Fabric Card
hh3cevtModuleSw-LST1MRPNE1                  OBJECT IDENTIFIER ::= { hh3cevtModuleSwitchType 974 } -- Management and Route Process Unit
hh3cevtModuleSw-LSX1CGX8FC0                 OBJECT IDENTIFIER ::= { hh3cevtModuleSwitchType 975 } -- 8-Port 100GBASE-R Interface Module (FC),(CXP,MPO)
hh3cevtModuleSw-LSX1CGX8FC1                 OBJECT IDENTIFIER ::= { hh3cevtModuleSwitchType 976 } -- 8-Port 100GBASE-R Interface Module (FC),(CXP,MPO)
hh3cevtModuleSw-LSX1QGS24FC0                OBJECT IDENTIFIER ::= { hh3cevtModuleSwitchType 977 } -- 24-Port 40GBASE-R Interface Module (FC),(QSFP+)
hh3cevtModuleSw-LSX1QGS24FC1                OBJECT IDENTIFIER ::= { hh3cevtModuleSwitchType 978 } -- 24-Port 40GBASE-R Interface Module (FC),(QSFP+)
hh3cevtModuleSw-LSX1TGS24FC0                OBJECT IDENTIFIER ::= { hh3cevtModuleSwitchType 979 } -- 24-Port 10GBASE-R Interface Module (FC),(SFP+,LC)
hh3cevtModuleSw-LSX1TGS24FC1                OBJECT IDENTIFIER ::= { hh3cevtModuleSwitchType 980 } -- 24-Port 10GBASE-R Interface Module (FC),(SFP+,LC)
hh3cevtModuleSw-LSX1TGS48FC0                OBJECT IDENTIFIER ::= { hh3cevtModuleSwitchType 981 } -- 48-Port 10GBASE-R Interface Module (FC),(SFP+,LC)
hh3cevtModuleSw-LSX1TGS48FC1                OBJECT IDENTIFIER ::= { hh3cevtModuleSwitchType 982 } -- 48-Port 10GBASE-R Interface Module (FC),(SFP+,LC)
hh3cevtModuleSw-LST1XP48LFD2                OBJECT IDENTIFIER ::= { hh3cevtModuleSwitchType 983 } -- 48-Port 10GBASE-R Interface Module (LFD),(SFP+,LC)
hh3cevtModuleSw-LST1XP40RFD2                OBJECT IDENTIFIER ::= { hh3cevtModuleSwitchType 984 } -- 40-Port 10GBASE-R Interface Module (RFD),(SFP+,LC)
hh3cevtModuleSw-LST1XP40RFG2                OBJECT IDENTIFIER ::= { hh3cevtModuleSwitchType 985 } -- 40-Port 10GBASE-R/W Interface Module (RFG),(SFP+,LC)
hh3cevtModuleSw-LST1XLP16RFD2               OBJECT IDENTIFIER ::= { hh3cevtModuleSwitchType 986 } -- 16-Port 40GBASE-R Interface Module (RFD),(QSFP+)
hh3cevtModuleSw-LST1CP4RFD2                 OBJECT IDENTIFIER ::= { hh3cevtModuleSwitchType 987 } -- 4-Port 100GBASE-R Interface Module (RFD),(CFP)
hh3cevtModuleSw-LST1CP4RFG2                 OBJECT IDENTIFIER ::= { hh3cevtModuleSwitchType 988 } -- 4-Port 100GBASE-R Interface Module (RFG),(CFP)
hh3cevtModuleSw-MPE-1004                    OBJECT IDENTIFIER ::= { hh3cevtModuleSwitchType 989 } -- Multi-Service Processing Engine
hh3cevtModuleSw-MIC-GP4L                    OBJECT IDENTIFIER ::= { hh3cevtModuleSwitchType 990 } -- 4-Port 1000BASE-X COMBO Interface Card,(SFP,LC)
hh3cevtModuleSw-MIC-GP8L                    OBJECT IDENTIFIER ::= { hh3cevtModuleSwitchType 991 } -- 8-Port 1000BASE-X Optical Interface Card,(SFP,LC)
hh3cevtModuleSw-MIC-SP4L                    OBJECT IDENTIFIER ::= { hh3cevtModuleSwitchType 992 } -- 4-Port OC-3/STM-1 POS/CPOS/ATM or 1-Port OC-12/STM-4 POS/ATM Optical Interface Card,(SFP,LC)
hh3cevtModuleSw-MIC-ET16L                   OBJECT IDENTIFIER ::= { hh3cevtModuleSwitchType 993 } -- 16-Port E1/T1 Electrical Interface Card
hh3cevtModuleSw-MIC-CLP4L                   OBJECT IDENTIFIER ::= { hh3cevtModuleSwitchType 994 } -- 4-Port OC-3/STM-1 CPOS/POS Optical Interface Card,(SFP,LC)
hh3cevtModuleSw-MIC-CLP2L                   OBJECT IDENTIFIER ::= { hh3cevtModuleSwitchType 995 } -- 2-Port OC-3/STM-1 CPOS/POS Optical Interface Card,(SFP,LC)
hh3cevtModuleSw-LST1IPS2A1                  OBJECT IDENTIFIER ::= { hh3cevtModuleSwitchType 996 } -- Intrusion Prevention System Module
hh3cevtModuleSw-SFC-04B                     OBJECT IDENTIFIER ::= { hh3cevtModuleSwitchType 997 } -- Switch Fabric Card(B Type)
hh3cevtModuleSw-SFC-04D                     OBJECT IDENTIFIER ::= { hh3cevtModuleSwitchType 998 } -- Switch Fabric Card(D Type)
hh3cevtModuleSw-SFC-08B                     OBJECT IDENTIFIER ::= { hh3cevtModuleSwitchType 999 } -- Switch Fabric Card(B Type)
hh3cevtModuleSw-SFC-08D                     OBJECT IDENTIFIER ::= { hh3cevtModuleSwitchType 1000 } -- Switch Fabric Card(D Type)
hh3cevtModuleSw-SFC-12B                     OBJECT IDENTIFIER ::= { hh3cevtModuleSwitchType 1001 } -- Switch Fabric Card(B Type)
hh3cevtModuleSw-SFC-12D                     OBJECT IDENTIFIER ::= { hh3cevtModuleSwitchType 1002 } -- Switch Fabric Card(D Type)
hh3cevtModuleSw-SR05SRP1H1                  OBJECT IDENTIFIER ::= { hh3cevtModuleSwitchType 1003 } -- Routing Switch Processing Unit(1H)
hh3cevtModuleSw-SPC-GP24LA1                 OBJECT IDENTIFIER ::= { hh3cevtModuleSwitchType 1004 } -- 16-Port 1000BASE-X Ethernet Optical Interface(SFP,LC)+8-Port Combo Interface Module(A Type)
hh3cevtModuleSw-SPC-GP24XP2LA               OBJECT IDENTIFIER ::= { hh3cevtModuleSwitchType 1005 } -- 16-Port 1000BASE-X Ethernet Optical Interface(SFP,LC)+8-Port Combo Interface+2-Port 10GE Optical Interface Module(XFP,LC)(A Type)
hh3cevtModuleSw-SPC-GP48LA1                 OBJECT IDENTIFIER ::= { hh3cevtModuleSwitchType 1006 } -- 48-Port 1000BASE-X Ethernet Optical Interface Module(SFP,LC)(A Type)
hh3cevtModuleSw-SPC-GP48LB                  OBJECT IDENTIFIER ::= { hh3cevtModuleSwitchType 1007 } -- 48-Port Enhanced 1000BASE-X Ethernet Optical Interface Module(SFP,LC)(B Type)
hh3cevtModuleSw-SPC-XP2LA1                  OBJECT IDENTIFIER ::= { hh3cevtModuleSwitchType 1008 } -- 2-Port 10GBASE Ethernet Optical Interface Module(XFP,LC)(A Type)
hh3cevtModuleSw-SPC-XP4LA1                  OBJECT IDENTIFIER ::= { hh3cevtModuleSwitchType 1009 } -- 4-Port 10GBASE Ethernet Optical Interface Module(XFP,LC)(A Type)
hh3cevtModuleSw-SPC-XP4LB                   OBJECT IDENTIFIER ::= { hh3cevtModuleSwitchType 1010 } -- 4-Port Enhanced 10GBASE Ethernet Optical Interface Module(XFP,LC)(B Type)
hh3cevtModuleSw-SPC-XP8LA                   OBJECT IDENTIFIER ::= { hh3cevtModuleSwitchType 1011 } -- 8-Port 10GBASE Ethernet Optical Interface Module(SFP+,LC)(A Type)
hh3cevtModuleSw-SPC-XP8LB                   OBJECT IDENTIFIER ::= { hh3cevtModuleSwitchType 1012 } -- 8-Port Enhanced 10GBASE Ethernet Optical Interface Module(SFP+,LC)(B Type)
hh3cevtModuleSw-SPC-XP48LA                  OBJECT IDENTIFIER ::= { hh3cevtModuleSwitchType 1013 } -- 48-Port 10GBASE Ethernet Optical Interface Module(SFP+,LC)(A Type)
hh3cevtModuleSw-SPC-XLP8LA                  OBJECT IDENTIFIER ::= { hh3cevtModuleSwitchType 1014 } -- 8-Port 40GBASE Ethernet Optical Interface Module(QSFP+,MPO)(A Type)
hh3cevtModuleSw-SPC-GP24XP2LB               OBJECT IDENTIFIER ::= { hh3cevtModuleSwitchType 1015 } -- 16-Port 1000BASE-X Optical Interface(SFP,LC)+8-Port Combo Interface+2-Port 10GE Optical Interface Module(XFP,LC)(B Type)
hh3cevtModuleSw-LST1MRPNE2                  OBJECT IDENTIFIER ::= { hh3cevtModuleSwitchType 1016 } -- Management and Route Process Unit
hh3cevtModuleSw-LST2FW3A1                   OBJECT IDENTIFIER ::= { hh3cevtModuleSwitchType 1017 } -- Firewall Board
hh3cevtModuleSw-LST1ADE1A1                  OBJECT IDENTIFIER ::= { hh3cevtModuleSwitchType 1018 } -- Load Balancing Board
hh3cevtModuleSw-CR-MRP-II                   OBJECT IDENTIFIER ::= { hh3cevtModuleSwitchType 1019 } -- Management and Route Unit-II
hh3cevtModuleSw-CR-SF08E                    OBJECT IDENTIFIER ::= { hh3cevtModuleSwitchType 1020 } -- Switch Fabric Module(E)
hh3cevtModuleSw-CR-SF18E                    OBJECT IDENTIFIER ::= { hh3cevtModuleSwitchType 1021 } -- Switch Fabric Module(E)
hh3cevtModuleSw-CR-SPC-XP40RC               OBJECT IDENTIFIER ::= { hh3cevtModuleSwitchType 1022 } -- 40-Port 10GBASE-R/W Optical Interface Module(RC),(SFP+,LC)
hh3cevtModuleSw-CR-SPC-XP40RB               OBJECT IDENTIFIER ::= { hh3cevtModuleSwitchType 1023 } -- 40-Port 10GBASE-R Ethernet Optical Interface Module(RB),(SFP+,LC)
hh3cevtModuleSw-CR-SPC-CP4RC                OBJECT IDENTIFIER ::= { hh3cevtModuleSwitchType 1024 } -- 4-Port 100GBASE Ethernet Optical Interface Module(RC),(CFP)
hh3cevtModuleSw-LST1FW3C1                   OBJECT IDENTIFIER ::= { hh3cevtModuleSwitchType 1025 } -- Firewall Board
hh3cevtModuleSw-LSU1FWCEA0                  OBJECT IDENTIFIER ::= { hh3cevtModuleSwitchType 1026 } -- Firewall Board
hh3cevtModuleSw-SPC-GT48LA1                 OBJECT IDENTIFIER ::= { hh3cevtModuleSwitchType 1027 } -- 48-Port 10/100/1000BASE-T Ethernet Interface Module(RJ45)(A Type)
hh3cevtModuleSw-LST1XP20RFD1                OBJECT IDENTIFIER ::= { hh3cevtModuleSwitchType 1028 } -- 20-Port 10GBASE-R Interface Module (RFD),(SFP+,LC)
hh3cevtModuleSw-LST1XP20RFD2                OBJECT IDENTIFIER ::= { hh3cevtModuleSwitchType 1029 } -- 20-Port 10GBASE-R Interface Module (RFD),(SFP+,LC)
hh3cevtModuleSw-MPE-1104                    OBJECT IDENTIFIER ::= { hh3cevtModuleSwitchType 1030 } -- 4-Port Multiservice Processing Engine
hh3cevtModuleSw-SPEX-1204                   OBJECT IDENTIFIER ::= { hh3cevtModuleSwitchType 1031 } -- 4-Port 10G Processing Engine
hh3cevtModuleSw-SPC-GP44XP4LCX              OBJECT IDENTIFIER ::= { hh3cevtModuleSwitchType 1032 } -- 44-Port 100/1000BASE-X Ethernet Optical Interface Module(SFP,LC)+4-Port 10GBASE Ethernet Optical Interface Module(SFP+,LC)(C Type)
hh3cevtModuleSw-SPC-GP44XP4LAX              OBJECT IDENTIFIER ::= { hh3cevtModuleSwitchType 1033 } -- 44-Port 100/1000BASE-X Ethernet Optical Interface Module(SFP,LC)+4-Port 10GBASE Ethernet Optical Interface Module(SFP+,LC)(A Type)
hh3cevtModuleSw-SPC-XP24LCX                 OBJECT IDENTIFIER ::= { hh3cevtModuleSwitchType 1034 } -- 24-Port 10GBASE Ethernet Optical Interface Module(SFP+,LC)(C Type)
hh3cevtModuleSw-SPC-XP24LAX                 OBJECT IDENTIFIER ::= { hh3cevtModuleSwitchType 1035 } -- 24-Port 10GBASE Ethernet Optical Interface Module(SFP+,LC)(A Type)
hh3cevtModuleSw-SPC-XP12LCX                 OBJECT IDENTIFIER ::= { hh3cevtModuleSwitchType 1036 } -- 12-Port 10GBASE Ethernet Optical Interface Module(SFP+,LC)(C Type)
hh3cevtModuleSw-SPC-XP12LAX                 OBJECT IDENTIFIER ::= { hh3cevtModuleSwitchType 1037 } -- 12-Port 10GBASE Ethernet Optical Interface Module(SFP+,LC)(A Type)
hh3cevtModuleSw-SPC-XLP6LCX                 OBJECT IDENTIFIER ::= { hh3cevtModuleSwitchType 1038 } -- 6-Port 40GBASE Ethernet Optical Interface Module(QSFP+,MPO)(C Type)
hh3cevtModuleSw-SPC-XLP6LAX                 OBJECT IDENTIFIER ::= { hh3cevtModuleSwitchType 1039 } -- 6-Port 40GBASE Ethernet Optical Interface Module(QSFP+,MPO)(A Type)
hh3cevtModuleSw-SPC-CP1LCX                  OBJECT IDENTIFIER ::= { hh3cevtModuleSwitchType 1040 } -- 1-Port 100GBASE Ethernet Optical Interface Module(CFP,LC)(C Type)
hh3cevtModuleSw-SPC-CP1LAX                  OBJECT IDENTIFIER ::= { hh3cevtModuleSwitchType 1041 } -- 1-Port 100GBASE Ethernet Optical Interface Module(CFP,LC)(A Type)
hh3cevtModuleSw-SPC-CP2LB                   OBJECT IDENTIFIER ::= { hh3cevtModuleSwitchType 1042 } -- 2-Port 100GBASE Ethernet Optical Interface Module(CFP,LC)(B Type)
hh3cevtModuleSw-SPC-CP2LA                   OBJECT IDENTIFIER ::= { hh3cevtModuleSwitchType 1043 } -- 2-Port 100GBASE Ethernet Optical Interface Module(CFP,LC)(A Type)
hh3cevtModuleSw-SR05SRP1L1                  OBJECT IDENTIFIER ::= { hh3cevtModuleSwitchType 1044 } -- Management and Route Process Unit(1L1)
hh3cevtModuleSw-SR05SRP1L3                  OBJECT IDENTIFIER ::= { hh3cevtModuleSwitchType 1045 } -- Management and Route Process Unit(1L3)
hh3cevtModuleSw-SFC-04-4                    OBJECT IDENTIFIER ::= { hh3cevtModuleSwitchType 1046 } -- Short-circuit Card Slot 4
hh3cevtModuleSw-SFC-04-3                    OBJECT IDENTIFIER ::= { hh3cevtModuleSwitchType 1047 } -- Short-circuit Card Slot 3
hh3cevtModuleSw-SFC-04-2                    OBJECT IDENTIFIER ::= { hh3cevtModuleSwitchType 1048 } -- Short-circuit Card Slot 2
hh3cevtModuleSw-SFC-04-1                    OBJECT IDENTIFIER ::= { hh3cevtModuleSwitchType 1049 } -- Short-circuit Card Slot 1
hh3cevtModuleSw-LST1NSM2C1                  OBJECT IDENTIFIER ::= { hh3cevtModuleSwitchType 1050 } -- NetStream Service Board
hh3cevtModuleSw-CR-SPC-XP20RB               OBJECT IDENTIFIER ::= { hh3cevtModuleSwitchType 1051 } -- 20-Port 10GBASE-R Ethernet Optical Interface Module(RB),(SFP+,LC)
hh3cevtModuleSw-SR07SRPUA1                  OBJECT IDENTIFIER ::= { hh3cevtModuleSwitchType 1052 } -- Management and Route Process Unit(UA1)
hh3cevtModuleSw-SR07SRPUB3                  OBJECT IDENTIFIER ::= { hh3cevtModuleSwitchType 1053 } -- Management and Route Process Unit(UB1)
hh3cevtModuleSw-SR07SRPUC3                  OBJECT IDENTIFIER ::= { hh3cevtModuleSwitchType 1054 } -- Management and Route Process Unit
hh3cevtModuleSw-SR07MPUA1                   OBJECT IDENTIFIER ::= { hh3cevtModuleSwitchType 1055 } -- Management and Route Process Unit
hh3cevtModuleSw-SR07SRPUB1                  OBJECT IDENTIFIER ::= { hh3cevtModuleSwitchType 1056 } -- Management and Route Process Unit(UB1)
hh3cevtModuleSw-SR07SRPUC1                  OBJECT IDENTIFIER ::= { hh3cevtModuleSwitchType 1057 } -- Management and Route Process Unit
hh3cevtModuleSw-MIC-MS4L                    OBJECT IDENTIFIER ::= { hh3cevtModuleSwitchType 1058 } -- 4-Port Multi-Service Optical Interface Card,Domestic&Overseas Version
hh3cevtModuleSw-SPC-GP44XP4LC               OBJECT IDENTIFIER ::= { hh3cevtModuleSwitchType 1059 } -- 44-Port 100/1000BASE-X Ethernet Optical Interface Board(SFP,LC)+4-Port 10GBASE Ethernet Optical Interface Board(SFP+,LC)(C Type)
hh3cevtModuleSw-SPC-GP44XP4LA               OBJECT IDENTIFIER ::= { hh3cevtModuleSwitchType 1060 } -- 44-Port 100/1000BASE-X Ethernet Optical Interface Board(SFP,LC)+4-Port 10GBASE Ethernet Optical Interface Board(SFP+,LC)(A Type)
hh3cevtModuleSw-SPC-XLP2XP4LC               OBJECT IDENTIFIER ::= { hh3cevtModuleSwitchType 1061 } -- 2-Port 40GBASE Ethernet Optical Interface Board(QSFP+,MPO)+4-Port 10GBASE Ethernet Optical Interface Board(SFP+,LC)(C Type)
hh3cevtModuleSw-SPC-XP12LC                  OBJECT IDENTIFIER ::= { hh3cevtModuleSwitchType 1062 } -- 12-Port 10GBASE Ethernet Optical Interface Board(SFP+,LC)(C Type)
hh3cevtModuleSw-SPC-CP1LC                   OBJECT IDENTIFIER ::= { hh3cevtModuleSwitchType 1063 } -- 1-Port 100GBASE Ethernet Optical Interface Module(CFP,LC)(C Type)
hh3cevtModuleSw-SPC-XP24LC                  OBJECT IDENTIFIER ::= { hh3cevtModuleSwitchType 1064 } -- 24-Port 10GBASE Ethernet Optical Interface Board(SFP+,LC)(C Type)
hh3cevtModuleSw-SR07SRPUD3                  OBJECT IDENTIFIER ::= { hh3cevtModuleSwitchType 1065 } -- Management and Route Process Unit(UD1)
hh3cevtModuleSw-SR07MPUA3                   OBJECT IDENTIFIER ::= { hh3cevtModuleSwitchType 1066 } -- Management and Route Process Unit(For 02 Chassis)
hh3cevtModuleSw-MPEX-1304                   OBJECT IDENTIFIER ::= { hh3cevtModuleSwitchType 1067 } -- 4-Port Multiservice Processing Engine
hh3cevtModuleSw-MIC-GP10L1                  OBJECT IDENTIFIER ::= { hh3cevtModuleSwitchType 1068 } -- 6-Port 1000BASE-X Optical Interface Card(SFP,LC)+4-Port 1000BASE-X/10GBASE Optical Interface Card(SFP+,LC)
hh3cevtModuleSw-SR07SRPUB                   OBJECT IDENTIFIER ::= { hh3cevtModuleSwitchType 1069 } -- Management and Route Processing Unit(UB3)
hh3cevtModuleSw-CMPE-1104                   OBJECT IDENTIFIER ::= { hh3cevtModuleSwitchType 1070 } -- 4-Port Multiservice Processing Engine
hh3cevtModuleSw-CSFC-04-1                   OBJECT IDENTIFIER ::= { hh3cevtModuleSwitchType 1071 } -- Fabric Card Slot 1
hh3cevtModuleSw-CSFC-04-2                   OBJECT IDENTIFIER ::= { hh3cevtModuleSwitchType 1072 } -- Fabric Card Slot 2
hh3cevtModuleSw-CSFC-04-3                   OBJECT IDENTIFIER ::= { hh3cevtModuleSwitchType 1073 } -- Fabric Card Slot 3
hh3cevtModuleSw-CSFC-04-4                   OBJECT IDENTIFIER ::= { hh3cevtModuleSwitchType 1074 } -- Fabric Card Slot 4
hh3cevtModuleSw-CSFC-04B                    OBJECT IDENTIFIER ::= { hh3cevtModuleSwitchType 1075 } -- Switch Fabric Card(B Type)
hh3cevtModuleSw-CSFC-04D                    OBJECT IDENTIFIER ::= { hh3cevtModuleSwitchType 1076 } -- Switch Fabric Card(D Type)
hh3cevtModuleSw-CSFC-08B                    OBJECT IDENTIFIER ::= { hh3cevtModuleSwitchType 1077 } -- Switch Fabric Card(B Type)
hh3cevtModuleSw-CSFC-08D                    OBJECT IDENTIFIER ::= { hh3cevtModuleSwitchType 1078 } -- Switch Fabric Card(D Type)
hh3cevtModuleSw-CSFC-12B                    OBJECT IDENTIFIER ::= { hh3cevtModuleSwitchType 1079 } -- Switch Fabric Card(B Type)
hh3cevtModuleSw-CSFC-12D                    OBJECT IDENTIFIER ::= { hh3cevtModuleSwitchType 1080 } -- Switch Fabric Card(D Type)
hh3cevtModuleSw-CSPC-CP1LCX                 OBJECT IDENTIFIER ::= { hh3cevtModuleSwitchType 1081 } -- 1-Port 100GBASE Ethernet Optical Interface Module(CFP,LC)(C Type)
hh3cevtModuleSw-CSPC-CP2LB                  OBJECT IDENTIFIER ::= { hh3cevtModuleSwitchType 1082 } -- 2-Port 100GBASE Ethernet Optical Interface Module(CFP,LC)(B Type)
hh3cevtModuleSw-CSPC-GP24LA1                OBJECT IDENTIFIER ::= { hh3cevtModuleSwitchType 1083 } -- 16-Port 1000BASE-X Ethernet Optical Interface(SFP,LC)+8-Port Combo Interface Module(A Type)
hh3cevtModuleSw-CSPC-GP24XP2LB              OBJECT IDENTIFIER ::= { hh3cevtModuleSwitchType 1084 } -- 16-Port 1000BASE-X Optical Interface(SFP,LC)+8-Port Combo Interface+2-Port 10GE Optical Interface Module(XFP,LC)(B Type)
hh3cevtModuleSw-CSPC-GP44XP4LCX             OBJECT IDENTIFIER ::= { hh3cevtModuleSwitchType 1085 } -- 44-Port 1000BASE-X Ethernet Optical Interface Module(SFP,LC)+4-Port 10GBASE Ethernet Optical Interface Module(SFP+,LC)(C Type)
hh3cevtModuleSw-CSPC-GP48LB                 OBJECT IDENTIFIER ::= { hh3cevtModuleSwitchType 1086 } -- 48-Port Enhanced 1000BASE-X Ethernet Optical Interface Module(SFP,LC)(B Type)
hh3cevtModuleSw-CSPC-GT48LA1                OBJECT IDENTIFIER ::= { hh3cevtModuleSwitchType 1087 } -- 48-Port 10/100/1000BASE-T Ethernet Interface Module(RJ45)(A Type)
hh3cevtModuleSw-CSPC-XLP6LCX                OBJECT IDENTIFIER ::= { hh3cevtModuleSwitchType 1088 } -- 6-Port 40GBASE Ethernet Optical Interface Module(QSFP+,MPO)(C Type)
hh3cevtModuleSw-CSPC-XP2LA1                 OBJECT IDENTIFIER ::= { hh3cevtModuleSwitchType 1089 } -- 2-Port 10GBASE Ethernet Optical Interface Module(XFP,LC)(A Type)
hh3cevtModuleSw-CSPC-XP4LB                  OBJECT IDENTIFIER ::= { hh3cevtModuleSwitchType 1090 } -- 4-Port Enhanced 10GBASE Ethernet Optical Interface Module(XFP,LC)(B Type)
hh3cevtModuleSw-CSPC-XP8LB                  OBJECT IDENTIFIER ::= { hh3cevtModuleSwitchType 1091 } -- 8-Port Enhanced 10GBASE Ethernet Optical Interface Module(SFP+,LC)(B Type)
hh3cevtModuleSw-CSPC-XP12LAX                OBJECT IDENTIFIER ::= { hh3cevtModuleSwitchType 1092 } -- 12-Port 10GBASE Ethernet Optical Interface Module(SFP+,LC)(A Type)
hh3cevtModuleSw-CSPC-XP12LCX                OBJECT IDENTIFIER ::= { hh3cevtModuleSwitchType 1093 } -- 12-Port 10GBASE Ethernet Optical Interface Module(SFP+,LC)(C Type)
hh3cevtModuleSw-CSPC-XP24LAX                OBJECT IDENTIFIER ::= { hh3cevtModuleSwitchType 1094 } -- 24-Port 10GBASE Ethernet Optical Interface Module(SFP+,LC)(A Type)
hh3cevtModuleSw-CSPC-XP24LCX                OBJECT IDENTIFIER ::= { hh3cevtModuleSwitchType 1095 } -- 24-Port 10GBASE Ethernet Optical Interface Module(SFP+,LC)(C Type)
hh3cevtModuleSw-CSPC-CSPEX-1204             OBJECT IDENTIFIER ::= { hh3cevtModuleSwitchType 1096 } -- 4-Port 10G Processing Engine
hh3cevtModuleSw-CSR05SRP1L1                 OBJECT IDENTIFIER ::= { hh3cevtModuleSwitchType 1097 } -- Management and Route Process Unit(1L1)
hh3cevtModuleSw-CSR05SRP1L3                 OBJECT IDENTIFIER ::= { hh3cevtModuleSwitchType 1098 } -- Management and Route Process Unit(1L3)
hh3cevtModuleSw-CSR07MPUA1                  OBJECT IDENTIFIER ::= { hh3cevtModuleSwitchType 1099 } -- Management and Route Processing Unit
hh3cevtModuleSw-CSR07SRPUA1                 OBJECT IDENTIFIER ::= { hh3cevtModuleSwitchType 1100 } -- Management and Route Processing Unit(UA1)
hh3cevtModuleSw-CSR07SRPUB1                 OBJECT IDENTIFIER ::= { hh3cevtModuleSwitchType 1101 } -- Management and Route Processing Unit(UB1)
hh3cevtModuleSw-CSR07SRPUC1                 OBJECT IDENTIFIER ::= { hh3cevtModuleSwitchType 1102 } -- Management and Route Processing Unit
hh3cevtModuleSw-LSXM1CGX8FX1                OBJECT IDENTIFIER ::= { hh3cevtModuleSwitchType 1103 } -- 8-Port 100GBASE Ethernet Optical Interface Module(CXP)(FX)
hh3cevtModuleSw-LSXM1QGS24FX1               OBJECT IDENTIFIER ::= { hh3cevtModuleSwitchType 1104 } -- 24-Port 40GBASE Ethernet Optical Interface Module(QSFP+)(FX)
hh3cevtModuleSw-LSXM1TGS48FX1               OBJECT IDENTIFIER ::= { hh3cevtModuleSwitchType 1105 } -- 48-Port 10GBASE Ethernet Optical Interface Module(SFP+,LC)(FX)
hh3cevtModuleSw-LSXM1QGS12FX1               OBJECT IDENTIFIER ::= { hh3cevtModuleSwitchType 1106 } -- 12-Port 40GBASE Ethernet Optical Interface Module(QSFP+)(FX)
hh3cevtModuleSw-LSXM1TGT48FX1               OBJECT IDENTIFIER ::= { hh3cevtModuleSwitchType 1107 } -- 48-Port 10GBASE-T Ethernet Electrical Interface Module(RJ45)(FX)
hh3cevtModuleSw-LSU1IPSBEA0                 OBJECT IDENTIFIER ::= { hh3cevtModuleSwitchType 1108 } -- Intrusion Prevention System Module
hh3cevtModuleSw-PIC-GP10L                   OBJECT IDENTIFIER ::= { hh3cevtModuleSwitchType 1109 } -- 10-Port 1000BASE-X Optical Interface Card,(SFP,LC)
hh3cevtModuleSw-PIC-XP1L                    OBJECT IDENTIFIER ::= { hh3cevtModuleSwitchType 1110 } -- 1-Port 10GBASE-R/W Ethernet Optical Interface Card,(XFP,LC)
hh3cevtModuleSw-PIC-PUP1L                   OBJECT IDENTIFIER ::= { hh3cevtModuleSwitchType 1111 } -- 1-Port 10G POS Optical Interface Card,(XFP,LC)
hh3cevtModuleSw-PIC-PSP4L                   OBJECT IDENTIFIER ::= { hh3cevtModuleSwitchType 1112 } -- 4-Port 2.5G POS Optical Interface Card(SFP,LC)
hh3cevtModuleSw-PIC-PS2G4L                  OBJECT IDENTIFIER ::= { hh3cevtModuleSwitchType 1113 } -- 2-Port 2.5G POS Optical Interface(SFP,LC)+4-Port 1000BASE-X Optical Interface Card(SFP,LC)
hh3cevtModuleSw-PIC-PL2G6L                  OBJECT IDENTIFIER ::= { hh3cevtModuleSwitchType 1114 } -- 2-Port 155M POS Optical Interface(SFP,LC)+6-Port 1000BASE-X Optical Interface Card(SFP,LC)
hh3cevtModuleSw-PIC-TCP8L                   OBJECT IDENTIFIER ::= { hh3cevtModuleSwitchType 1115 } -- 8-Port OC-3c/OC-12c POS/GE Optical Interface Card,(SFP,LC)
hh3cevtModuleSw-PIC-CSP1L                   OBJECT IDENTIFIER ::= { hh3cevtModuleSwitchType 1116 } -- 1-Port 2.5G CPOS Optical Interface Card(SFP,LC)
hh3cevtModuleSw-PIC-PH2G6L                  OBJECT IDENTIFIER ::= { hh3cevtModuleSwitchType 1117 } -- 2-Port 622M POS Optical Interface(SFP,LC)+6-Port 1000BASE-X Optical Interface Card(SFP,LC)
hh3cevtModuleSw-LSXM1CGP12FX1               OBJECT IDENTIFIER ::= { hh3cevtModuleSwitchType 1118 } -- 12-Port 100GBASE Ethernet Optical Interface Module(CFP2)(FX)
hh3cevtModuleSw-LSXM1CGP8FX1                OBJECT IDENTIFIER ::= { hh3cevtModuleSwitchType 1119 } -- 8-Port 100GBASE Ethernet Optical Interface Module(CFP2)(FX)
hh3cevtModuleSw-LSXM1GT48FX1                OBJECT IDENTIFIER ::= { hh3cevtModuleSwitchType 1120 } -- 48-Port 1000Base-T Gigabit Ethernet Interface Board(RJ45)
hh3cevtModuleSw-LSXM1GT48FX0                OBJECT IDENTIFIER ::= { hh3cevtModuleSwitchType 1121 } -- 48-Port 1000Base-T Gigabit Ethernet Interface Board(RJ45)
hh3cevtModuleSw-LSXM1GP48FX1                OBJECT IDENTIFIER ::= { hh3cevtModuleSwitchType 1122 } -- 48-Port 1000BASE Ethernet SFP Optical Interface Board
hh3cevtModuleSw-LSXM1GP48FX0                OBJECT IDENTIFIER ::= { hh3cevtModuleSwitchType 1123 } -- 48-Port 1000BASE Ethernet SFP Optical Interface Board
hh3cevtModuleSw-LSXM1TGS24FX0               OBJECT IDENTIFIER ::= { hh3cevtModuleSwitchType 1124 } -- 24-Port 10GBASE Ethernet SFP+ Optical Interface Board
hh3cevtModuleSw-LSXM1TGS24FX1               OBJECT IDENTIFIER ::= { hh3cevtModuleSwitchType 1125 } -- 24-Port 10GBASE Ethernet SFP+ Optical Interface Board
hh3cevtModuleSw-MIC-SP8L                    OBJECT IDENTIFIER ::= { hh3cevtModuleSwitchType 1126 } -- 8-Port OC-3c/STM-1c POS Optical Interface Card
hh3cevtModuleSw-LSXM1TGS48FE1               OBJECT IDENTIFIER ::= { hh3cevtModuleSwitchType 1127 } -- 48-Port 10GBASE Ethernet SFP+ Optical Interface Board(FE)
hh3cevtModuleSw-LSXM1QGS24FE1               OBJECT IDENTIFIER ::= { hh3cevtModuleSwitchType 1128 } -- 24-Port 40GBASE Ethernet Optical Interface Board(QSFP+)
hh3cevtModuleSw-CSPEX-1504S                 OBJECT IDENTIFIER ::= { hh3cevtModuleSwitchType 1129 } -- Multi-Service Processing Board
hh3cevtModuleSw-CSPEX-1504X                 OBJECT IDENTIFIER ::= { hh3cevtModuleSwitchType 1130 } -- Multi-Service Processing Board
hh3cevtModuleSw-CSPEX-1404S                 OBJECT IDENTIFIER ::= { hh3cevtModuleSwitchType 1131 } -- Multi-Service Processing Board
hh3cevtModuleSw-CSPEX-1304S                 OBJECT IDENTIFIER ::= { hh3cevtModuleSwitchType 1132 } -- Multi-Service Processing Board
hh3cevtModuleSw-CSPEX-1404X                 OBJECT IDENTIFIER ::= { hh3cevtModuleSwitchType 1133 } -- Multi-Service Processing Board
hh3cevtModuleSw-CSPEX-1304X                 OBJECT IDENTIFIER ::= { hh3cevtModuleSwitchType 1134 } -- Multi-Service Processing Board
hh3cevtModuleSw-MIC-XP5L                    OBJECT IDENTIFIER ::= { hh3cevtModuleSwitchType 1135 } -- 5-Port 10GBASE-R/W Ethernet Optical Interface Card,(SFP+,LC)
hh3cevtModuleSw-MIC-XP2L                    OBJECT IDENTIFIER ::= { hh3cevtModuleSwitchType 1136 } -- 2-Port 10GBASE-R/W Ethernet Optical Interface Card,(SFP+,LC)
hh3cevtModuleSw-MIC-CP1L                    OBJECT IDENTIFIER ::= { hh3cevtModuleSwitchType 1137 } -- 1-Port 100G Optical Interface Card,(CFP,LC)
hh3cevtModuleSw-MIC-GP20L                   OBJECT IDENTIFIER ::= { hh3cevtModuleSwitchType 1138 } -- 20-Port 1000BASE-X Ethernet Optical Interface Card,(SFP,LC),Monolithic
hh3cevtModuleSw-MIC-GT20L                   OBJECT IDENTIFIER ::= { hh3cevtModuleSwitchType 1139 } -- 20-Port 1000BASE-X Ethernet Electrical Interface Card,(RJ45,LC),Monolithic
hh3cevtModuleSw-CEPC-XP48RX                 OBJECT IDENTIFIER ::= { hh3cevtModuleSwitchType 1140 } -- 48-Port 10GBASE-R/W Interface Module,(SFP+,LC)
hh3cevtModuleSw-CEPC-CP4RX                  OBJECT IDENTIFIER ::= { hh3cevtModuleSwitchType 1141 } -- 4-Port 100GBASE Ethernet Optical Interface Board(CFP2)
hh3cevtModuleSw-MIC-GP10L-V2                OBJECT IDENTIFIER ::= { hh3cevtModuleSwitchType 1142 } -- 10-Port 1000BASE-X Optical Interface Card,(SFP,LC)
hh3cevtModuleSw-CSR07SRPUD3                 OBJECT IDENTIFIER ::= { hh3cevtModuleSwitchType 1143 } -- Management and Route Process Board(UD3)
hh3cevtModuleSw-MIC-XP1L                    OBJECT IDENTIFIER ::= { hh3cevtModuleSwitchType 1144 } -- 1-Port 10GBASE-R/W Ethernet Optical Interface Card,(SFP+,LC)
hh3cevtModuleSw-CSFC-12E                    OBJECT IDENTIFIER ::= { hh3cevtModuleSwitchType 1145 } -- Switch Fabric Board
hh3cevtModuleSw-CEPC-XP24LX                 OBJECT IDENTIFIER ::= { hh3cevtModuleSwitchType 1146 } -- 24-Port 10GBASE-R/W Interface Module,(SFP+,LC)
hh3cevtModuleSw-IM-MSUX                     OBJECT IDENTIFIER ::= { hh3cevtModuleSwitchType 1147 } -- Multi-Service Processing Board,Monolithic
hh3cevtModuleSw-CSFC-12F                    OBJECT IDENTIFIER ::= { hh3cevtModuleSwitchType 1148 } -- Switch Fabric Board, Monolithic
hh3cevtModuleSw-CSR05SRP1N3                 OBJECT IDENTIFIER ::= { hh3cevtModuleSwitchType 1149 } -- Main Processing Unit(1N3)
hh3cevtModuleSw-CSPEX-1602X                 OBJECT IDENTIFIER ::= { hh3cevtModuleSwitchType 1150 } -- Service Processing Unit(1602X)
hh3cevtModuleSw-MIC-XP20L                   OBJECT IDENTIFIER ::= { hh3cevtModuleSwitchType 1151 } -- 20-port 10GBASE-R/W Ethernet Optical Interface Card(SFP+,LC)
hh3cevtModuleSw-MIC-CP2L                    OBJECT IDENTIFIER ::= { hh3cevtModuleSwitchType 1152 } -- 2-port 100G Ethernet Optical Interface Card(CFP2,LC)
hh3cevtModuleSw-IM-NGFWX-IV                 OBJECT IDENTIFIER ::= { hh3cevtModuleSwitchType 1153 } -- Next Generation Firewall Module
hh3cevtModuleSw-SFC-12E                     OBJECT IDENTIFIER ::= { hh3cevtModuleSwitchType 1154 } -- Switch Fabric Board

hh3cevtModuleSw-SPEX-1602X-E                OBJECT IDENTIFIER ::= { hh3cevtModuleSwitchType 1155 } -- Service Processing Unit(1602X)-E
hh3cevtModuleSw-SPEX-1602X-L                OBJECT IDENTIFIER ::= { hh3cevtModuleSwitchType 1156 } -- Service Processing Unit(1602X)-L
hh3cevtModuleSw-EPC-XP24LX-E                OBJECT IDENTIFIER ::= { hh3cevtModuleSwitchType 1157 } -- 24-Port 10GBASE-R/W Ethernet Optical Interface Line Processing Unit (SFP+,LC)-E
hh3cevtModuleSw-EPC-XP24LX-L                OBJECT IDENTIFIER ::= { hh3cevtModuleSwitchType 1158 } -- 24-Port 10GBASE-R/W Ethernet Optical Interface Line Processing Unit (SFP+,LC)-L
hh3cevtModuleSw-EPC-CP4RX-L                 OBJECT IDENTIFIER ::= { hh3cevtModuleSwitchType 1159 } -- 4-Port 100GBASE Ethernet Optical Interface Line Processing Unit (CFP2)-L
hh3cevtModuleSw-SPEX-1504X-E                OBJECT IDENTIFIER ::= { hh3cevtModuleSwitchType 1160 } -- Service Processing Unit(1504X)-E
hh3cevtModuleSw-SPEX-1504X-L                OBJECT IDENTIFIER ::= { hh3cevtModuleSwitchType 1161 } -- Service Processing Unit(1504X)-L
hh3cevtModuleSw-CSPEX-1602X-L               OBJECT IDENTIFIER ::= { hh3cevtModuleSwitchType 1162 } -- Service Processing Unit(1602X)-L
hh3cevtModuleSw-CEPC-XP24LX-L               OBJECT IDENTIFIER ::= { hh3cevtModuleSwitchType 1163 } -- 24-Port 10GBASE-R/W Ethernet Optical Interface Line Processing Unit (SFP+,LC)-L
hh3cevtModuleSw-CEPC-CP4RX-L                OBJECT IDENTIFIER ::= { hh3cevtModuleSwitchType 1164 } -- 4-port 100G Ethernet Optical Interface Line Processing Unit(QSFP28)
hh3cevtModuleSw-MIC-CP1L-E                  OBJECT IDENTIFIER ::= { hh3cevtModuleSwitchType 1165 } -- 1-port 100G Ethernet Optical Interface Card(CFP,LC)-E
hh3cevtModuleSw-MIC-XP4L-E                  OBJECT IDENTIFIER ::= { hh3cevtModuleSwitchType 1166 } -- 4-Port 10GBASE-R/W Ethernet Optical Interface Card,(SFP+,LC)-E
hh3cevtModuleSw-MIC-XP16L-E                 OBJECT IDENTIFIER ::= { hh3cevtModuleSwitchType 1167 } -- 16-port 10GBASE-R/W Ethernet Optical Interface Card(SFP+,LC)-E
hh3cevtModuleSw-MIC-GP20L-E                 OBJECT IDENTIFIER ::= { hh3cevtModuleSwitchType 1168 } -- 20-Port 1000BASE-X Ethernet Optical Interface Card,(SFP,LC)-E
hh3cevtModuleSw-MIC-GP10L-V2-E              OBJECT IDENTIFIER ::= { hh3cevtModuleSwitchType 1169 } -- 10-Port 1000BASE-X Ethernet Optical Interface Card(SFP,LC)-E
hh3cevtModuleSw-MIC-GT20L-E                 OBJECT IDENTIFIER ::= { hh3cevtModuleSwitchType 1170 } -- 20-Port 1000BASE-X Ethernet Electrical Interface Card,(RJ45,LC)-E
hh3cevtModuleSw-CSR05SRP1P3                 OBJECT IDENTIFIER ::= { hh3cevtModuleSwitchType 1171 } -- CR16018-F Main Processing Unit(1P3)
hh3cevtModuleSw-SR05SRP1P3                  OBJECT IDENTIFIER ::= { hh3cevtModuleSwitchType 1172 } -- SR8816-X Main Processing Unit(1P3)
hh3cevtModuleSw-CSFC-16E                    OBJECT IDENTIFIER ::= { hh3cevtModuleSwitchType 1173 } -- CR16018-F Fabric Module(E Type)
hh3cevtModuleSw-SFC-16E                     OBJECT IDENTIFIER ::= { hh3cevtModuleSwitchType 1174 } -- SR8816-X Fabric Module(E Type)
hh3cevtModuleSw-CSFC-08E                    OBJECT IDENTIFIER ::= { hh3cevtModuleSwitchType 1175 } -- CR16010-F Fabric Module(E Type)
hh3cevtModuleSw-SFC-08E                     OBJECT IDENTIFIER ::= { hh3cevtModuleSwitchType 1176 } -- SR8808-X Fabric Module(E Type)
hh3cevtModuleSw-IM-SMUX                     OBJECT IDENTIFIER ::= { hh3cevtModuleSwitchType 1177 } -- Security Monitor Unit (IM-SMUX)
hh3cevtModuleSw-IM-IPSX-IV                  OBJECT IDENTIFIER ::= { hh3cevtModuleSwitchType 1178 } -- Intrusion Prevention System Module
hh3cevtModuleSw-IM-ACGX-IV                  OBJECT IDENTIFIER ::= { hh3cevtModuleSwitchType 1179 } -- Application Control Gateway Module
hh3cevtModuleSw-SFC-08E1                    OBJECT IDENTIFIER ::= { hh3cevtModuleSwitchType 1180 } -- SR8808H-X Fabric Module(E Type)
hh3cevtModuleSw-CSFC-08E1                   OBJECT IDENTIFIER ::= { hh3cevtModuleSwitchType 1181 } -- CR16010H-F Fabric Module(E Type)
hh3cevtModuleSw-IM-ACG1000X-IV              OBJECT IDENTIFIER ::= { hh3cevtModuleSwitchType 1182 } -- SecPath ACG1000-Blade-X Application Control Module(SR88-X SecBladeIV)
hh3cevtModuleSw-MIC-QP1L                    OBJECT IDENTIFIER ::= { hh3cevtModuleSwitchType 1183 } -- 1-port 40G Ethernet Optical Interface Card(QSFP+,LC)
hh3cevtModuleSw-CSPEX-1804X                 OBJECT IDENTIFIER ::= { hh3cevtModuleSwitchType 1184 } -- Service Processing Unit(1804X)
hh3cevtModuleSw-MIC-CP2L-V2                 OBJECT IDENTIFIER ::= { hh3cevtModuleSwitchType 1185 } -- 2-port 100G Ethernet Optical Interface Card(QSFP28)
hh3cevtModuleSw-MIC-XP4L1                   OBJECT IDENTIFIER ::= { hh3cevtModuleSwitchType 1186 } -- 4-port 10GBASE-R/W Ethernet Optical Interface Card 1(SFP+,LC)
hh3cevtModuleSw-SFC-16T                     OBJECT IDENTIFIER ::= { hh3cevtModuleSwitchType 1187 } -- SR8816-X Fabric Module(T Type)
hh3cevtModuleSw-CSFC-16T                    OBJECT IDENTIFIER ::= { hh3cevtModuleSwitchType 1188 } -- CR16018-F Fabric Module(T Type)
hh3cevtModuleSw-SFC-08T                     OBJECT IDENTIFIER ::= { hh3cevtModuleSwitchType 1189 } -- SR8808H-X Fabric Module(T Type)
hh3cevtModuleSw-CSFC-08T                    OBJECT IDENTIFIER ::= { hh3cevtModuleSwitchType 1190 } -- CR16010H-F Fabric Module(T Type)
hh3cevtModuleSw-MIC-XP2L-LAN                OBJECT IDENTIFIER ::= { hh3cevtModuleSwitchType 1191 } -- 2-port 10GBASE-R Ethernet Optical Interface Card(SFP+,LC)-LAN
hh3cevtModuleSw-MIC-XP5L1                   OBJECT IDENTIFIER ::= { hh3cevtModuleSwitchType 1192 } -- 5-port 10GBASE-R/W Ethernet Optical Interface Card(SFP+,LC)
hh3cevtModuleSw-MIC-CP1L-V2                 OBJECT IDENTIFIER ::= { hh3cevtModuleSwitchType 1193 } -- 1-port 100G Ethernet Optical Interface Card(CFP2,LC)
hh3cevtModuleSw-CEPC-XP40LX                 OBJECT IDENTIFIER ::= { hh3cevtModuleSwitchType 1194 } -- 40-port 10GBASE-R/W Ethernet Optical Interface Line Processing Unit Module(SFP+,LC)
hh3cevtModuleSw-CEPC-CQ4LX                  OBJECT IDENTIFIER ::= { hh3cevtModuleSwitchType 1195 } -- 4-port 100G Ethernet Optical Interface Line Processing Unit Module(QSFP28,LC)


--
-- 1200 to 1399 reserved for secondary switches part II
--
hh3cevtModuleSw-LSU1QGC4SF0                 OBJECT IDENTIFIER ::= { hh3cevtModuleSwitchType 1201 } -- 4 Port 40G BASE Ethernet Optical Interface Board(CFP,SC)(SF)
hh3cevtModuleSw-LSU1QGS8SF0                 OBJECT IDENTIFIER ::= { hh3cevtModuleSwitchType 1202 } -- 8-Port 40G BASE Ethernet Optical Interface Board(QSFP,MPO)(SF)
hh3cevtModuleSw-LSU1TGS48SF0                OBJECT IDENTIFIER ::= { hh3cevtModuleSwitchType 1203 } -- 48-Port 10GBASE Ethernet SFP+ Optical Interface Board
hh3cevtModuleSw-LSU1QGS4SF0                 OBJECT IDENTIFIER ::= { hh3cevtModuleSwitchType 1204 } -- 4-Port 40G BASE Ethernet Optical Interface Board(QSFP,MPO)(SF)
hh3cevtModuleSw-LSU1TGS32SF0                OBJECT IDENTIFIER ::= { hh3cevtModuleSwitchType 1205 } -- 32-Port 10GBASE Ethernet SFP+ Optical Interface Board
hh3cevtModuleSw-LSU1FAB08D0                 OBJECT IDENTIFIER ::= { hh3cevtModuleSwitchType 1206 } -- Switching Fabric Module
hh3cevtModuleSw-LSU1FAB04B0                 OBJECT IDENTIFIER ::= { hh3cevtModuleSwitchType 1207 } -- Switching Fabric Module
hh3cevtModuleSw-LSU1FAB08B0                 OBJECT IDENTIFIER ::= { hh3cevtModuleSwitchType 1208 } -- Switching Fabric Module
hh3cevtModuleSw-LSU1FAB12D0                 OBJECT IDENTIFIER ::= { hh3cevtModuleSwitchType 1209 } -- Switching Fabric Module
hh3cevtModuleSw-LSU1FAB12B0                 OBJECT IDENTIFIER ::= { hh3cevtModuleSwitchType 1210 } -- Switching Fabric Module
hh3cevtModuleSw-LSU1FAB04D0                 OBJECT IDENTIFIER ::= { hh3cevtModuleSwitchType 1211 } -- Switching Fabric Module
hh3cevtModuleSw-LSQ1CTGS16SC0               OBJECT IDENTIFIER ::= { hh3cevtModuleSwitchType 1212 } -- Supervisor Engine Board With 16-Port 10GBASE Ethernet SFP+ Optical Interfaces
hh3cevtModuleSw-EWPX2CTGS16SC0              OBJECT IDENTIFIER ::= { hh3cevtModuleSwitchType 1213 } -- Supervisor Engine Board With 16-Port 10GBASE Ethernet SFP+ Optical Interfaces
hh3cevtModuleSw-LSU3WCMD0                   OBJECT IDENTIFIER ::= { hh3cevtModuleSwitchType 1214 } -- Access Controller Card
hh3cevtModuleSw-EWPX3WCMD0                  OBJECT IDENTIFIER ::= { hh3cevtModuleSwitchType 1215 } -- Access Controller Card
hh3cevtModuleSw-LSQ1QGS4SC0                 OBJECT IDENTIFIER ::= { hh3cevtModuleSwitchType 1216 } -- 4-Port 40G BASE Ethernet Optical Interface Board(QSFP+,MPO)(SC)
hh3cevtModuleSw-LSQ1QGC4SC0                 OBJECT IDENTIFIER ::= { hh3cevtModuleSwitchType 1217 } -- 4 Port 40GBASE Ethernet Optical Interface Board(CFP)(SC)
hh3cevtModuleSw-LSU1TGT24SF0                OBJECT IDENTIFIER ::= { hh3cevtModuleSwitchType 1218 } -- 24-Port 10GBASE-T Ethernet Electrical Interface Board(RJ45)(SF)
hh3cevtModuleSw-LSQ1QGS8SC3                 OBJECT IDENTIFIER ::= { hh3cevtModuleSwitchType 1219 } -- 8-Port 40G BASE Ethernet Optical Interface Board(QSFP+,MPO)
hh3cevtModuleSw-LSQ1TGS32SC3                OBJECT IDENTIFIER ::= { hh3cevtModuleSwitchType 1220 } -- 32-Port 10GBASE Ethernet SFP+ Optical Interface Board
hh3cevtModuleSw-LSQ1QGS4SC3                 OBJECT IDENTIFIER ::= { hh3cevtModuleSwitchType 1221 } -- 4-Port 40GBASE Ethernet Optical Interface Board(QSFP+,MPO)(SC)
hh3cevtModuleSw-LSQ1TGS48SC3                OBJECT IDENTIFIER ::= { hh3cevtModuleSwitchType 1222 } -- 48-Port 10GBASE Ethernet SFP+ Optical Interface Board
hh3cevtModuleSw-LSQ1QGC4SC3                 OBJECT IDENTIFIER ::= { hh3cevtModuleSwitchType 1223 } -- 4-Port 40GBASE Ethernet Optical Interface Board(CFP)(SC)
hh3cevtModuleSw-LSQ1FAB12D3                 OBJECT IDENTIFIER ::= { hh3cevtModuleSwitchType 1224 } -- Switch Fabric Board
hh3cevtModuleSw-LSQ1FAB08D3                 OBJECT IDENTIFIER ::= { hh3cevtModuleSwitchType 1225 } -- Switching Fabric Module
hh3cevtModuleSw-LSQ1FAB04D3                 OBJECT IDENTIFIER ::= { hh3cevtModuleSwitchType 1226 } -- Switching Fabric Module
hh3cevtModuleSw-LSQ1TGS8EB3                 OBJECT IDENTIFIER ::= { hh3cevtModuleSwitchType 1227 } -- 8-Port 10GBASE Ethernet SFP+ Optical Interface Board
hh3cevtModuleSw-LSQ1TGT24SC3                OBJECT IDENTIFIER ::= { hh3cevtModuleSwitchType 1228 } -- 24-Port 10GBASE-T Ethernet Electrical Interface Board(RJ45)(SC)
hh3cevtModuleSw-LSQ1FAB08B0                 OBJECT IDENTIFIER ::= { hh3cevtModuleSwitchType 1229 } -- Switching Fabric Module
hh3cevtModuleSw-EWPX2CTGS16SC               OBJECT IDENTIFIER ::= { hh3cevtModuleSwitchType 1230 } -- Supervisor Engine Board With 16-Port 10GBASE Ethernet SFP+ Optical Interfaces
hh3cevtModuleSw-LSU1SUPB0                   OBJECT IDENTIFIER ::= { hh3cevtModuleSwitchType 1231 } -- Supervisor Engine Board
hh3cevtModuleSw-LSQ1GP48SA0                 OBJECT IDENTIFIER ::= { hh3cevtModuleSwitchType 1232 } -- 48-Port 1000BASE-X Ethernet Optical Interface Board(SFP,LC)
hh3cevtModuleSw-LSQ1TGX2SA0                 OBJECT IDENTIFIER ::= { hh3cevtModuleSwitchType 1233 } -- 2-Port 10GBASE Ethernet Optical Interface Board(XFP,LC)
hh3cevtModuleSw-LSV1SRPUA1                  OBJECT IDENTIFIER ::= { hh3cevtModuleSwitchType 1234 } -- Supervisor Engine Board
hh3cevtModuleSw-LSV1QGS12SA1                OBJECT IDENTIFIER ::= { hh3cevtModuleSwitchType 1235 } -- 12-Port 40G BASE Ethernet Optical Interface Board(QSFP+)
hh3cevtModuleSw-LSV1MPUA1                   OBJECT IDENTIFIER ::= { hh3cevtModuleSwitchType 1236 } -- Supervisor Engine Board
hh3cevtModuleSw-LSX1SUP10A0                 OBJECT IDENTIFIER ::= { hh3cevtModuleSwitchType 1237 } -- Supervisor Engine Board
hh3cevtModuleSw-LSX1SUP16A0                 OBJECT IDENTIFIER ::= { hh3cevtModuleSwitchType 1238 } -- Supervisor Engine Board
hh3cevtModuleSw-LSX1SUP10A1                 OBJECT IDENTIFIER ::= { hh3cevtModuleSwitchType 1239 } -- Supervisor Engine Board
hh3cevtModuleSw-LSX1SUP16A1                 OBJECT IDENTIFIER ::= { hh3cevtModuleSwitchType 1240 } -- Supervisor Engine Board
hh3cevtModuleSw-LSX1FAB10B0                 OBJECT IDENTIFIER ::= { hh3cevtModuleSwitchType 1241 } -- Switch Fabric Board
hh3cevtModuleSw-LSX1FAB16B0                 OBJECT IDENTIFIER ::= { hh3cevtModuleSwitchType 1242 } -- Switch Fabric Board
hh3cevtModuleSw-LSX1FAB10B1                 OBJECT IDENTIFIER ::= { hh3cevtModuleSwitchType 1243 } -- Switch Fabric Board
hh3cevtModuleSw-LSX1FAB16B1                 OBJECT IDENTIFIER ::= { hh3cevtModuleSwitchType 1244 } -- Switch Fabric Board
hh3cevtModuleSw-LSX1QGS16EA0                OBJECT IDENTIFIER ::= { hh3cevtModuleSwitchType 1245 } -- Switch Fabric Board16-Port 40G BASE Ethernet Optical Interface Board(QSFP+,MPO)
hh3cevtModuleSw-LSX1TGS48EA0                OBJECT IDENTIFIER ::= { hh3cevtModuleSwitchType 1246 } -- 48-Port 10GBASE Ethernet SFP+ Optical Interface Board
hh3cevtModuleSw-LSX1QGS16EA1                OBJECT IDENTIFIER ::= { hh3cevtModuleSwitchType 1247 } -- Switch Fabric Board16-Port 40G BASE Ethernet Optical Interface Board(QSFP+,MPO)
hh3cevtModuleSw-LSX1TGS48EA1                OBJECT IDENTIFIER ::= { hh3cevtModuleSwitchType 1248 } -- 48-Port 10GBASE Ethernet SFP+ Optical Interface Board
hh3cevtModuleSw-LSU1TGT24SF9                OBJECT IDENTIFIER ::= { hh3cevtModuleSwitchType 1249 } -- 24-Port 10GBASE-T Ethernet Electrical Interface Board(RJ45)(SF)
hh3cevtModuleSw-LSU1QGS8SF9                 OBJECT IDENTIFIER ::= { hh3cevtModuleSwitchType 1250 } -- 8-Port 40G BASE Ethernet Optical Interface Board(QSFP+,MPO)(SF)
hh3cevtModuleSw-LSU1QGS4SF9                 OBJECT IDENTIFIER ::= { hh3cevtModuleSwitchType 1251 } -- 4-Port 40GBASE Ethernet QSFP+ Optical Interface Board(QSFP+,MPO)(SF)
hh3cevtModuleSw-LSU1TGS48SF9                OBJECT IDENTIFIER ::= { hh3cevtModuleSwitchType 1252 } -- 48-Port 10GBASE Ethernet SFP+ Optical Interface Board
hh3cevtModuleSw-LSU1TGS32SF9                OBJECT IDENTIFIER ::= { hh3cevtModuleSwitchType 1253 } -- 32-Port 10GBASE Ethernet SFP+ Optical Interface Board
hh3cevtModuleSw-LSU1FAB08D9                 OBJECT IDENTIFIER ::= { hh3cevtModuleSwitchType 1254 } -- Switching Fabric Module
hh3cevtModuleSw-LSU1SUPB9                   OBJECT IDENTIFIER ::= { hh3cevtModuleSwitchType 1255 } -- Supervisor Engine Board
hh3cevtModuleSw-LSQ3GV48SC0                 OBJECT IDENTIFIER ::= { hh3cevtModuleSwitchType 1256 } -- 48-Port 1000Base-T Gigabit Ethernet Interface Board(RJ45), PoE Plus
hh3cevtModuleSw-LSX1QGS12EC1                OBJECT IDENTIFIER ::= { hh3cevtModuleSwitchType 1257 } -- 12-Port 40GBASE Ethernet Optical Interface Board(QSFP+)
hh3cevtModuleSw-LSX1QGS12EC0                OBJECT IDENTIFIER ::= { hh3cevtModuleSwitchType 1258 } -- 12-Port 40GBASE Ethernet Optical Interface Board(QSFP+)
hh3cevtModuleSw-LSX1TGS48EC0                OBJECT IDENTIFIER ::= { hh3cevtModuleSwitchType 1259 } -- 48-Port 10GBASE Ethernet SFP+ Optical Interface Board
hh3cevtModuleSw-LSX1TGS48EC1                OBJECT IDENTIFIER ::= { hh3cevtModuleSwitchType 1260 } -- 48-Port 10GBASE Ethernet SFP+ Optical Interface Board
hh3cevtModuleSw-LSX1TGS24EC0                OBJECT IDENTIFIER ::= { hh3cevtModuleSwitchType 1261 } -- 24-Port 10GBASE Ethernet SFP+ Optical Interface Board(EC)
hh3cevtModuleSw-LSX1TGS24EC1                OBJECT IDENTIFIER ::= { hh3cevtModuleSwitchType 1262 } -- 24-Port 10GBASE Ethernet SFP+ Optical Interface Board(EC)
hh3cevtModuleSw-LSX1FAB10A0                 OBJECT IDENTIFIER ::= { hh3cevtModuleSwitchType 1263 } -- Switch Fabric Board,For 10 Slots Chassis
hh3cevtModuleSw-LSX1FAB16A1                 OBJECT IDENTIFIER ::= { hh3cevtModuleSwitchType 1264 } -- Switch Fabric Board,For 16 Slots Chassis
hh3cevtModuleSw-LSX1QGS12FB0                OBJECT IDENTIFIER ::= { hh3cevtModuleSwitchType 1265 } -- 12-Port 40GBASE Ethernet Optical Interface Board(QSFP+)
hh3cevtModuleSw-LSX1TGS24FB0                OBJECT IDENTIFIER ::= { hh3cevtModuleSwitchType 1266 } -- 24-Port 10GBASE Ethernet SFP+ Optical Interface Board(FB)
hh3cevtModuleSw-LSX1TGS48FB0                OBJECT IDENTIFIER ::= { hh3cevtModuleSwitchType 1267 } -- 48-Port 10GBASE Ethernet SFP+ Optical Interface Board(FB)
hh3cevtModuleSw-LSX1QGS12EB1                OBJECT IDENTIFIER ::= { hh3cevtModuleSwitchType 1268 } -- 12-Port 40GBASE Ethernet Optical Interface Board(QSFP+)
hh3cevtModuleSw-LSX1TGS24EB1                OBJECT IDENTIFIER ::= { hh3cevtModuleSwitchType 1269 } -- 24-Port 10GBASE Ethernet SFP+ Optical Interface Board(EB)
hh3cevtModuleSw-LSX1FAB10A1                 OBJECT IDENTIFIER ::= { hh3cevtModuleSwitchType 1270 } -- Switch Fabric Board,For 10 Slots Chassis
hh3cevtModuleSw-LSX1TGS48EB1                OBJECT IDENTIFIER ::= { hh3cevtModuleSwitchType 1271 } -- 48-Port 10GBASE Ethernet SFP+ Optical Interface Board(EB)
hh3cevtModuleSw-LSX1GP48EB1                 OBJECT IDENTIFIER ::= { hh3cevtModuleSwitchType 1272 } -- 44-Port GE Optical Interface(SFP,LC)+4-Port 10GE Optical Interface Board(SFP+,LC)
hh3cevtModuleSw-LSX1GP48FB0                 OBJECT IDENTIFIER ::= { hh3cevtModuleSwitchType 1273 } -- 44-Port GE Optical Interface(SFP,LC)+4-Port 10GE Optical Interface Board(SFP+,LC)
hh3cevtModuleSw-LSX1GT48FC0                 OBJECT IDENTIFIER ::= { hh3cevtModuleSwitchType 1274 } -- 48-Port 1000Base-T Gigabit Ethernet Interface Module(RJ45)(FC)
hh3cevtModuleSw-LSX1GT48FC1                 OBJECT IDENTIFIER ::= { hh3cevtModuleSwitchType 1275 } -- 48-Port 1000Base-T Gigabit Ethernet Interface Module(RJ45)(FC)
hh3cevtModuleSw-LSX1GP48FC0                 OBJECT IDENTIFIER ::= { hh3cevtModuleSwitchType 1276 } -- 48-Port 1000BASE-X Gigabit Ethernet Optical Interface Module(SFP,LC)(FC)
hh3cevtModuleSw-LSX1GP48FC1                 OBJECT IDENTIFIER ::= { hh3cevtModuleSwitchType 1277 } -- 48-Port 1000BASE-X Gigabit Ethernet Optical Interface Module(SFP,LC)(FC)
hh3cevtModuleSw-LSX1QGS12FC0                OBJECT IDENTIFIER ::= { hh3cevtModuleSwitchType 1278 } -- 12-Port 40GBASE Ethernet Optical Interface Module(QSFP+)(FC)
hh3cevtModuleSw-LSX1QGS12FC1                OBJECT IDENTIFIER ::= { hh3cevtModuleSwitchType 1279 } -- 12-Port 40GBASE Ethernet Optical Interface Module(QSFP+)(FC)
hh3cevtModuleSw-LSX2TGS48EA1                OBJECT IDENTIFIER ::= { hh3cevtModuleSwitchType 1280 } -- 48-Port 10GBASE Ethernet SFP+ Optical Interface Board(EA)
hh3cevtModuleSw-LSX1CGC4EB1                 OBJECT IDENTIFIER ::= { hh3cevtModuleSwitchType 1281 } -- 4-Port 100GBASE Ethernet Optical Interface Board(CFP),Monolithic
hh3cevtModuleSw-LSX1CGC4EC0                 OBJECT IDENTIFIER ::= { hh3cevtModuleSwitchType 1282 } -- 4-Port 100GBASE Ethernet Optical Interface Board(CFP),Monolithic
hh3cevtModuleSw-LSX1GT48EB1                 OBJECT IDENTIFIER ::= { hh3cevtModuleSwitchType 1283 } -- 48-Port 1000Base-T Gigabit Ethernet Interface Board(RJ45)
hh3cevtModuleSw-LSX1GT48FB0                 OBJECT IDENTIFIER ::= { hh3cevtModuleSwitchType 1284 } -- 48-Port 1000Base-T Gigabit Ethernet Interface Board(RJ45)
hh3cevtModuleSw-LSX1FAB16S1                 OBJECT IDENTIFIER ::= { hh3cevtModuleSwitchType 1285 } -- Switch Fabric Board,For 16 Slots Chassis
hh3cevtModuleSw-LSQ1SUPB3                   OBJECT IDENTIFIER ::= { hh3cevtModuleSwitchType 1286 } -- Supervisor Engine Board
hh3cevtModuleSw-LSU1CGC2SE0                 OBJECT IDENTIFIER ::= { hh3cevtModuleSwitchType 1287 } -- 2 Port 100GBASE Ethernet Optical Interface Board(CFP)(SE)
hh3cevtModuleSw-LSU1TGS16SF0                OBJECT IDENTIFIER ::= { hh3cevtModuleSwitchType 1288 } -- 16-Port 10GBASE Ethernet SFP+ Optical Interface Board
hh3cevtModuleSw-LSU1TGS8SF0                 OBJECT IDENTIFIER ::= { hh3cevtModuleSwitchType 1289 } -- 8-Port 10GBASE Ethernet SFP+ Optical Interface Board
hh3cevtModuleSw-LSQ1TGS4SC0                 OBJECT IDENTIFIER ::= { hh3cevtModuleSwitchType 1290 } -- 4-Port 10GBASE Ethernet SFP+ Optical Interface Board
hh3cevtModuleSw-LSU1GT48SE3                 OBJECT IDENTIFIER ::= { hh3cevtModuleSwitchType 1291 } -- 48-Port 1000Base-T Gigabit Ethernet Interface Board(RJ45)
hh3cevtModuleSw-LSU1GP48SE3                 OBJECT IDENTIFIER ::= { hh3cevtModuleSwitchType 1292 } -- 48-Port 1000BASE Ethernet Optical Interface Board(SFP,LC)
hh3cevtModuleSw-LSX1SUP10B0                 OBJECT IDENTIFIER ::= { hh3cevtModuleSwitchType 1293 } -- Supervisor Engine Board
hh3cevtModuleSw-LSX1SUP16B0                 OBJECT IDENTIFIER ::= { hh3cevtModuleSwitchType 1294 } -- Supervisor Engine Board
hh3cevtModuleSw-LSX1SUP10B1                 OBJECT IDENTIFIER ::= { hh3cevtModuleSwitchType 1295 } -- Supervisor Engine Board
hh3cevtModuleSw-LSX1SUP16B1                 OBJECT IDENTIFIER ::= { hh3cevtModuleSwitchType 1296 } -- Supervisor Engine Board
hh3cevtModuleSw-LSQ1CGV24PSC3               OBJECT IDENTIFIER ::= { hh3cevtModuleSwitchType 1297 } -- Switching and Routing Processing Unit with 24 10/100/1000BASE-T Electrical Ports(RJ45),including 4 Combo Ports,SFP Req,PoE,No Spell
hh3cevtModuleSw-LSQ1SRPA8                   OBJECT IDENTIFIER ::= { hh3cevtModuleSwitchType 1298 } -- Supervisor Engine Board
hh3cevtModuleSw-LSQ1CGP24TSC8               OBJECT IDENTIFIER ::= { hh3cevtModuleSwitchType 1299 } -- Supervisor Engine Board
hh3cevtModuleSw-LSQ1CGT24PSC8               OBJECT IDENTIFIER ::= { hh3cevtModuleSwitchType 1300 } -- Supervisor Engine Board
hh3cevtModuleSw-LSQ1GT24PSA8                OBJECT IDENTIFIER ::= { hh3cevtModuleSwitchType 1301 } -- 24-Port 10/100/1000BASE-T Electrical(RJ45) Interface Board,including 4 Combo Ports,SFP Req,Upgradeable to PoE
hh3cevtModuleSw-LSQ1GP24TSA8                OBJECT IDENTIFIER ::= { hh3cevtModuleSwitchType 1302 } -- 16-Port 1000BASE-X Gigabit Ethernet Optical(SFP,LC) And 8-Port 10/100/1000BASE-T RJ45/1000BASE-X SFP Combo Interface Board
hh3cevtModuleSw-LSQ1GT48SA8                 OBJECT IDENTIFIER ::= { hh3cevtModuleSwitchType 1303 } -- 48-Port 1000Base-T Gigabit Ethernet Interface Board(RJ45)
hh3cevtModuleSw-LSQ1GP48SA8                 OBJECT IDENTIFIER ::= { hh3cevtModuleSwitchType 1304 } -- 48-Port 1000BASE-X Ethernet Optical Interface Board(SFP,LC)
hh3cevtModuleSw-LSQ1TGS4SC8                 OBJECT IDENTIFIER ::= { hh3cevtModuleSwitchType 1305 } -- 4-Port 10GBASE Ethernet SFP+ Optical Interface Board
hh3cevtModuleSw-LSQ1TGS8SC8                 OBJECT IDENTIFIER ::= { hh3cevtModuleSwitchType 1306 } -- 8-Port 10GBASE Ethernet SFP+ Optical Interface Board
hh3cevtModuleSw-LSU1GT24SE3                 OBJECT IDENTIFIER ::= { hh3cevtModuleSwitchType 1307 } -- 24-Port 1000BASE-T Ethernet Interface Board (RJ45)
hh3cevtModuleSw-LSU1GP12SE3                 OBJECT IDENTIFIER ::= { hh3cevtModuleSwitchType 1308 } -- 12-Port 1000BASE-X Ethernet Optical Interface Board(SFP,LC)
hh3cevtModuleSw-LSU1GP24SE3                 OBJECT IDENTIFIER ::= { hh3cevtModuleSwitchType 1309 } -- 24 Port 1000BASE-X Ethernet Optical Interface Board(SFP,LC)
hh3cevtModuleSw-LSU1T24XGSE3                OBJECT IDENTIFIER ::= { hh3cevtModuleSwitchType 1310 } -- 24-Port 1000BASE-T Gigabit Ethernet Interface(RJ45)+2-Port 10GBASE Ethernet Optical Interface Board(XFP,LC)
hh3cevtModuleSw-LSU1P24XGSE3                OBJECT IDENTIFIER ::= { hh3cevtModuleSwitchType 1311 } -- 24-Port 1000BASE-X Gigabit Ethernet Optical Interface(SFP,LC)+2-Port 10GBASE Ethernet Optical Interface Board(XFP,LC)
hh3cevtModuleSw-LSU1GP24TSE3                OBJECT IDENTIFIER ::= { hh3cevtModuleSwitchType 1312 } -- 16-Port 1000BASE-X Gigabit Ethernet Optical(SFP,LC) And 8-Port 10/100/1000BASE-T RJ45/1000BASE-X SFP Combo Interface Board
hh3cevtModuleSw-LSU1GT40PSE3                OBJECT IDENTIFIER ::= { hh3cevtModuleSwitchType 1313 } -- 40-Port 10/100/1000BASE-T Electrical(RJ45) And 8-Port 1000BASE-X Optical Ethernet Interface Board(SFP,LC),PoE
hh3cevtModuleSw-LSV1TGS24SA1                OBJECT IDENTIFIER ::= { hh3cevtModuleSwitchType 1314 } -- 24-Port 10G BASE Ethernet Optical Interface Board(SFP+)
hh3cevtModuleSw-LSVM1SRPA1                  OBJECT IDENTIFIER ::= { hh3cevtModuleSwitchType 1315 } -- Switching Fabric Module
hh3cevtModuleSw-LSVM1SRPC1                  OBJECT IDENTIFIER ::= { hh3cevtModuleSwitchType 1316 } -- Switching Fabric Module
hh3cevtModuleSw-LSX1FAB16S0                 OBJECT IDENTIFIER ::= { hh3cevtModuleSwitchType 1317 } -- Switch Fabric Board,For 16 Slots Chassis
hh3cevtModuleSw-LSU1WCME0                   OBJECT IDENTIFIER ::= { hh3cevtModuleSwitchType 1318 } -- Access Controller Service Board
hh3cevtModuleSw-EWPX1WCME0                  OBJECT IDENTIFIER ::= { hh3cevtModuleSwitchType 1319 } -- Access Controller Service Board
hh3cevtModuleSw-LSUM1TGS48SG0               OBJECT IDENTIFIER ::= { hh3cevtModuleSwitchType 1320 } -- 48-Port 10GBASE-R Ethernet SFP+ Optical Interface Board(SG)
hh3cevtModuleSw-LSUM1QGS12SG0               OBJECT IDENTIFIER ::= { hh3cevtModuleSwitchType 1321 } -- 12-Port 40GBASE-R Ethernet QSFP+ Optical Interface Board(SG)
hh3cevtModuleSw-LSUM1GP44TSEC0              OBJECT IDENTIFIER ::= { hh3cevtModuleSwitchType 1322 } -- 44-Port 1000BASE-R Ethernet SFP Optical Interface Board(EC)+4-Port 10GBASE-R Ethernet SFP+ Optical Interface Board(EC)
hh3cevtModuleSw-LSUM1TGS24EC0               OBJECT IDENTIFIER ::= { hh3cevtModuleSwitchType 1323 } -- 24-Port 10GBASE-R Ethernet SFP+ Optical Interface Board(EC)
hh3cevtModuleSw-LSUM1QGS6EC0                OBJECT IDENTIFIER ::= { hh3cevtModuleSwitchType 1324 } -- 6-Port 40GBASE-R Ethernet QSFP+ Optical Interface Board(EC)
hh3cevtModuleSw-LSUM1CGC2EC0                OBJECT IDENTIFIER ::= { hh3cevtModuleSwitchType 1325 } -- 2-Port 100GBASE-R Ethernet CFP Optical Interface Board(EC)
hh3cevtModuleSw-LSU1CGC2SE9                 OBJECT IDENTIFIER ::= { hh3cevtModuleSwitchType 1326 } -- 2 Port 100GBASE Ethernet Optical Interface Board(CFP)(SE)
hh3cevtModuleSw-LSXM1QGS24EX1               OBJECT IDENTIFIER ::= { hh3cevtModuleSwitchType 1327 } -- 24 Ports 40G BASE Ethernet Optical Interface Board(QSFP+,MPO),No Spell
hh3cevtModuleSw-LSXM1QGS24FB0               OBJECT IDENTIFIER ::= { hh3cevtModuleSwitchType 1328 } -- 24 Ports 40G BASE Ethernet Optical Interface Board(QSFP+,MPO),No Spell
hh3cevtModuleSw-LSVM1QGS12FX1               OBJECT IDENTIFIER ::= { hh3cevtModuleSwitchType 1329 } -- 12-Port 40G BASE Ethernet Optical Interface Module(QSFP+,MPO/LC)
hh3cevtModuleSw-LSVM1TGS24FX1               OBJECT IDENTIFIER ::= { hh3cevtModuleSwitchType 1330 } -- 24-Port 10G BASE Ethernet Optical Interface Module(SFP+,LC)
hh3cevtModuleSw-LSVM1QGS6C2FX1              OBJECT IDENTIFIER ::= { hh3cevtModuleSwitchType 1331 } -- 2-Port 100GBASE Ethernet Optical Interface(CXP,MPO)+6-Port 40GBASE Ethernet Optical Interface(QSFP+,MPO/LC)+4-Port 10G BASE Ethernet Optical Interface Module(SFP+,LC)
hh3cevtModuleSw-LSQM2GP44TSSC0              OBJECT IDENTIFIER ::= { hh3cevtModuleSwitchType 1332 } -- 44-Port GE Optical Interface(SFP,LC)+4-Port 10GE Optical Interface Board(SFP+,LC)(SC)
hh3cevtModuleSw-LSQM2GP44TSSC3              OBJECT IDENTIFIER ::= { hh3cevtModuleSwitchType 1333 } -- 44-Port GE Optical Interface(SFP,LC)+4-Port 10GE Optical Interface Board(SFP+,LC)(SC)
hh3cevtModuleSw-LSQM2GP24TSSC0              OBJECT IDENTIFIER ::= { hh3cevtModuleSwitchType 1334 } -- 24-Port GE Optical Interface(SFP,LC)+4-Port 10GE Optical Interface Board(SFP+,LC)(SC)
hh3cevtModuleSw-LSQM2GP24TSSC3              OBJECT IDENTIFIER ::= { hh3cevtModuleSwitchType 1335 } -- 24-Port GE Optical Interface(SFP,LC)+4-Port 10GE Optical Interface Board(SFP+,LC)(SC)
hh3cevtModuleSw-LSQM2GT24PTSSC0             OBJECT IDENTIFIER ::= { hh3cevtModuleSwitchType 1336 } -- 24-Port 1000Base-T Gigabit Ethernet Interface Board(RJ45)+20-Port GE Optical Interface(SFP,LC)+4-Port 10GE Optical Interface Board(SFP+,LC)(SC)
hh3cevtModuleSw-LSQM2GT24PTSSC3             OBJECT IDENTIFIER ::= { hh3cevtModuleSwitchType 1337 } -- 24-Port 1000Base-T Gigabit Ethernet Interface Board(RJ45)+20-Port GE Optical Interface(SFP,LC)+4-Port 10GE Optical Interface Board(SFP+,LC)(SC)
hh3cevtModuleSw-LSQM2GT24TSSC0              OBJECT IDENTIFIER ::= { hh3cevtModuleSwitchType 1338 } -- 24-Port 1000Base-T Gigabit Ethernet Interface Board(RJ45)+4-Port 10GE Optical Interface Board(SFP+,LC)(SC)
hh3cevtModuleSw-LSQM2GT24TSSC3              OBJECT IDENTIFIER ::= { hh3cevtModuleSwitchType 1339 } -- 24-Port 1000Base-T Gigabit Ethernet Interface Board(RJ45)+4-Port 10GE Optical Interface Board(SFP+,LC)(SC)
hh3cevtModuleSw-LSQM2GT48SC0                OBJECT IDENTIFIER ::= { hh3cevtModuleSwitchType 1340 } -- 48-Port 1000Base-T Gigabit Ethernet Interface Board(RJ45)(SC)
hh3cevtModuleSw-LSQM2GT48SC3                OBJECT IDENTIFIER ::= { hh3cevtModuleSwitchType 1341 } -- 48-Port 1000Base-T Gigabit Ethernet Interface Board(RJ45)(SC)
hh3cevtModuleSw-LSQM4GV48SC0                OBJECT IDENTIFIER ::= { hh3cevtModuleSwitchType 1342 } -- 48-Port 1000Base-T Gigabit Ethernet Interface Board(RJ45)(SC)-POE
hh3cevtModuleSw-LSQM4GV48SC3                OBJECT IDENTIFIER ::= { hh3cevtModuleSwitchType 1343 } -- 48-Port 1000Base-T Gigabit Ethernet Interface Board(RJ45)(SC)-POE
hh3cevtModuleSw-LSQM2TGS16SF0               OBJECT IDENTIFIER ::= { hh3cevtModuleSwitchType 1344 } -- 16-Port 10GE Optical Interface Board(SFP+,LC)(SF)
hh3cevtModuleSw-LSQM2TGS16SF3               OBJECT IDENTIFIER ::= { hh3cevtModuleSwitchType 1345 } -- 16-Port 10GE Optical Interface Board(SFP+,LC)(SF)
hh3cevtModuleSw-LSQM2MPUD0                  OBJECT IDENTIFIER ::= { hh3cevtModuleSwitchType 1346 } -- Supervisor Engine Board
hh3cevtModuleSw-LSQM2MPUD3                  OBJECT IDENTIFIER ::= { hh3cevtModuleSwitchType 1347 } -- Supervisor Engine Board
hh3cevtModuleSw-LSQM3MPUA0                  OBJECT IDENTIFIER ::= { hh3cevtModuleSwitchType 1348 } -- Supervisor Engine Board
hh3cevtModuleSw-LSQM3MPUA3                  OBJECT IDENTIFIER ::= { hh3cevtModuleSwitchType 1349 } -- Supervisor Engine Board
hh3cevtModuleSw-LSUM2GP44TSSE0              OBJECT IDENTIFIER ::= { hh3cevtModuleSwitchType 1350 } -- 44-Port GE Optical Interface(SFP,LC)+4-Port 10GE Optical Interface Board(SFP+,LC)(SE)
hh3cevtModuleSw-LSUM2GP44TSSC3              OBJECT IDENTIFIER ::= { hh3cevtModuleSwitchType 1351 } -- 44-Port GE Optical Interface(SFP,LC)+4-Port 10GE Optical Interface Board(SFP+,LC)(SC)
hh3cevtModuleSw-LSUM2GP24TSSE0              OBJECT IDENTIFIER ::= { hh3cevtModuleSwitchType 1352 } -- 24-Port GE Optical Interface(SFP,LC)+4-Port 10GE Optical Interface Board(SFP+,LC)(SE)
hh3cevtModuleSw-LSUM2GP24TSSC3              OBJECT IDENTIFIER ::= { hh3cevtModuleSwitchType 1353 } -- 24-Port GE Optical Interface(SFP,LC)+4-Port 10GE Optical Interface Board(SFP+,LC)(SC)
hh3cevtModuleSw-LSUM2GT24PTSSE0             OBJECT IDENTIFIER ::= { hh3cevtModuleSwitchType 1354 } -- 24-Port 1000Base-T Gigabit Ethernet Interface Board(RJ45)+20-Port GE Optical Interface(SFP,LC)+4-Port 10GE Optical Interface Board(SFP+,LC)(SE)
hh3cevtModuleSw-LSUM2GT24PTSSC3             OBJECT IDENTIFIER ::= { hh3cevtModuleSwitchType 1355 } -- 24-Port 1000Base-T Gigabit Ethernet Interface Board(RJ45)+20-Port GE Optical Interface(SFP,LC)+4-Port 10GE Optical Interface Board(SFP+,LC)(SC)
hh3cevtModuleSw-LSUM2GT24TSSE0              OBJECT IDENTIFIER ::= { hh3cevtModuleSwitchType 1356 } -- 24-Port 1000Base-T Gigabit Ethernet Interface Board(RJ45)+4-Port 10GE Optical Interface Board(SFP+,LC)(SE)
hh3cevtModuleSw-LSUM2GT24TSSC3              OBJECT IDENTIFIER ::= { hh3cevtModuleSwitchType 1357 } -- 24-Port 1000Base-T Gigabit Ethernet Interface Board(RJ45)+4-Port 10GE Optical Interface Board(SFP+,LC)(SC)
hh3cevtModuleSw-LSUM2GT48SE0                OBJECT IDENTIFIER ::= { hh3cevtModuleSwitchType 1358 } -- 48-Port 1000Base-T Gigabit Ethernet Interface Board(RJ45)(SE)
hh3cevtModuleSw-LSUM2GT48SC3                OBJECT IDENTIFIER ::= { hh3cevtModuleSwitchType 1359 } -- 48-Port 1000Base-T Gigabit Ethernet Interface Board(RJ45)(SC)
hh3cevtModuleSw-LSUM2GV48SE0                OBJECT IDENTIFIER ::= { hh3cevtModuleSwitchType 1360 } -- 48-Port 1000Base-T Gigabit Ethernet Interface Board(RJ45)(SE)-POE
hh3cevtModuleSw-LSUM2GV48SC3                OBJECT IDENTIFIER ::= { hh3cevtModuleSwitchType 1361 } -- 48-Port 1000Base-T Gigabit Ethernet Interface Board(RJ45)(SC)-POE
hh3cevtModuleSw-LSUM2TGS16SF0               OBJECT IDENTIFIER ::= { hh3cevtModuleSwitchType 1362 } -- 16-Port 10GE Optical Interface Board(SFP+,LC)(SF)
hh3cevtModuleSw-LSUM2TGS16SF3               OBJECT IDENTIFIER ::= { hh3cevtModuleSwitchType 1363 } -- 16-Port 10GE Optical Interface Board(SFP+,LC)(SF)
hh3cevtModuleSw-LSUM1MPU06B0                OBJECT IDENTIFIER ::= { hh3cevtModuleSwitchType 1364 } -- Supervisor Engine Board
hh3cevtModuleSw-LSUM1MPU06B3                OBJECT IDENTIFIER ::= { hh3cevtModuleSwitchType 1365 } -- Supervisor Engine Board
hh3cevtModuleSw-LSUM1MPU10C0                OBJECT IDENTIFIER ::= { hh3cevtModuleSwitchType 1366 } -- Supervisor Engine Board
hh3cevtModuleSw-LSUM1MPU10C3                OBJECT IDENTIFIER ::= { hh3cevtModuleSwitchType 1367 } -- Supervisor Engine Board
hh3cevtModuleSw-LSUM1FAB06C0                OBJECT IDENTIFIER ::= { hh3cevtModuleSwitchType 1368 } -- Switching Fabric Module
hh3cevtModuleSw-LSUM1FAB06C3                OBJECT IDENTIFIER ::= { hh3cevtModuleSwitchType 1369 } -- Switching Fabric Module
hh3cevtModuleSw-LSUM1FAB10C0                OBJECT IDENTIFIER ::= { hh3cevtModuleSwitchType 1370 } -- Switching Fabric Module
hh3cevtModuleSw-LSUM1FAB10C3                OBJECT IDENTIFIER ::= { hh3cevtModuleSwitchType 1371 } -- Switching Fabric Module
hh3cevtModuleSw-LSXM1SUPA1                  OBJECT IDENTIFIER ::= { hh3cevtModuleSwitchType 1372 } -- Supervisor Engine Module
hh3cevtModuleSw-LSXM1SFF16B1                OBJECT IDENTIFIER ::= { hh3cevtModuleSwitchType 1373 } -- Switch Fabric Board
hh3cevtModuleSw-LSUM1SPMAEC0                OBJECT IDENTIFIER ::= { hh3cevtModuleSwitchType 1374 } -- 4-Port Multiservice Processing Engine
hh3cevtModuleSw-LSXM1SUPB1                  OBJECT IDENTIFIER ::= { hh3cevtModuleSwitchType 1375 } -- Supervisor Engine Module
hh3cevtModuleSw-LSXM1SFF08B1                OBJECT IDENTIFIER ::= { hh3cevtModuleSwitchType 1376 } -- Switching Fabric Module,Type B(F1)
hh3cevtModuleSw-LSXM1TGS4GPEB1              OBJECT IDENTIFIER ::= { hh3cevtModuleSwitchType 1377 } -- 44-Port GE Optical Interface(SFP,LC)+4-Port 10GE Optical Interface Module(SFP+,LC)(EB)
hh3cevtModuleSw-LSXM1TGS16EA1               OBJECT IDENTIFIER ::= { hh3cevtModuleSwitchType 1378 } -- 16-Port 10GBASE Ethernet Optical Interface Module(SFP+,LC)(EA)
hh3cevtModuleSw-LSXM1TGS8EA1                OBJECT IDENTIFIER ::= { hh3cevtModuleSwitchType 1379 } -- 8-Port 10GBASE Ethernet Optical Interface Module(SFP+,LC)(EA)
hh3cevtModuleSw-LSXM1QGS36FX1               OBJECT IDENTIFIER ::= { hh3cevtModuleSwitchType 1380 } -- 36-Port 40GBASE Ethernet Optical Interface Module(QSFP+)(FX)
hh3cevtModuleSw-LSXM1SFF16C1                OBJECT IDENTIFIER ::= { hh3cevtModuleSwitchType 1381 } -- Switching Fabric Module
hh3cevtModuleSw-LSQM3MPUB0                  OBJECT IDENTIFIER ::= { hh3cevtModuleSwitchType 1382 } -- Supervisor Engine Board
hh3cevtModuleSw-LSQM3MPUB3                  OBJECT IDENTIFIER ::= { hh3cevtModuleSwitchType 1383 } -- Supervisor Engine Board
hh3cevtModuleSw-LSQM2MPUC0                  OBJECT IDENTIFIER ::= { hh3cevtModuleSwitchType 1384 } -- Supervisor Engine Board
hh3cevtModuleSw-LSQM2MPUC3                  OBJECT IDENTIFIER ::= { hh3cevtModuleSwitchType 1385 } -- Supervisor Engine Board
hh3cevtModuleSw-LST1FW3B1                   OBJECT IDENTIFIER ::= { hh3cevtModuleSwitchType 1386 } -- Firewall Board
hh3cevtModuleSw-LSX1NSCEA1                  OBJECT IDENTIFIER ::= { hh3cevtModuleSwitchType 1387 } -- NetStream Service Board
hh3cevtModuleSw-LSX1FWCEA1                  OBJECT IDENTIFIER ::= { hh3cevtModuleSwitchType 1388 } -- Firewall Service Board
hh3cevtModuleSw-LSXM1ADECEA1                OBJECT IDENTIFIER ::= { hh3cevtModuleSwitchType 1389 } -- Application Dilevery Engine Module,Domestic&Overseas Version
hh3cevtModuleSw-LSXM1SFF16A1                OBJECT IDENTIFIER ::= { hh3cevtModuleSwitchType 1390 } -- Switching Fabric Module
hh3cevtModuleSw-LSV1MPUA0                   OBJECT IDENTIFIER ::= { hh3cevtModuleSwitchType 1391 } -- Supervisor Engine Board
hh3cevtModuleSw-LSVM1SRPA0                  OBJECT IDENTIFIER ::= { hh3cevtModuleSwitchType 1392 } -- Switching Fabric Module
hh3cevtModuleSw-LSVM1SRPC0                  OBJECT IDENTIFIER ::= { hh3cevtModuleSwitchType 1393 } -- Switching Fabric Module
hh3cevtModuleSw-LSV1QGS12SA0                OBJECT IDENTIFIER ::= { hh3cevtModuleSwitchType 1394 } -- 12-Port 40G BASE Ethernet Optical Interface Board(QSFP+)
hh3cevtModuleSw-LSVM1QGS12FX0               OBJECT IDENTIFIER ::= { hh3cevtModuleSwitchType 1395 } -- 12-Port 40G BASE Ethernet Optical Interface Module(QSFP+,MPO/LC)
hh3cevtModuleSw-LSVM1TGS24FX0               OBJECT IDENTIFIER ::= { hh3cevtModuleSwitchType 1396 } -- 24-Port 10G BASE Ethernet Optical Interface Module(SFP+,LC)
hh3cevtModuleSw-LSVM1QGS6C2FX0              OBJECT IDENTIFIER ::= { hh3cevtModuleSwitchType 1397 } -- 2-Port 100GBASE Ethernet Optical Interface(CXP,MPO)+6-Port 40GBASE Ethernet Optical Interface(QSFP+,MPO/LC)+4-Port 10G BASE Ethernet Optical Interface Module(SFP+,LC)
hh3cevtModuleSw-LSQ2FWBSC0                  OBJECT IDENTIFIER ::= { hh3cevtModuleSwitchType 1398 } -- Gigabit Firewall Card, 4 Gigabit Port for Management
hh3cevtModuleSw-LSQM1SRP8X2QE0              OBJECT IDENTIFIER ::= { hh3cevtModuleSwitchType 1399 } -- Supervisor Engine Board With 8-Port 10GBASE Ethernet SFP+ Optical Interfaces+2-Port 40GBASE-R Ethernet QSFP+ Optical Interfaces

--
-- 1400 to 1599 reserved for switche RPU logical modules
--
hh3cevtModulesw-PEX-Common                  OBJECT IDENTIFIER ::= { hh3cevtModuleSwitchType 1400 } -- The general logical module type for PEX
hh3cevtModuleSw-CSPEX-1812X                 OBJECT IDENTIFIER ::= { hh3cevtModuleSwitchType 1401 } -- Service Processing Unit Module(1812X)
hh3cevtModuleSw-CSPEX-1612X                 OBJECT IDENTIFIER ::= { hh3cevtModuleSwitchType 1402 } -- Service Processing Unit Module(1612X)
hh3cevtModuleSw-CSPEX-1512X                 OBJECT IDENTIFIER ::= { hh3cevtModuleSwitchType 1403 } -- Service Processing Unit Module(1512X)
hh3cevtModuleSw-NIC-XP20L                   OBJECT IDENTIFIER ::= { hh3cevtModuleSwitchType 1404 } -- 20-port 10GBASE-R/W Ethernet Optical Interface Card Module(SFP+,LC)(NIC)
hh3cevtModuleSw-NIC-XP10L                   OBJECT IDENTIFIER ::= { hh3cevtModuleSwitchType 1405 } -- 10-port 10GBASE-R/W Ethernet Optical Interface Card Module(SFP+,LC)(NIC)
hh3cevtModuleSw-NIC-CC2L                    OBJECT IDENTIFIER ::= { hh3cevtModuleSwitchType 1406 } -- 2-port 100G Ethernet Optical Interface Card Module(CFP2,LC)(NIC)
hh3cevtModuleSw-NIC-CC1L                    OBJECT IDENTIFIER ::= { hh3cevtModuleSwitchType 1407 } -- 1-port 100G Ethernet Optical Interface Card Module(CFP2,LC)(NIC)
hh3cevtModuleSw-NIC-XP5L                    OBJECT IDENTIFIER ::= { hh3cevtModuleSwitchType 1408 } -- 5-port 10GBASE-R/W Ethernet Optical Interface Card Module(SFP+,LC)(NIC)
hh3cevtModuleSw-NIC-GP20L                   OBJECT IDENTIFIER ::= { hh3cevtModuleSwitchType 1409 } -- 20-port 1000BASE-X Ethernet Optical Interface Card Module(SFP,LC)(NIC)
hh3cevtModuleSw-NIC-GT20L                   OBJECT IDENTIFIER ::= { hh3cevtModuleSwitchType 1410 } -- 20-port 1000BASE-T Ethernet Copper Interface Card Module(RJ45)(NIC)
hh3cevtModuleSw-MIC-CQ1L                    OBJECT IDENTIFIER ::= { hh3cevtModuleSwitchType 1411 } -- 1-port 100G Ethernet Optical Interface Card Module(QSFP28,LC)
hh3cevtModuleSw-MIC-XP10CQ1L                OBJECT IDENTIFIER ::= { hh3cevtModuleSwitchType 1412 } -- 10-port 10GBASE-R/W Ethernet Optical Interface(SFP+,LC)+1-port 100G Ethernet Optical Interface Card Module(QSFP28,LC)
hh3cevtModuleSw-CSPEX-1502X                 OBJECT IDENTIFIER ::= { hh3cevtModuleSwitchType 1413 } -- Service Processing Unit(1502X)
hh3cevtModuleSw-EPC-CP4RX                   OBJECT IDENTIFIER ::= { hh3cevtModuleSwitchType 1414 } -- 4-port 100GBASE Ethernet Optical Line Processing Unit(CFP2)
hh3cevtModuleSw-EPC-CQ4LX                   OBJECT IDENTIFIER ::= { hh3cevtModuleSwitchType 1415 } -- 4-port 100GBASE Ethernet Optical Line Processing Unit(QSFP28)
hh3cevtModuleSw-MIC-XP4L1-E                 OBJECT IDENTIFIER ::= { hh3cevtModuleSwitchType 1416 } -- 4-port 10GBASE-R/W Ethernet Optical Interface Card 1(SFP+,LC)
hh3cevtModuleSw-MIC-CQ1L-E                  OBJECT IDENTIFIER ::= { hh3cevtModuleSwitchType 1417 } -- 1-port 100G Ethernet Optical Interface Card 1(QSFP28)
hh3cevtModuleSw-MIC-XP8L                    OBJECT IDENTIFIER ::= { hh3cevtModuleSwitchType 1418 } -- 8-port 10GBASE-R/W Ethernet Optical Interface Card (SFP+,LC)
hh3cevtModuleSw-IM-OAPX                     OBJECT IDENTIFIER ::= { hh3cevtModuleSwitchType 1419 } -- Universal Open Platform(IM-OAPX)
hh3cevtModuleSw-MIC-GP20L1                  OBJECT IDENTIFIER ::= { hh3cevtModuleSwitchType 1420 } -- 20-port 1000BASE-X Ethernet Optical Interface Card(SFP,LC)
hh3cevtModuleSw-CSPEX-1802X                 OBJECT IDENTIFIER ::= { hh3cevtModuleSwitchType 1421 } -- Service Processing Unit(1802X)
hh3cevtModuleSw-MIC-CQ2L                    OBJECT IDENTIFIER ::= { hh3cevtModuleSwitchType 1422 } -- 2-port 100G Ethernet Optical Interface Card(QSFP28,LC)
hh3cevtModuleSw-IMMSUX                      OBJECT IDENTIFIER ::= { hh3cevtModuleSwitchType 1423 } -- Universal Line Processing Unit(IM-MSUX)(China Telecom)
hh3cevtModuleSw-CSPEX-1104-E                OBJECT IDENTIFIER ::= { hh3cevtModuleSwitchType 1424 } -- Service Processing Unit(1104E)
hh3cevtModuleSw-IMSMUX                      OBJECT IDENTIFIER ::= { hh3cevtModuleSwitchType 1425 } -- Security Monitor Unit(IM-SMUX)
hh3cevtModuleSw-MIC-XP10L                   OBJECT IDENTIFIER ::= { hh3cevtModuleSwitchType 1426 } -- 10-port 10GBASE-R/W Ethernet Optical Interface Card(SFP+,LC)
hh3cevtModuleSw-RX-SRP1P3                   OBJECT IDENTIFIER ::= { hh3cevtModuleSwitchType 1427 } -- RX8800 Main Processing Unit(1P3)
hh3cevtModuleSw-RX-SFC-08T                  OBJECT IDENTIFIER ::= { hh3cevtModuleSwitchType 1428 } -- 1Tbps Fabric Module(08)
hh3cevtModuleSw-RX-SFC-16T                  OBJECT IDENTIFIER ::= { hh3cevtModuleSwitchType 1429 } -- 1Tbps Fabric Module(16)
hh3cevtModuleSw-RX-SPE100                   OBJECT IDENTIFIER ::= { hh3cevtModuleSwitchType 1430 } -- 100G Service Processing Unit(SPE100)
hh3cevtModuleSw-RX-SPE200                   OBJECT IDENTIFIER ::= { hh3cevtModuleSwitchType 1431 } -- 200G Service Processing Unit(SPE200)
hh3cevtModuleSw-RX-SPE400                   OBJECT IDENTIFIER ::= { hh3cevtModuleSwitchType 1432 } -- 400G Service Processing Unit(SPE400)
hh3cevtModuleSw-RX-NIC-GP20L                OBJECT IDENTIFIER ::= { hh3cevtModuleSwitchType 1433 } -- 20-port 1000BASE-X Ethernet Optical Interface Card(SFP,LC)(RX-NIC,SPE100)
hh3cevtModuleSw-RX-NIC-XP5L                 OBJECT IDENTIFIER ::= { hh3cevtModuleSwitchType 1434 } -- 5-port 10GBASE-R/W Ethernet Optical Interface Card(SFP+,LC)(RX-NIC,SPE100)
hh3cevtModuleSw-RX-NIC-XP10L                OBJECT IDENTIFIER ::= { hh3cevtModuleSwitchType 1435 } -- 10-port 10GBASE-R/W Ethernet Optical Interface Card(SFP+,LC)(RX-NIC,SPE200)
hh3cevtModuleSw-RX-NIC-CC1L                 OBJECT IDENTIFIER ::= { hh3cevtModuleSwitchType 1436 } -- 1-port 100G Ethernet Optical Interface Card(CFP2,LC)(RX-NIC,SPE200)
hh3cevtModuleSw-RX-NIC-CC2L                 OBJECT IDENTIFIER ::= { hh3cevtModuleSwitchType 1437 } -- 2-port 100G Ethernet Optical Interface Card(CFP2,LC)(RX-NIC,SPE400)
hh3cevtModuleSw-RX-NIC-XP20L                OBJECT IDENTIFIER ::= { hh3cevtModuleSwitchType 1438 } -- 20-port 10GBASE-R/W Ethernet Optical Interface Card(SFP+,LC)(RX-NIC,SPE400)
hh3cevtModuleSw-CSPC-GE24L-E                OBJECT IDENTIFIER ::= { hh3cevtModuleSwitchType 1439 } -- 24-port 1000BASE-X Ethernet Combo Interface Line Processing Unit(E Type)
hh3cevtModuleSw-CSPC-GP24GE8XP2L-E          OBJECT IDENTIFIER ::= { hh3cevtModuleSwitchType 1440 } -- 24-port 1000BASE-X Ethernet Optical Interface(SFP,LC)+ 8-port 1000BASE-X Ethernet Combo Interface+2-port 10GBASE-R/W Ethernet Optical Interface Line Processing Unit(SFP+,LC)(E Type)
hh3cevtModuleSw-CSPC-GE16XP4L-E             OBJECT IDENTIFIER ::= { hh3cevtModuleSwitchType 1441 } -- 16-port 1000BASE-X Ethernet Combo Interface+4-port 10GBASE-R/W Ethernet Optical Interface Line Processing Unit(SFP+,LC)(E Type)
hh3cevtModuleSw-CSFC-04E                    OBJECT IDENTIFIER ::= { hh3cevtModuleSwitchType 1442 } -- CR16006-F Fabric Module(E Type)
hh3cevtModuleSw-SFC-04E                     OBJECT IDENTIFIER ::= { hh3cevtModuleSwitchType 1443 } -- SR8804-X Fabric Module(E Type)
hh3cevtModuleSw-IM-MSUX-II                  OBJECT IDENTIFIER ::= { hh3cevtModuleSwitchType 1444 } -- Universal Line Processing Unit(IM-MSUX-II)
hh3cevtModuleSw-RX-NIC-YGS4L                OBJECT IDENTIFIER ::= { hh3cevtModuleSwitchType 1445 } -- 4-port 25G Ethernet Optical Interface Card(SFP28,LC)
hh3cevtModuleSw-RX-NIC-CQ2LF                OBJECT IDENTIFIER ::= { hh3cevtModuleSwitchType 1446 } -- 2-port 100G Flexible Ethernet Optical Interface Card(QSFP28,LC)
hh3cevtModuleSw-RX-SRP1Q3                   OBJECT IDENTIFIER ::= { hh3cevtModuleSwitchType 1447 } -- RX8800 Main Processing Unit(1Q3)
hh3cevtModuleSw-RX-SFC-08E                  OBJECT IDENTIFIER ::= { hh3cevtModuleSwitchType 1448 } -- 400Gbps Fabric Module(08)
hh3cevtModuleSw-RX-SFC-16E                  OBJECT IDENTIFIER ::= { hh3cevtModuleSwitchType 1449 } -- 400Gbps Fabric Module(16)
hh3cevtModuleSw-RX-NIC-LGQ2L                OBJECT IDENTIFIER ::= { hh3cevtModuleSwitchType 1450 } -- 2-port 50G Ethernet Optical Interface Card(QSFP28,LC)(RX-NIC)

hh3cevtModuleSw-RX-NIC-CQ1LF                OBJECT IDENTIFIER ::= { hh3cevtModuleSwitchType 1452 } -- 1-port 100G Flexible Ethernet Optical Interface Card(QSFP28,LC)(RX-NIC)
hh3cevtModuleSw-IM-SFMX                     OBJECT IDENTIFIER ::= { hh3cevtModuleSwitchType 1453 } -- Network Data Encryption Service Processing Unit(IM-SFMX)
hh3cevtModuleSw-MIC-SM                      OBJECT IDENTIFIER ::= { hh3cevtModuleSwitchType 1454 } -- Network Data Encryption Interface Card(MIC-SM)
hh3cevtModuleSw-RX-NIC-CQ1L                 OBJECT IDENTIFIER ::= { hh3cevtModuleSwitchType 1455 } -- 1-port 100G Ethernet Optical Interface Card(QSFP28,LC)(RX-NIC)
hh3cevtModuleSw-RX-NIC-CQ2L                 OBJECT IDENTIFIER ::= { hh3cevtModuleSwitchType 1456 } -- 2-port 100G Ethernet Optical Interface Card(QSFP28,LC)(RX-NIC)
hh3cevtModuleSw-NIC-GP24L                   OBJECT IDENTIFIER ::= { hh3cevtModuleSwitchType 1457 } -- 24-port 1000BASE-X Ethernet Optical Interface Card(SFP,LC)(NIC)
hh3cevtModuleSw-NIC-CQ1L                    OBJECT IDENTIFIER ::= { hh3cevtModuleSwitchType 1458 } -- 1-port 100G Ethernet Optical Interface Card(QSFP28,LC)(NIC)
hh3cevtModuleSw-NIC-CQ2L                    OBJECT IDENTIFIER ::= { hh3cevtModuleSwitchType 1459 } -- 2-port 100G Ethernet Optical Interface Card(QSFP28,LC)(NIC)
-- 1600 to 1799 reserved for secondary switches part III
--
hh3cevtModuleSw-LSUM2GP44TSSE9              OBJECT IDENTIFIER ::= { hh3cevtModuleSwitchType 1600 } -- 44-Port GE Optical Interface(SFP,LC)+4-Port 10GE Optical Interface Board(SFP+,LC)(SE)
hh3cevtModuleSw-LSUM2GP24TSSE9              OBJECT IDENTIFIER ::= { hh3cevtModuleSwitchType 1601 } -- 24-Port GE Optical Interface(SFP,LC)+4-Port 10GE Optical Interface Board(SFP+,LC)(SE)
hh3cevtModuleSw-LSUM2GT24TSSE9              OBJECT IDENTIFIER ::= { hh3cevtModuleSwitchType 1602 } -- 24-Port 1000Base-T Gigabit Ethernet Interface Board(RJ45)+4-Port 10GE Optical Interface Board(SFP+,LC)(SE)
hh3cevtModuleSw-LSUM2GT48SE9                OBJECT IDENTIFIER ::= { hh3cevtModuleSwitchType 1603 } -- 48-Port 1000Base-T Gigabit Ethernet Interface Board(RJ45)(SE)
hh3cevtModuleSw-LSUM1SUPD0                  OBJECT IDENTIFIER ::= { hh3cevtModuleSwitchType 1604 } -- Supervisor Engine Board
hh3cevtModuleSw-LSUM1SUPD9                  OBJECT IDENTIFIER ::= { hh3cevtModuleSwitchType 1605 } -- Supervisor Engine Board
hh3cevtModuleSw-LSXM1TGT48FX0               OBJECT IDENTIFIER ::= { hh3cevtModuleSwitchType 1606 } -- 48-Port 10GBASE-T Ethernet Electrical Interface Module(RJ45)(FX)
hh3cevtModuleSw-LSXM1TGS48FX0               OBJECT IDENTIFIER ::= { hh3cevtModuleSwitchType 1607 } -- 48-Port 10GBASE-T Ethernet Electrical Interface Module(RJ45)(FX)
hh3cevtModuleSw-LSXM1TGS48FE0               OBJECT IDENTIFIER ::= { hh3cevtModuleSwitchType 1608 } -- 48-Port 10GBASE Ethernet Optical Interface Module(SFP+,LC)(FE)
hh3cevtModuleSw-LSXM1QGS36FX0               OBJECT IDENTIFIER ::= { hh3cevtModuleSwitchType 1609 } -- 36-Port 40GBASE Ethernet Optical Interface Module(QSFP+)(FX)
hh3cevtModuleSw-LSXM1QGS24FX0               OBJECT IDENTIFIER ::= { hh3cevtModuleSwitchType 1610 } -- 24-Port 40GBASE Ethernet Optical Interface Module(QSFP+)(FX)
hh3cevtModuleSw-LSXM1QGS24FE0               OBJECT IDENTIFIER ::= { hh3cevtModuleSwitchType 1611 } -- 24-Port 40GBASE Ethernet Optical Interface Module(QSFP+)(FE)
hh3cevtModuleSw-LSXM1CGX8FX0                OBJECT IDENTIFIER ::= { hh3cevtModuleSwitchType 1612 } -- 8-Port 100GBASE Ethernet Optical Interface Module(CXP)(FX)
hh3cevtModuleSw-LSXM1CGP12FX0               OBJECT IDENTIFIER ::= { hh3cevtModuleSwitchType 1613 } -- 12-Port 100GBASE Ethernet Optical Interface Module(CFP2)(FX)
hh3cevtModuleSw-LSXM1SUPB0                  OBJECT IDENTIFIER ::= { hh3cevtModuleSwitchType 1614 } -- Supervisor Engine Module
hh3cevtModuleSw-LSXM1SFF16C0                OBJECT IDENTIFIER ::= { hh3cevtModuleSwitchType 1615 } -- Switching Fabric Module,Type F(Class C)
hh3cevtModuleSw-LSXM1SFF16A0                OBJECT IDENTIFIER ::= { hh3cevtModuleSwitchType 1616 } -- Switching Fabric Module,Type F(Class A)
hh3cevtModuleSw-LSXM1SFF08B0                OBJECT IDENTIFIER ::= { hh3cevtModuleSwitchType 1617 } -- Switching Fabric Module,Type F(Class B)
hh3cevtModuleSw-LSQM6GV48SC0                OBJECT IDENTIFIER ::= { hh3cevtModuleSwitchType 1618 } -- 48-Port 10/100/1000BASE-T Ethernet Interface Module(RJ45),Upgradeable to PoE
hh3cevtModuleSw-LSXM1SUP04B1                OBJECT IDENTIFIER ::= { hh3cevtModuleSwitchType 1619 } -- Supervisor Engine Module
hh3cevtModuleSw-LSXM1SFF04B1                OBJECT IDENTIFIER ::= { hh3cevtModuleSwitchType 1620 } -- Switching Fabric Module,Type F(Class B)
hh3cevtModuleSw-LSXM1SUP04B0                OBJECT IDENTIFIER ::= { hh3cevtModuleSwitchType 1621 } -- Supervisor Engine Module
hh3cevtModuleSw-LSXM1SFF04B0                OBJECT IDENTIFIER ::= { hh3cevtModuleSwitchType 1622 } -- Switching Fabric Module,Type F(Class B)
hh3cevtModuleSw-LSU1ADECEA0                 OBJECT IDENTIFIER ::= { hh3cevtModuleSwitchType 1623 } -- Application Dilevery Engine Module,Domestic&Overseas Version
hh3cevtModuleSw-LSU1NSCEA0                  OBJECT IDENTIFIER ::= { hh3cevtModuleSwitchType 1624 } -- NetStream Service Board
hh3cevtModuleSw-LSU3FWCEA0                  OBJECT IDENTIFIER ::= { hh3cevtModuleSwitchType 1625 } -- Firewall Service Board
hh3cevtModuleSw-LSXM1MPU06B3                OBJECT IDENTIFIER ::= { hh3cevtModuleSwitchType 1626 } -- Supervisor Engine Board
hh3cevtModuleSw-LSXM1MPU10C3                OBJECT IDENTIFIER ::= { hh3cevtModuleSwitchType 1627 } -- Supervisor Engine Board
hh3cevtModuleSw-LSXM1SUPD3                  OBJECT IDENTIFIER ::= { hh3cevtModuleSwitchType 1628 } -- Supervisor Engine Board
hh3cevtModuleSw-LSXM1FAB06C3                OBJECT IDENTIFIER ::= { hh3cevtModuleSwitchType 1629 } -- Switching Fabric Module
hh3cevtModuleSw-LSXM1FAB10C3                OBJECT IDENTIFIER ::= { hh3cevtModuleSwitchType 1630 } -- Switching Fabric Module
hh3cevtModuleSw-LSXM1FAB12D3                OBJECT IDENTIFIER ::= { hh3cevtModuleSwitchType 1631 } -- Switching Fabric Module
hh3cevtModuleSw-LSXM1FAB04D3                OBJECT IDENTIFIER ::= { hh3cevtModuleSwitchType 1632 } -- Switching Fabric Module
hh3cevtModuleSw-LSXM1FAB08D3                OBJECT IDENTIFIER ::= { hh3cevtModuleSwitchType 1633 } -- Switching Fabric Module
hh3cevtModuleSw-LSXM1GP44TSSE3              OBJECT IDENTIFIER ::= { hh3cevtModuleSwitchType 1634 } -- 44-Port GE Optical Interface(SFP,LC)+4-Port 10GE Optical Interface Board(SFP+,LC)(SE)
hh3cevtModuleSw-LSXM1GP24TSSE3              OBJECT IDENTIFIER ::= { hh3cevtModuleSwitchType 1635 } -- 24-Port GE Optical Interface(SFP,LC)+4-Port 10GE Optical Interface Board(SFP+,LC)(SE)
hh3cevtModuleSw-LSXM1GT24PTSSE3             OBJECT IDENTIFIER ::= { hh3cevtModuleSwitchType 1636 } -- 24-Port 1000Base-T Gigabit Ethernet Interface Board(RJ45)+20-Port GE Optical Interface(SFP,LC)+4-Port 10GE Optical Interface Board(SFP+,LC)(SE)
hh3cevtModuleSw-LSXM1GT48SE3                OBJECT IDENTIFIER ::= { hh3cevtModuleSwitchType 1637 } -- 48-Port 1000Base-T Gigabit Ethernet Interface Board(RJ45)(SE)
hh3cevtModuleSw-LSXM1TGS24EC3               OBJECT IDENTIFIER ::= { hh3cevtModuleSwitchType 1638 } -- 24-Port 10GBASE-R Ethernet SFP+ Optical Interface Board(EC)
hh3cevtModuleSw-LSXM1CGC2EC3                OBJECT IDENTIFIER ::= { hh3cevtModuleSwitchType 1639 } -- 2-Port 100GBASE-R Ethernet CFP Optical Interface Board(EC)
hh3cevtModuleSw-LSXM1TGT24SF3               OBJECT IDENTIFIER ::= { hh3cevtModuleSwitchType 1640 } -- 24-Port 10GBASE-T Ethernet Electrical Interface Board(RJ45)(SF)
hh3cevtModuleSw-LSXM1TGS16SF3               OBJECT IDENTIFIER ::= { hh3cevtModuleSwitchType 1641 } -- 16-Port 10GE Optical Interface Board(SFP+,LC)(SF)
hh3cevtModuleSw-LSXM1QGS12SG3               OBJECT IDENTIFIER ::= { hh3cevtModuleSwitchType 1642 } -- 12-Port 40GBASE-R Ethernet QSFP+ Optical Interface Board(SG)
hh3cevtModuleSw-LSXM1TGS48SG3               OBJECT IDENTIFIER ::= { hh3cevtModuleSwitchType 1643 } -- 48-Port 10GBASE-R Ethernet SFP+ Optical Interface Board(SG)
hh3cevtModuleSw-LSQM1FAB04B3                OBJECT IDENTIFIER ::= { hh3cevtModuleSwitchType 1644 } -- Switching Fabric Module
hh3cevtModuleSw-LSQM1FAB08B3                OBJECT IDENTIFIER ::= { hh3cevtModuleSwitchType 1645 } -- Switching Fabric Module
hh3cevtModuleSw-LSQM1FAB12B3                OBJECT IDENTIFIER ::= { hh3cevtModuleSwitchType 1646 } -- Switching Fabric Module
hh3cevtModuleSw-LSXM1SFF08A0                OBJECT IDENTIFIER ::= { hh3cevtModuleSwitchType 1647 } -- Switching Fabric Board
hh3cevtModuleSw-LSXM1SFF08A1                OBJECT IDENTIFIER ::= { hh3cevtModuleSwitchType 1648 } -- Switching Fabric Board
hh3cevtModuleSw-LSXM1FWDF1                  OBJECT IDENTIFIER ::= { hh3cevtModuleSwitchType 1649 } -- FW IV Next Generation Firewall Module
hh3cevtModuleSw-LSQM1PT8TSSC0               OBJECT IDENTIFIER ::= { hh3cevtModuleSwitchType 1650 } -- 8-Port 1G EPON OLT Optical Interface(SFP,SC)+2-Port 10GE Optical Interface Board(SFP+,LC)(SC)
hh3cevtModuleSw-LSQM1PT24TSSC0              OBJECT IDENTIFIER ::= { hh3cevtModuleSwitchType 1651 } -- 24-Port 1G EPON OLT Optical Interface(SFP,SC)+2-Port 10GE Optical Interface Board(SFP+,LC)(SC)
hh3cevtModuleSw-LSQM1TGS12EC0               OBJECT IDENTIFIER ::= { hh3cevtModuleSwitchType 1652 } -- 12-Port 10GBASE-R Ethernet SFP+ Optical Interface Board(EC)
hh3cevtModuleSw-LSX1M1CGQ32TB1              OBJECT IDENTIFIER ::= { hh3cevtModuleSwitchType 1653 } -- 32-Port 100GBASE Ethernet Optical Interface Board(QSFP28),Monolithic,LF
hh3cevtModuleSw-LSX1M1CGQ48TB1              OBJECT IDENTIFIER ::= { hh3cevtModuleSwitchType 1654 } -- 48-Port 100GBASE Ethernet Optical Interface Board(QSFP28),Monolithic
hh3cevtModuleSw-LSXM1QGS48TB1               OBJECT IDENTIFIER ::= { hh3cevtModuleSwitchType 1655 } -- 48-Port 40GBASE Ethernet Optical Interface Board(QSFP+),Monolithic
hh3cevtModuleSw-LSXM1SRT08E1                OBJECT IDENTIFIER ::= { hh3cevtModuleSwitchType 1656 } -- Switch Fabric Board
hh3cevtModuleSw-LSXM1SRT16E1                OBJECT IDENTIFIER ::= { hh3cevtModuleSwitchType 1657 } -- Switch Fabric Board
hh3cevtModuleSw-LSXM1SRT02E1                OBJECT IDENTIFIER ::= { hh3cevtModuleSwitchType 1658 } -- Switch Fabric Board
hh3cevtModuleSw-LSXM1SUP02B1                OBJECT IDENTIFIER ::= { hh3cevtModuleSwitchType 1659 } -- Supervisor Engine Module
hh3cevtModuleSw-LSUM1SUPC0                  OBJECT IDENTIFIER ::= { hh3cevtModuleSwitchType 1660 } -- Supervisor Engine Board
hh3cevtModuleSw-LSUM1SUPC3                  OBJECT IDENTIFIER ::= { hh3cevtModuleSwitchType 1661 } -- Supervisor Engine Board
hh3cevtModuleSw-LSXM1SUPC3                  OBJECT IDENTIFIER ::= { hh3cevtModuleSwitchType 1662 } -- Supervisor Engine Board
hh3cevtModuleSw-LSQM1GP44TSSE0              OBJECT IDENTIFIER ::= { hh3cevtModuleSwitchType 1663 } -- 44-Port GE Optical Interface(SFP,LC)+4-Port 10GE Optical Interface Board(SFP+,LC)(SC)
hh3cevtModuleSw-LSQM1GP24TSSE0              OBJECT IDENTIFIER ::= { hh3cevtModuleSwitchType 1664 } -- 24-Port GE Optical Interface(SFP,LC)+4-Port 10GE Optical Interface Board(SFP+,LC)(SC)
hh3cevtModuleSw-LSQM1GT48SE0                OBJECT IDENTIFIER ::= { hh3cevtModuleSwitchType 1665 } -- 48-Port 1000Base-T Gigabit Ethernet Interface Board(RJ45)(SC)
hh3cevtModuleSw-LSQM1GV48SE0                OBJECT IDENTIFIER ::= { hh3cevtModuleSwitchType 1666 } -- 48-Port 1000Base-T Gigabit Ethernet Interface Board(RJ45)(SC)-POE
hh3cevtModuleSw-LSXM1QGS12FX0               OBJECT IDENTIFIER ::= { hh3cevtModuleSwitchType 1667 } -- 12-Port 40GBASE Ethernet Optical Interface Module(QSFP+)(FX)
hh3cevtModuleSw-LSXM3QGS24FE1               OBJECT IDENTIFIER ::= { hh3cevtModuleSwitchType 1668 } -- 24-Port 40GBASE Ethernet Optical Interface Module(QSFP+)(FE)
hh3cevtModuleSw-LSXM3QGS24FX1               OBJECT IDENTIFIER ::= { hh3cevtModuleSwitchType 1669 } -- 24-Port 40GBASE Ethernet Optical Interface Module(QSFP+)(FX)
hh3cevtModuleSw-LSXM3QGS36FX1               OBJECT IDENTIFIER ::= { hh3cevtModuleSwitchType 1670 } -- 36-Port 40GBASE Ethernet Optical Interface Module(QSFP+)(FX)
hh3cevtModuleSw-LSXM3TGS48FE1               OBJECT IDENTIFIER ::= { hh3cevtModuleSwitchType 1671 } -- 48-Port 10GBASE Ethernet Optical Interface Module(SFP+,LC)(FX)
hh3cevtModuleSw-LSXM3TGS48FX1               OBJECT IDENTIFIER ::= { hh3cevtModuleSwitchType 1672 } -- 48-Port 10GBASE Ethernet Optical Interface Module(SFP+,LC)(FX)
hh3cevtModuleSw-LSXM2TGS48FX1               OBJECT IDENTIFIER ::= { hh3cevtModuleSwitchType 1673 } -- 48-Port 10GBASE Ethernet Optical Interface Module(SFP+,LC)(FX)
hh3cevtModuleSw-LSQM1MPU06B0                OBJECT IDENTIFIER ::= { hh3cevtModuleSwitchType 1674 } -- Supervisor Engine Board
hh3cevtModuleSw-LSQM1MPU10C0                OBJECT IDENTIFIER ::= { hh3cevtModuleSwitchType 1675 } -- Supervisor Engine Board
hh3cevtModuleSw-LSQM1FAB06C0                OBJECT IDENTIFIER ::= { hh3cevtModuleSwitchType 1676 } -- Switching Fabric Module
hh3cevtModuleSw-LSQM1FAB10C0                OBJECT IDENTIFIER ::= { hh3cevtModuleSwitchType 1677 } -- Switching Fabric Module
hh3cevtModuleSw-LSQM1QGS12SG0               OBJECT IDENTIFIER ::= { hh3cevtModuleSwitchType 1678 } -- 12-Port 40GBASE-R Ethernet QSFP+ Optical Interface Board(SG)
hh3cevtModuleSw-LSQM1TGS48SG0               OBJECT IDENTIFIER ::= { hh3cevtModuleSwitchType 1679 } -- 48-Port 10GBASE-R Ethernet SFP+ Optical Interface Board(SG)
hh3cevtModuleSw-LSQM1TGT24SF0               OBJECT IDENTIFIER ::= { hh3cevtModuleSwitchType 1680 } -- 24-Port 10GBASE-T Ethernet Electrical Interface Board(RJ45)(SF)
hh3cevtModuleSw-LSQM1QGS8A0                 OBJECT IDENTIFIER ::= { hh3cevtModuleSwitchType 1681 } -- 8-Port QSFP+ Module
hh3cevtModuleSw-LSQM1TGS24QSM0              OBJECT IDENTIFIER ::= { hh3cevtModuleSwitchType 1682 } -- 24-Port SFP+ and 2-Port QSFP+ Module
hh3cevtModuleSw-LSQM1TGT24QSM0              OBJECT IDENTIFIER ::= { hh3cevtModuleSwitchType 1683 } -- 24-Port 10G BASE-T and 2-Port QSFP+ Module
hh3cevtModuleSw-LSQM1TGS24QSA0              OBJECT IDENTIFIER ::= { hh3cevtModuleSwitchType 1684 } -- 24-Port SFP+ and 2-Port QSFP+ Module
hh3cevtModuleSw-LSUM1FWCEAB0                OBJECT IDENTIFIER ::= { hh3cevtModuleSwitchType 1685 } -- Firewall Board
hh3cevtModuleSw-LSQM2GP24TSSA0              OBJECT IDENTIFIER ::= { hh3cevtModuleSwitchType 1686 } -- 24-Port GE Optical Interface(SFP,LC)+4-Port 10GE Optical Interface Board(SFP+,LC)(SA)
hh3cevtModuleSw-LSQM2GT48SA0                OBJECT IDENTIFIER ::= { hh3cevtModuleSwitchType 1687 } -- 48-Port 1000Base-T Gigabit Ethernet Interface Board(RJ45)(SA)
hh3cevtModuleSw-LSQM2GP48SA0                OBJECT IDENTIFIER ::= { hh3cevtModuleSwitchType 1688 } -- 48-Port 1000BASE-X Ethernet Optical Interface Board(SFP,LC)(SA)
hh3cevtModuleSw-LSQM2GP24TSSA3              OBJECT IDENTIFIER ::= { hh3cevtModuleSwitchType 1689 } -- 24-Port GE Optical Interface(SFP,LC)+4-Port 10GE Optical Interface Board(SFP+,LC)(SA)
hh3cevtModuleSw-LSQM2GT48SA3                OBJECT IDENTIFIER ::= { hh3cevtModuleSwitchType 1690 } -- 48-Port 1000Base-T Gigabit Ethernet Interface Board(RJ45)(SA)
hh3cevtModuleSw-LSQM2GP48SA3                OBJECT IDENTIFIER ::= { hh3cevtModuleSwitchType 1691 } -- 48-Port 1000BASE-X Ethernet Optical Interface Board(SFP,LC)(SA)
hh3cevtModuleSw-LSUM2GP24TSSA0              OBJECT IDENTIFIER ::= { hh3cevtModuleSwitchType 1692 } -- 24-Port GE Optical Interface(SFP,LC)+4-Port 10GE Optical Interface Board(SFP+,LC)(SA)
hh3cevtModuleSw-LSUM2GT48SA0                OBJECT IDENTIFIER ::= { hh3cevtModuleSwitchType 1693 } -- 48-Port 1000Base-T Gigabit Ethernet Interface Board(RJ45)(SA)
hh3cevtModuleSw-LSUM2GP48SA0                OBJECT IDENTIFIER ::= { hh3cevtModuleSwitchType 1694 } -- 48-Port 1000BASE-X Ethernet Optical Interface Board(SFP,LC)(SA)
hh3cevtModuleSw-LSXM1SUPT1                  OBJECT IDENTIFIER ::= { hh3cevtModuleSwitchType 1695 } -- Supervisor Engine Module
hh3cevtModuleSw-LSXM1SUP02T1                OBJECT IDENTIFIER ::= { hh3cevtModuleSwitchType 1696 } -- Supervisor Engine Module
hh3cevtModuleSw-LSXM1SFF16B0                OBJECT IDENTIFIER ::= { hh3cevtModuleSwitchType 1697 } -- Switch Fabric Board
hh3cevtModuleSw-LSXM4TGS48FX1               OBJECT IDENTIFIER ::= { hh3cevtModuleSwitchType 1698 } -- 48-Port 10GBASE Ethernet Optical Interface Module(SFP+,LC)(FX)
hh3cevtModuleSw-LSXM4QGS24FX1               OBJECT IDENTIFIER ::= { hh3cevtModuleSwitchType 1699 } -- 24-Port 40GBASE Ethernet Optical Interface Module(QSFP+)(FX)
hh3cevtModuleSw-LSXM1TGS48FD1               OBJECT IDENTIFIER ::= { hh3cevtModuleSwitchType 1700 } -- 48-Port 10GBASE Ethernet Optical Interface Module(SFP+,LC)(FD)
hh3cevtModuleSw-LSXM1QGS24FD1               OBJECT IDENTIFIER ::= { hh3cevtModuleSwitchType 1701 } -- 24-Port 40GBASE Ethernet Optical Interface Module(QSFP+)(FD)
hh3cevtModuleSw-LSXM2QGS24FX1               OBJECT IDENTIFIER ::= { hh3cevtModuleSwitchType 1702 } -- 24-Port 40GBASE Ethernet Optical Interface Module(QSFP+)(FX)
hh3cevtModuleSw-LSXM1TGS48FD0               OBJECT IDENTIFIER ::= { hh3cevtModuleSwitchType 1703 } -- 48-Port 10GBASE Ethernet Optical Interface Module(SFP+,LC)
hh3cevtModuleSw-LSXM1QGS24FD0               OBJECT IDENTIFIER ::= { hh3cevtModuleSwitchType 1704 } -- 24-Port 40GBASE Ethernet Optical Interface Module(QSFP+)(FD)
hh3cevtModuleSw-LSXM2TGS48FX0               OBJECT IDENTIFIER ::= { hh3cevtModuleSwitchType 1705 } -- 48-Port 10GBASE Ethernet Optical Interface Module(SFP+,LC)(FX)
hh3cevtModuleSw-LSXM2QGS24FX0               OBJECT IDENTIFIER ::= { hh3cevtModuleSwitchType 1706 } -- 24-Port 40GBASE Ethernet Optical Interface Module(QSFP+)(FX)
hh3cevtModuleSw-LSXM4TGS48FX0               OBJECT IDENTIFIER ::= { hh3cevtModuleSwitchType 1707 } -- 48-Port 10GBASE Ethernet Optical Interface Module(SFP+,LC)(FX)
hh3cevtModuleSw-LSXM4QGS24FX0               OBJECT IDENTIFIER ::= { hh3cevtModuleSwitchType 1708 } -- 24-Port 40GBASE Ethernet Optical Interface Module(QSFP+)(FX)
hh3cevtModuleSw-LSXM1TGW48FX1               OBJECT IDENTIFIER ::= { hh3cevtModuleSwitchType 1709 } -- 48-Port 10GBASE Ethernet WAN Optical Interface Module(SFP+,LC)(FX)
hh3cevtModuleSw-LSUM1MPU10A0                OBJECT IDENTIFIER ::= { hh3cevtModuleSwitchType 1710 } -- Supervisor Engine Board
hh3cevtModuleSw-LSUM1FAB10A0                OBJECT IDENTIFIER ::= { hh3cevtModuleSwitchType 1711 } -- Switching Fabric Module
hh3cevtModuleSw-LSUM2TGS32QSSG0             OBJECT IDENTIFIER ::= { hh3cevtModuleSwitchType 1712 } -- 32-Port 10GBASE-R Ethernet Optical Interface(SFP+,LC)+4-Port 40GBASE-R Ethernet Optical Interface Board(QSFP+,LC)(SG)
hh3cevtModuleSw-LSUM2QGS12SG0               OBJECT IDENTIFIER ::= { hh3cevtModuleSwitchType 1713 } -- 12-Port 40GBASE-R Ethernet QSFP+ Optical Interface Board(SG)
hh3cevtModuleSw-LSUM2TGS48SG0               OBJECT IDENTIFIER ::= { hh3cevtModuleSwitchType 1714 } -- 48-Port 10GBASE-R Ethernet SFP+ Optical Interface Board(SG)
hh3cevtModuleSw-LSXM2QGS12SG3               OBJECT IDENTIFIER ::= { hh3cevtModuleSwitchType 1715 } -- 12-Port 40GBASE-R Ethernet QSFP+ Optical Interface Board(SG)
hh3cevtModuleSw-LSXM2TGS48SG3               OBJECT IDENTIFIER ::= { hh3cevtModuleSwitchType 1716 } -- 48-Port 10GBASE-R Ethernet SFP+ Optical Interface Board(SG)
hh3cevtModuleSw-LSUM1FWDEC0                 OBJECT IDENTIFIER ::= { hh3cevtModuleSwitchType 1717 } -- Firewall Service Board
hh3cevtModuleSw-LSQM1FWDSC0                 OBJECT IDENTIFIER ::= { hh3cevtModuleSwitchType 1718 } -- Firewall Service Board
hh3cevtModuleSw-LSQM1TGS48RSG0              OBJECT IDENTIFIER ::= { hh3cevtModuleSwitchType 1719 } -- 48-Port 10GBASE-R Ethernet SFP+ Optical Interface Board(SG)
hh3cevtModuleSw-LSQM2TGS48XSG0              OBJECT IDENTIFIER ::= { hh3cevtModuleSwitchType 1720 } -- 48-Port 10GBASE-R Ethernet SFP+ Optical Interface Board(SG)
hh3cevtModuleSw-LSQM2QGS12XSG0              OBJECT IDENTIFIER ::= { hh3cevtModuleSwitchType 1721 } -- 12-Port 40GBASE-R Ethernet QSFP+ Optical Interface Board(SG)
hh3cevtModuleSw-LSQM3GP44TSSC0              OBJECT IDENTIFIER ::= { hh3cevtModuleSwitchType 1722 } -- 44-Port GE Optical Interface(SFP,LC)+4-Port 10GE Optical Interface Board(SFP+,LC)(SC)
hh3cevtModuleSw-LSXM1CGQ36HB1               OBJECT IDENTIFIER ::= { hh3cevtModuleSwitchType 1723 } -- 36-Port 100GBASE Ethernet Optical Interface Module(QSFP28)(HB)
hh3cevtModuleSw-LSXM1CGQ36HC1               OBJECT IDENTIFIER ::= { hh3cevtModuleSwitchType 1724 } -- 36-Port 100GBASE Ethernet Optical Interface Module(QSFP28)(HC)
hh3cevtModuleSw-LSXM1CGQ18QGHB1             OBJECT IDENTIFIER ::= { hh3cevtModuleSwitchType 1725 } -- 18-Port 100GBASE (QSFP28) + 18-Port 40GBASE Ethernet Optical Interface Module (QSFP+)(HB)
hh3cevtModuleSw-LSXM1CGQ18QGHC1             OBJECT IDENTIFIER ::= { hh3cevtModuleSwitchType 1726 } -- 18-Port 100GBASE (QSFP28) + 18-Port 40GBASE Ethernet Optical Interface Module (QSFP+)(HC)
hh3cevtModuleSw-LSXM1QGS48HB1               OBJECT IDENTIFIER ::= { hh3cevtModuleSwitchType 1727 } -- 48-Port 40GBASE Ethernet Optical Interface Module(QSFP+)(HB)
hh3cevtModuleSw-LSXM1QGS48HC1               OBJECT IDENTIFIER ::= { hh3cevtModuleSwitchType 1728 } -- 48-Port 40GBASE Ethernet Optical Interface Module(QSFP+)(HC)
hh3cevtModuleSw-LSXM1TGS48C2HB1             OBJECT IDENTIFIER ::= { hh3cevtModuleSwitchType 1729 } -- 48-Port 10G BASE Ethernet Optical Interface(SFP+,LC)+2-Port 100GBASE Ethernet Optical Interface Module(QSFP28)(HB)
hh3cevtModuleSw-LSXM1SFH04D1                OBJECT IDENTIFIER ::= { hh3cevtModuleSwitchType 1730 } -- Switch Fabric Board,Type H(Class D)
hh3cevtModuleSw-LSXM1SFH08D1                OBJECT IDENTIFIER ::= { hh3cevtModuleSwitchType 1731 } -- Switch Fabric Board For S12508X-AF,Type D(F2)
hh3cevtModuleSw-LSXM1SFH12D1                OBJECT IDENTIFIER ::= { hh3cevtModuleSwitchType 1732 } -- Fabric Module,Type H(Class D)
hh3cevtModuleSw-LSXM1SFH16C1                OBJECT IDENTIFIER ::= { hh3cevtModuleSwitchType 1733 } -- Switch Fabric Board,Type H(Class C)
hh3cevtModuleSw-LSXM1GP48FD0                OBJECT IDENTIFIER ::= { hh3cevtModuleSwitchType 1737 } -- 48-Port 1000BASE-X Gigabit Ethernet Optical Interface Module(SFP,LC)(FD)
hh3cevtModuleSw-LSXM1GP48FD1                OBJECT IDENTIFIER ::= { hh3cevtModuleSwitchType 1738 } -- 48-Port 1000BASE-X Gigabit Ethernet Optical Interface Module(SFP,LC)(FD)
hh3cevtModuleSw-LSXM1GT48FD0                OBJECT IDENTIFIER ::= { hh3cevtModuleSwitchType 1739 } -- 48-Port 1000Base-T Gigabit Ethernet Interface Module(RJ45)(FD)
hh3cevtModuleSw-LSXM1GT48FD1                OBJECT IDENTIFIER ::= { hh3cevtModuleSwitchType 1740 } -- 48-Port 1000Base-T Gigabit Ethernet Interface Module(RJ45)(FD)
hh3cevtModuleSw-LSXM1FAB10B0                OBJECT IDENTIFIER ::= { hh3cevtModuleSwitchType 1741 } -- Switching Fabric Module
hh3cevtModuleSw-LSUM1MPU10A3                OBJECT IDENTIFIER ::= { hh3cevtModuleSwitchType 1742 } -- Supervisor Engine Board
hh3cevtModuleSw-LSUM1FAB10A3                OBJECT IDENTIFIER ::= { hh3cevtModuleSwitchType 1743 } -- Switching Fabric Module
hh3cevtModuleSw-LSQM1MPU10A0                OBJECT IDENTIFIER ::= { hh3cevtModuleSwitchType 1744 } -- Supervisor Engine Board
hh3cevtModuleSw-LSQM1FAB10A0                OBJECT IDENTIFIER ::= { hh3cevtModuleSwitchType 1745 } -- Switching Fabric Module
hh3cevtModuleSw-LSQM2TGS32QSXSG0            OBJECT IDENTIFIER ::= { hh3cevtModuleSwitchType 1746 } -- 32-Port 10GBASE-R Ethernet Optical Interface(SFP+,LC)+4-Port 40GBASE-R Ethernet Optical Interface Board(QSFP+,LC)(SG)
hh3cevtModuleSw-LSQM1TGS48RSG3              OBJECT IDENTIFIER ::= { hh3cevtModuleSwitchType 1747 } -- 48-Port 10GBASE-R Ethernet SFP+ Optical Interface Board(SG)
hh3cevtModuleSw-LSXM2TGS32QSSG3             OBJECT IDENTIFIER ::= { hh3cevtModuleSwitchType 1748 } -- 32-Port 10GBASE-R Ethernet Optical Interface(SFP+,LC)+4-Port 40GBASE-R Ethernet Optical Interface Board(QSFP+,LC)(SG)
hh3cevtModuleSw-LSUM1NSDEC0                 OBJECT IDENTIFIER ::= { hh3cevtModuleSwitchType 1749 } -- NetStream Service Board
hh3cevtModuleSw-LSQM1NSDSC0                 OBJECT IDENTIFIER ::= { hh3cevtModuleSwitchType 1750 } -- NetStream Service Board
hh3cevtModuleSw-LSQM1QGS4SC0                OBJECT IDENTIFIER ::= { hh3cevtModuleSwitchType 1751 } -- 4-Port 40G BASE Ethernet Optical Interface Board(QSFP+,MPO)(SC)
hh3cevtModuleSw-LLSQM2MPUD3                 OBJECT IDENTIFIER ::= { hh3cevtModuleSwitchType 1752 } -- Supervisor Engine Board
hh3cevtModuleSw-LLSQM3MPUB3                 OBJECT IDENTIFIER ::= { hh3cevtModuleSwitchType 1753 } -- Supervisor Engine Board
hh3cevtModuleSw-LSQM3MPUB4                  OBJECT IDENTIFIER ::= { hh3cevtModuleSwitchType 1754 } -- Supervisor Engine Board
hh3cevtModuleSw-LSQM2MPUDS0                 OBJECT IDENTIFIER ::= { hh3cevtModuleSwitchType 1755 } -- Supervisor Engine Board
hh3cevtModuleSw-LSQM4GV48SA0                OBJECT IDENTIFIER ::= { hh3cevtModuleSwitchType 1756 } -- 48-Port 1000Base-T Gigabit Ethernet Interface Board(RJ45)(SA)-POE
hh3cevtModuleSw-LSQM1WCMX20                 OBJECT IDENTIFIER ::= { hh3cevtModuleSwitchType 1757 } -- Access Controller Service Board
hh3cevtModuleSw-LSQM1WCMX40                 OBJECT IDENTIFIER ::= { hh3cevtModuleSwitchType 1758 } -- Access Controller Service Board
hh3cevtModuleSw-LSUM1WCMX20RT               OBJECT IDENTIFIER ::= { hh3cevtModuleSwitchType 1759 } -- Access Controller Service Board
hh3cevtModuleSw-LSUM1WCMX40RT               OBJECT IDENTIFIER ::= { hh3cevtModuleSwitchType 1760 } -- Access Controller Service Board
hh3cevtModuleSw-LSXM1CGQ18QGHB0             OBJECT IDENTIFIER ::= { hh3cevtModuleSwitchType 1761 } -- 18-PORT 100GBASE Ethernet Optical Interface (QSFP28)/36-PORT 40GBASE Ethernet Optical Interface Module(QSFP+)(HB)
hh3cevtModuleSw-LSXM1SFH08C0                OBJECT IDENTIFIER ::= { hh3cevtModuleSwitchType 1762 } -- Fabric Module,Type H(Class C)
hh3cevtModuleSw-LSXM1SFH08C1                OBJECT IDENTIFIER ::= { hh3cevtModuleSwitchType 1763 } -- Fabric Module,Type H(Class C)
hh3cevtModuleSw-LSXM2SFH16C0                OBJECT IDENTIFIER ::= { hh3cevtModuleSwitchType 1764 } -- Fabric Module,Type H(Class C)
hh3cevtModuleSw-LSXM2SFH16C1                OBJECT IDENTIFIER ::= { hh3cevtModuleSwitchType 1765 } -- Fabric Module,Type H(Class C)
hh3cevtModuleSw-LSXM1NSDF1                  OBJECT IDENTIFIER ::= { hh3cevtModuleSwitchType 1766 } -- SecBlade IV NetStream Module
hh3cevtModuleSw-LSUM2TGS48SG3               OBJECT IDENTIFIER ::= { hh3cevtModuleSwitchType 1767 } -- 48-Port 10GBASE-R Ethernet SFP+ Optical Interface Board(SG)
hh3cevtModuleSw-DS-3E7602-MPU               OBJECT IDENTIFIER ::= { hh3cevtModuleSwitchType 1768 } -- Supervisor Engine Board
hh3cevtModuleSw-DS-3E7606-MPU               OBJECT IDENTIFIER ::= { hh3cevtModuleSwitchType 1769 } -- Supervisor Engine Board
hh3cevtModuleSw-DS-3E7600-24T4X-SC          OBJECT IDENTIFIER ::= { hh3cevtModuleSwitchType 1770 } -- 24-Port 1000Base-T Gigabit Ethernet Interface Board(RJ45)+4-Port 10GE Optical Interface Board(SFP+,LC)(SC)
hh3cevtModuleSw-DS-3E7600-24F4X-SA          OBJECT IDENTIFIER ::= { hh3cevtModuleSwitchType 1771 } -- 24-Port GE Optical Interface(SFP,LC)+4-Port 10GE Optical Interface Board(SFP+,LC)(SA)
hh3cevtModuleSw-DS-3E7600-48T-SA            OBJECT IDENTIFIER ::= { hh3cevtModuleSwitchType 1772 } -- 48-Port 1000Base-T Gigabit Ethernet Interface Board(RJ45)(SA)
hh3cevtModuleSw-DS-3E7600-48F-SA            OBJECT IDENTIFIER ::= { hh3cevtModuleSwitchType 1773 } -- 48-Port 1000BASE-X Ethernet Optical Interface Board(SFP,LC)(SA)
hh3cevtModuleSw-DS-3E7600-24F4X-SC          OBJECT IDENTIFIER ::= { hh3cevtModuleSwitchType 1774 } -- 24-Port GE Optical Interface(SFP,LC)+4-Port 10GE Optical Interface Board(SFP+,LC)(SC)
hh3cevtModuleSw-DS-3E7600-44F4X-SC          OBJECT IDENTIFIER ::= { hh3cevtModuleSwitchType 1775 } -- 44-Port GE Optical Interface(SFP,LC)+4-Port 10GE Optical Interface Board(SFP+,LC)(SC)
hh3cevtModuleSw-DS-3E7600-48T-SC            OBJECT IDENTIFIER ::= { hh3cevtModuleSwitchType 1776 } -- 48-Port 1000Base-T Gigabit Ethernet Interface Board(RJ45)(SC)
hh3cevtModuleSw-DS-3E7600-16X-SC            OBJECT IDENTIFIER ::= { hh3cevtModuleSwitchType 1777 } -- 16-Port 10GE Optical Interface Board(SFP+,LC)(SF)
hh3cevtModuleSw-S7602-MPU                   OBJECT IDENTIFIER ::= { hh3cevtModuleSwitchType 1778 } -- Supervisor Engine Board
hh3cevtModuleSw-S7606-MPU                   OBJECT IDENTIFIER ::= { hh3cevtModuleSwitchType 1779 } -- Supervisor Engine Board
hh3cevtModuleSw-S76-24GT4XFSC               OBJECT IDENTIFIER ::= { hh3cevtModuleSwitchType 1780 } -- 24-Port 1000Base-T Gigabit Ethernet Interface Board(RJ45)+4-Port 10GE Optical Interface Board(SFP+,LC)(SC)
hh3cevtModuleSw-S76-24GF4XFSA               OBJECT IDENTIFIER ::= { hh3cevtModuleSwitchType 1781 } -- 24-Port GE Optical Interface(SFP,LC)+4-Port 10GE Optical Interface Board(SFP+,LC)(SA)
hh3cevtModuleSw-S76-48GTSA                  OBJECT IDENTIFIER ::= { hh3cevtModuleSwitchType 1782 } -- 48-Port 1000Base-T Gigabit Ethernet Interface Board(RJ45)(SA)
hh3cevtModuleSw-S76-48GFSA                  OBJECT IDENTIFIER ::= { hh3cevtModuleSwitchType 1783 } -- 48-Port 1000BASE-X Ethernet Optical Interface Board(SFP,LC)(SA)
hh3cevtModuleSw-S76-24GT20GF4XFSC           OBJECT IDENTIFIER ::= { hh3cevtModuleSwitchType 1784 } -- 24-Port 1000Base-T Gigabit Ethernet Interface Board(RJ45)+20-Port GE Optical Interface(SFP,LC)+4-Port 10GE Optical Interface Board(SFP+,LC)(SC)
hh3cevtModuleSw-LSXM1TGS48C2HB0             OBJECT IDENTIFIER ::= { hh3cevtModuleSwitchType 1785 } -- 48-PORT 10GBASE Ethernet Optical Interface (SFP+,LC)+2-PORT 100GBASE Ethernet Optical Interface Module(QSFP28)(HB)
hh3cevtModuleSw-LSXM1CGQ18QGHC0             OBJECT IDENTIFIER ::= { hh3cevtModuleSwitchType 1786 } -- 18-PORT 100GBASE Ethernet Optical Interface (QSFP28)/36-PORT 40GBASE Ethernet Optical Interface Module(QSFP+)(HC)
hh3cevtModuleSw-LSXM1TGS48HB1               OBJECT IDENTIFIER ::= { hh3cevtModuleSwitchType 1787 } -- 48-Port 10G BASE Ethernet Optical Interface Module(SFP+,LC)(HB)
hh3cevtModuleSw-LSXM1TGS48HB0               OBJECT IDENTIFIER ::= { hh3cevtModuleSwitchType 1788 } -- 48-Port 10G BASE Ethernet Optical Interface Module(SFP+,LC)(HB)
hh3cevtModuleSw-LSQM1CGP24TSSC0             OBJECT IDENTIFIER ::= { hh3cevtModuleSwitchType 1789 } -- Supervisor Engine Board With 24-Port 1000BASE-X Ethernet SFP Optical Interface+4-Port 10GBASE-R Ethernet SFP+ Optical Interfaces
hh3cevtModuleSw-LSQM1CGP24TSSA0             OBJECT IDENTIFIER ::= { hh3cevtModuleSwitchType 1790 } -- Supervisor Engine Board With 24-Port 1000BASE-X Ethernet SFP Optical Interface+4-Port 10GBASE-R Ethernet SFP+ Optical Interfaces
hh3cevtModuleSw-LSQM1CGT24TSSC0             OBJECT IDENTIFIER ::= { hh3cevtModuleSwitchType 1791 } -- Supervisor Engine Board With 24-Port 10/100/1000BASE-T Ethernet Interface+4-Port 10GBASE-R Ethernet SFP+ Optical Interfaces
hh3cevtModuleSw-LSQM1CGT24TSSA0             OBJECT IDENTIFIER ::= { hh3cevtModuleSwitchType 1792 } -- Supervisor Engine Board With 24-Port 10/100/1000BASE-T Ethernet Interface+4-Port 10GBASE-R Ethernet SFP+ Optical Interfaces
hh3cevtModuleSw-LSQM2GP24SA0                OBJECT IDENTIFIER ::= { hh3cevtModuleSwitchType 1793 } -- 24-Port GE Optical Interface(SFP,LC)(SA)
hh3cevtModuleSw-LSX1SUPH1                   OBJECT IDENTIFIER ::= { hh3cevtModuleSwitchType 1794 } -- Supervisor Engine Board
hh3cevtModuleSw-LSX1SUPH0                   OBJECT IDENTIFIER ::= { hh3cevtModuleSwitchType 1795 } -- Supervisor Engine Board
hh3cevtModuleSw-LSX1SUP04H1                 OBJECT IDENTIFIER ::= { hh3cevtModuleSwitchType 1796 } -- Supervisor Engine Board
hh3cevtModuleSw-LSX1SUP04H0                 OBJECT IDENTIFIER ::= { hh3cevtModuleSwitchType 1797 } -- Supervisor Engine Board
hh3cevtModuleSw-LSXM1SFH08D0                OBJECT IDENTIFIER ::= { hh3cevtModuleSwitchType 1798 } -- Fabric Module,Type H(Class D)
hh3cevtModuleSw-LSXM1SFH04D0                OBJECT IDENTIFIER ::= { hh3cevtModuleSwitchType 1799 } -- Fabric Module,Type H(Class D)
--
-- 1800 for united assignment
--
hh3cevtModuleSw-LSXM1SFH16C0                OBJECT IDENTIFIER ::= { hh3cevtModuleSwitchType 1800 } -- Fabric Module,Type H(Class C+)
hh3cevtModuleSw-LSXM1SFH12D0                OBJECT IDENTIFIER ::= { hh3cevtModuleSwitchType 1801 } -- Fabric Module,Type H(Class D)
hh3cevtModuleSw-LSXM1QGS48HB0               OBJECT IDENTIFIER ::= { hh3cevtModuleSwitchType 1802 } -- 48-Port 40GBASE Ethernet Optical Interface Module(QSFP+)(HB)
hh3cevtModuleSw-LSXM1QGS48HC0               OBJECT IDENTIFIER ::= { hh3cevtModuleSwitchType 1803 } -- 48-Port 40GBASE Ethernet Optical Interface Module(QSFP+)(HC)
hh3cevtModuleSw-LSXM1CGQ36HB0               OBJECT IDENTIFIER ::= { hh3cevtModuleSwitchType 1804 } -- 36-Port 100GBASE Ethernet Optical Interface Module(QSFP28)(HB)
hh3cevtModuleSw-LSXM1TGS48C2HC0             OBJECT IDENTIFIER ::= { hh3cevtModuleSwitchType 1805 } -- 48-PORT 10GBASE Ethernet Optical Interface (SFP+,LC)+2-PORT 100GBASE Ethernet Optical Interface Module(QSFP28)(HC)
hh3cevtModuleSw-LSQM2GP44TSSE0              OBJECT IDENTIFIER ::= { hh3cevtModuleSwitchType 1806 } -- 44-Port GE Optical Interface(SFP,LC)+4-Port 10GE Optical Interface Board(SFP+,LC)(SE)
hh3cevtModuleSw-LSQM2GP24TSSA8              OBJECT IDENTIFIER ::= { hh3cevtModuleSwitchType 1807 } -- 24-Port GE Optical Interface(SFP,LC)+4-Port 10GE Optical Interface Board(SFP+,LC)(SA)
hh3cevtModuleSw-LSQM2GT48SA8                OBJECT IDENTIFIER ::= { hh3cevtModuleSwitchType 1808 } -- 48-Port 1000Base-T Gigabit Ethernet Interface Board(RJ45)(SA)
hh3cevtModuleSw-LSQM2GP48SA8                OBJECT IDENTIFIER ::= { hh3cevtModuleSwitchType 1809 } -- 48-Port 1000BASE-X Ethernet Optical Interface Board(SFP,LC)(SA)
hh3cevtModuleSw-EWPXM1CGP24TSSC0            OBJECT IDENTIFIER ::= { hh3cevtModuleSwitchType 1810 } -- Supervisor Engine Board With 24-Port 1000BASE-X Ethernet SFP Optical Interface+4-Port 10GBASE-R Ethernet SFP+ Optical Interfaces
hh3cevtModuleSw-EWPXM3MPUB0                 OBJECT IDENTIFIER ::= { hh3cevtModuleSwitchType 1811 } -- Supervisor Engine Board
hh3cevtModuleSw-EWPXM2MPUDS0                OBJECT IDENTIFIER ::= { hh3cevtModuleSwitchType 1812 } -- Supervisor Engine Board
hh3cevtModuleSw-EWPXM2TGS16SF0              OBJECT IDENTIFIER ::= { hh3cevtModuleSwitchType 1813 } -- 16-Port 10GE Optical Interface Board(SFP+,LC)(SF)
hh3cevtModuleSw-EWPXM2GP44TSSC0             OBJECT IDENTIFIER ::= { hh3cevtModuleSwitchType 1814 } -- 44-Port GE Optical Interface(SFP,LC)+4-Port 10GE Optical Interface Board(SFP+,LC)(SC)
hh3cevtModuleSw-EWPXM2GP24TSSC0             OBJECT IDENTIFIER ::= { hh3cevtModuleSwitchType 1815 } -- 24-Port GE Optical Interface(SFP,LC)+4-Port 10GE Optical Interface Board(SFP+,LC)(SC)
hh3cevtModuleSw-EWPXM1MAC0F                 OBJECT IDENTIFIER ::= { hh3cevtModuleSwitchType 1816 } -- Access Controller Service Board
hh3cevtModuleSw-LSQM1CGP24TSSA8             OBJECT IDENTIFIER ::= { hh3cevtModuleSwitchType 1817 } -- Supervisor Engine Board With 24-Port 1000BASE-X Ethernet SFP Optical Interface+4-Port 10GBASE-R Ethernet SFP+ Optical Interfaces
hh3cevtModuleSw-LSQM1CGT24TSSA8             OBJECT IDENTIFIER ::= { hh3cevtModuleSwitchType 1818 } -- Supervisor Engine Board With 24-Port 10/100/1000BASE-T Ethernet Interface+4-Port 10GBASE-R Ethernet SFP+ Optical Interfaces
hh3cevtModuleSw-LSWM1FWD0                   OBJECT IDENTIFIER ::= { hh3cevtModuleSwitchType 1819 } -- Firewall Service Board
hh3cevtModuleSw-LSUM2MPU10C0                OBJECT IDENTIFIER ::= { hh3cevtModuleSwitchType 1820 } -- Supervisor Engine Board
hh3cevtModuleSw-LSQM2MPU10C0                OBJECT IDENTIFIER ::= { hh3cevtModuleSwitchType 1821 } -- Supervisor Engine Board
hh3cevtModuleSw-LSUM2MPU10C3                OBJECT IDENTIFIER ::= { hh3cevtModuleSwitchType 1822 } -- Supervisor Engine Board
hh3cevtModuleSw-LSUM2FAB10C0                OBJECT IDENTIFIER ::= { hh3cevtModuleSwitchType 1823 } -- Switching Fabric Module
hh3cevtModuleSw-LSQM2FAB10C0                OBJECT IDENTIFIER ::= { hh3cevtModuleSwitchType 1824 } -- Switching Fabric Module
hh3cevtModuleSw-LSUM2FAB10C3                OBJECT IDENTIFIER ::= { hh3cevtModuleSwitchType 1825 } -- Switching Fabric Module
hh3cevtModuleSw-LSUM2CQGS12SG0              OBJECT IDENTIFIER ::= { hh3cevtModuleSwitchType 1826 } -- 12-Port 40GBASE-R QSFP+ or 4-Port 100GBASE-R QSFP28 Optical Interface Board(SG)
hh3cevtModuleSw-LSXM2CQGS12SG3              OBJECT IDENTIFIER ::= { hh3cevtModuleSwitchType 1827 } -- 12-Port 40GBASE-R QSFP+ or 4-Port 100GBASE-R QSFP28 Optical Interface Board(SG)
hh3cevtModuleSw-LSQM2CQGS12XSG0             OBJECT IDENTIFIER ::= { hh3cevtModuleSwitchType 1828 } -- 12-Port 40GBASE-R QSFP+ or 4-Port 100GBASE-R QSFP28 Optical Interface Board(SG)
hh3cevtModuleSw-LSQM1CQGS12SG0              OBJECT IDENTIFIER ::= { hh3cevtModuleSwitchType 1829 } -- 12-Port 40GBASE-R QSFP+ or 4-Port 100GBASE-R QSFP28 Optical Interface Board(SG)
hh3cevtModuleSw-LSXM1CGQ6QGHB0              OBJECT IDENTIFIER ::= { hh3cevtModuleSwitchType 1830 } -- 6-Port 100GBASE Ethernet Optical Interface(QSFP28)/12-Port 40GBASE Ethernet Optical Interface Module(QSFP+)(HB)
hh3cevtModuleSw-LSXM1CGQ6QGHB1              OBJECT IDENTIFIER ::= { hh3cevtModuleSwitchType 1831 } -- 6-Port 100GBASE Ethernet Optical Interface(QSFP28)/12-Port 40GBASE Ethernet Optical Interface Module(QSFP+)(HB)
hh3cevtModuleSw-LSXM1CGQ6QGHC0              OBJECT IDENTIFIER ::= { hh3cevtModuleSwitchType 1832 } -- 6-Port 100GBASE Ethernet Optical Interface(QSFP28)/12-Port 40GBASE Ethernet Optical Interface Module(QSFP+)(HC)
hh3cevtModuleSw-LSXM1QGS36HB0               OBJECT IDENTIFIER ::= { hh3cevtModuleSwitchType 1833 } -- 36-Port 40GBASE Ethernet Optical Interface Module(QSFP+)(HB)
hh3cevtModuleSw-LSXM1QGS36HB1               OBJECT IDENTIFIER ::= { hh3cevtModuleSwitchType 1834 } -- 36-Port 40GBASE Ethernet Optical Interface Module(QSFP+)(HB)
hh3cevtModuleSw-LSXM1QGS36HC0               OBJECT IDENTIFIER ::= { hh3cevtModuleSwitchType 1835 } -- 36-Port 40GBASE Ethernet Optical Interface Module(QSFP+)(HC)
hh3cevtModuleSw-LSXM1SUPC0                  OBJECT IDENTIFIER ::= { hh3cevtModuleSwitchType 1836 } -- Supervisor Engine Unit
hh3cevtModuleSw-LSXM1SUPC1                  OBJECT IDENTIFIER ::= { hh3cevtModuleSwitchType 1837 } -- Supervisor Engine Unit
hh3cevtModuleSw-LSXM1SUP04H0                OBJECT IDENTIFIER ::= { hh3cevtModuleSwitchType 1838 } -- Supervisor Engine Unit
hh3cevtModuleSw-LSXM1SUP04H1                OBJECT IDENTIFIER ::= { hh3cevtModuleSwitchType 1839 } -- Supervisor Engine Unit
hh3cevtModuleSw-LSXM1SUPH0                  OBJECT IDENTIFIER ::= { hh3cevtModuleSwitchType 1840 } -- Supervisor Engine Unit
hh3cevtModuleSw-LSXM1SUPH1                  OBJECT IDENTIFIER ::= { hh3cevtModuleSwitchType 1841 } -- Supervisor Engine Unit
hh3cevtModuleSw-EWPXM2WCMD0F                OBJECT IDENTIFIER ::= { hh3cevtModuleSwitchType 1842 } -- 20G Access Controller Module
hh3cevtModuleSw-LSUM2QGS24RSG0              OBJECT IDENTIFIER ::= { hh3cevtModuleSwitchType 1843 } -- 24-Port 40GBASE-R Ethernet QSFP+ Optical Interface Board(SG)
hh3cevtModuleSw-LSQM1QGS24RSG0              OBJECT IDENTIFIER ::= { hh3cevtModuleSwitchType 1844 } -- 24-Port 40GBASE-R Ethernet QSFP+ Optical Interface Board(SG)
hh3cevtModuleSw-LSXM2QGS24RSG3              OBJECT IDENTIFIER ::= { hh3cevtModuleSwitchType 1845 } -- 24-Port 40GBASE-R Ethernet QSFP+ Optical Interface Board(SG)
hh3cevtModuleSw-LSQM2QGS24RXSG0             OBJECT IDENTIFIER ::= { hh3cevtModuleSwitchType 1846 } -- 24-Port 40GBASE-R Ethernet QSFP+ Optical Interface Board(SG)
hh3cevtModuleSw-LSQM2TGS48RSG0              OBJECT IDENTIFIER ::= { hh3cevtModuleSwitchType 1847 } -- 48-Port 10GBASE-R Ethernet SFP+ Optical Interface Board(SG)
hh3cevtModuleSw-LSXM1X86SUPE0               OBJECT IDENTIFIER ::= { hh3cevtModuleSwitchType 1848 } -- Cloud Supervisor Engine Unit
hh3cevtModuleSw-LSXM1X86SUPE1               OBJECT IDENTIFIER ::= { hh3cevtModuleSwitchType 1849 } -- Cloud Supervisor Engine Unit
hh3cevtModuleSw-LSQM1CGS2QSA0               OBJECT IDENTIFIER ::= { hh3cevtModuleSwitchType 1850 } -- 2-Port 100G Ethernet Optical Interface(QSFP28)+2-Port 40G Ethernet Optical Interface Module(QSFP+)
hh3cevtModuleSw-LSUM1ACGDEC0                OBJECT IDENTIFIER ::= { hh3cevtModuleSwitchType 1851 } -- SecBlade IV Application Control Module
hh3cevtModuleSw-LSQM1ACGDSC0                OBJECT IDENTIFIER ::= { hh3cevtModuleSwitchType 1852 } -- SecBlade IV Application Control Module
hh3cevtModuleSw-LSXM1CGQ36HF1               OBJECT IDENTIFIER ::= { hh3cevtModuleSwitchType 1853 } -- 36-Port 100GBASE Ethernet Optical Interface Module(QSFP28)(HF)
hh3cevtModuleSw-LSXM1QGS48HF1               OBJECT IDENTIFIER ::= { hh3cevtModuleSwitchType 1854 } -- 48-Port 40GBASE Ethernet Optical Interface Module(QSFP+)(HF)
hh3cevtModuleSw-LSXM1CGQ18QGHF1             OBJECT IDENTIFIER ::= { hh3cevtModuleSwitchType 1855 } -- 18-PORT 100GBASE Ethernet Optical Interface(QSFP28)/36-Port 40GBASE Ethernet Optical Interface Module(QSFP+)(HF)
hh3cevtModuleSw-LSXM1QGS36HF1               OBJECT IDENTIFIER ::= { hh3cevtModuleSwitchType 1856 } -- 36-Port 40GBASE Ethernet Optical Interface Module(QSFP+)(HF)
hh3cevtModuleSw-LSXM1CGQ6QGHF1              OBJECT IDENTIFIER ::= { hh3cevtModuleSwitchType 1857 } -- 6-Port 100GBASE Ethernet Optical Interface(QSFP28)/12-Port 40GBASE Ethernet Optical Interface Module(QSFP+)(HF)
hh3cevtModuleSw-LSXM1QGS48HF0               OBJECT IDENTIFIER ::= { hh3cevtModuleSwitchType 1858 } -- 48-Port 40GBASE Ethernet Optical Interface Module(QSFP+)(HF)
hh3cevtModuleSw-LSXM1CGQ18QGHF0             OBJECT IDENTIFIER ::= { hh3cevtModuleSwitchType 1859 } -- 18-PORT 100GBASE Ethernet Optical Interface(QSFP28)/36-Port 40GBASE Ethernet Optical Interface Module(QSFP+)(HF)
hh3cevtModuleSw-LSXM1CGQ6QGHF0              OBJECT IDENTIFIER ::= { hh3cevtModuleSwitchType 1860 } -- 6-Port 100GBASE Ethernet Optical Interface(QSFP28)/12-Port 40GBASE Ethernet Optical Interface Module(QSFP+)(HF)
hh3cevtModuleSw-LSXM1TGS48HF0               OBJECT IDENTIFIER ::= { hh3cevtModuleSwitchType 1861 } -- 48-Port 10GBASE Ethernet Optical Interface Module(SFP+,LC)(HF)
hh3cevtModuleSw-LSXM1TGS48HF1               OBJECT IDENTIFIER ::= { hh3cevtModuleSwitchType 1862 } -- 48-Port 10GBASE Ethernet Optical Interface Module(SFP+,LC)(HF)
hh3cevtModuleSw-LSQM1GP24FC3                OBJECT IDENTIFIER ::= { hh3cevtModuleSwitchType 1863 } -- 24-Port 1000BASE-X Optical Interface Board(SFP,LC)
hh3cevtModuleSw-LSQM1GP24FD3                OBJECT IDENTIFIER ::= { hh3cevtModuleSwitchType 1864 } -- 24-Port 1000BASE-X Optical Interface Board(SFP,LC)
hh3cevtModuleSw-LSQM1GP24TSFC3              OBJECT IDENTIFIER ::= { hh3cevtModuleSwitchType 1865 } -- 24-Port 1000BASE-X Optical Interface(SFP,LC)+4-Port 10GBASE-R Ethernet Optical Interface Board(SFP+,LC)
hh3cevtModuleSw-LSQM1GP24TSFD3              OBJECT IDENTIFIER ::= { hh3cevtModuleSwitchType 1866 } -- 24-Port 1000BASE-X Optical Interface(SFP,LC)+4-Port 10GBASE-R Ethernet Optical Interface Board(SFP+,LC)
hh3cevtModuleSw-LSQM1GP40TS8FD0             OBJECT IDENTIFIER ::= { hh3cevtModuleSwitchType 1867 } -- 40-Port 1000BASE-X Optical Interface(SFP,LC)+8-Port 10GBASE-R Ethernet Optical Interface Board(SFP+,LC)
hh3cevtModuleSw-LSQM1GP48FC3                OBJECT IDENTIFIER ::= { hh3cevtModuleSwitchType 1868 } -- 48-Port 1000BASE-X Optical Interface Board(SFP,LC)
hh3cevtModuleSw-LSQM1GP48FD0                OBJECT IDENTIFIER ::= { hh3cevtModuleSwitchType 1869 } -- 48-Port 1000BASE-X Optical Interface Board(SFP,LC)
hh3cevtModuleSw-LSQM1GP48FD3                OBJECT IDENTIFIER ::= { hh3cevtModuleSwitchType 1870 } -- 48-Port 1000BASE-X Optical Interface Board(SFP,LC)
hh3cevtModuleSw-LSQM1GT48FC3                OBJECT IDENTIFIER ::= { hh3cevtModuleSwitchType 1871 } -- 48-Port 10/100/1000BASE-T Electrical Interface Board(RJ45)
hh3cevtModuleSw-LSQM1GT48FD0                OBJECT IDENTIFIER ::= { hh3cevtModuleSwitchType 1872 } -- 48-Port 10/100/1000BASE-T Electrical Interface Board(RJ45)
hh3cevtModuleSw-LSQM1GT48FD3                OBJECT IDENTIFIER ::= { hh3cevtModuleSwitchType 1873 } -- 48-Port 10/100/1000BASE-T Electrical Interface Board(RJ45)
hh3cevtModuleSw-LSQM1TGS24FC3               OBJECT IDENTIFIER ::= { hh3cevtModuleSwitchType 1874 } -- 24-Port 10GBASE-R Ethernet Optical Interface Board(SFP+,LC)
hh3cevtModuleSw-LSQM1TGS24FD0               OBJECT IDENTIFIER ::= { hh3cevtModuleSwitchType 1875 } -- 24-Port 10GBASE-R Ethernet Optical Interface Board(SFP+,LC)
hh3cevtModuleSw-LSQM1TGS24FD3               OBJECT IDENTIFIER ::= { hh3cevtModuleSwitchType 1876 } -- 24-Port 10GBASE-R Ethernet Optical Interface Board(SFP+,LC)
hh3cevtModuleSw-LSQM1TGS24XFD0              OBJECT IDENTIFIER ::= { hh3cevtModuleSwitchType 1877 } -- 24-Port 10GBASE-R Ethernet Optical Interface Board(SFP+,LC)
hh3cevtModuleSw-LSQM1TGS48RFE0              OBJECT IDENTIFIER ::= { hh3cevtModuleSwitchType 1878 } -- 48-Port 10GBASE-R Ethernet Optical Interface Board(SFP+,LC)
hh3cevtModuleSw-LSQM1TGS8FC3                OBJECT IDENTIFIER ::= { hh3cevtModuleSwitchType 1879 } -- 8-Port 10GBASE-R Ethernet Optical Interface Board(SFP+,LC)
hh3cevtModuleSw-LSQM1TGS8FD3                OBJECT IDENTIFIER ::= { hh3cevtModuleSwitchType 1880 } -- 8-Port 10GBASE-R Ethernet Optical Interface Board(SFP+,LC)
hh3cevtModuleSw-LSUM1GP40TS8FD0             OBJECT IDENTIFIER ::= { hh3cevtModuleSwitchType 1881 } -- 40-Port 1000BASE-X Optical Interface(SFP,LC)+8-Port 10GBASE-R Ethernet Optical Interface Board(SFP+,LC)
hh3cevtModuleSw-LSUM1GP48FD0                OBJECT IDENTIFIER ::= { hh3cevtModuleSwitchType 1882 } -- 48-Port 1000BASE-X Optical Interface Board(SFP,LC)
hh3cevtModuleSw-LSUM1GP48FD3                OBJECT IDENTIFIER ::= { hh3cevtModuleSwitchType 1883 } -- 48-Port 1000BASE-X Optical Interface Board(SFP,LC)
hh3cevtModuleSw-LSUM1GT48FD0                OBJECT IDENTIFIER ::= { hh3cevtModuleSwitchType 1884 } -- 48-Port 10/100/1000BASE-T Electrical Interface Board(RJ45)
hh3cevtModuleSw-LSUM1GT48FD3                OBJECT IDENTIFIER ::= { hh3cevtModuleSwitchType 1885 } -- 48-Port 10/100/1000BASE-T Electrical Interface Board(RJ45)
hh3cevtModuleSw-LSUM1TGS24FD0               OBJECT IDENTIFIER ::= { hh3cevtModuleSwitchType 1886 } -- 24-Port 10GBASE-R Ethernet Optical Interface Board(SFP+,LC)
hh3cevtModuleSw-LSUM1TGS24FD3               OBJECT IDENTIFIER ::= { hh3cevtModuleSwitchType 1887 } -- 24-Port 10GBASE-R Ethernet Optical Interface Board(SFP+,LC)
hh3cevtModuleSw-LSXM1GP40TS8FD0             OBJECT IDENTIFIER ::= { hh3cevtModuleSwitchType 1888 } -- 40-Port 1000BASE-X Optical Interface(SFP,LC)+8-Port 10GBASE-R Ethernet Optical Interface Board(SFP+,LC)
hh3cevtModuleSw-LSXM1GT48FD3                OBJECT IDENTIFIER ::= { hh3cevtModuleSwitchType 1889 } -- 48-Port 10/100/1000BASE-T Electrical Interface Board(RJ45)
hh3cevtModuleSw-LSXM1TGS24FD3               OBJECT IDENTIFIER ::= { hh3cevtModuleSwitchType 1890 } -- 24-Port 10GBASE-R Ethernet Optical Interface Board(SFP+,LC)
hh3cevtModuleSw-LSQM1MPUS10C3               OBJECT IDENTIFIER ::= { hh3cevtModuleSwitchType 1891 } -- Supervisor Engine Board
hh3cevtModuleSw-LSQM1MPUSA3                 OBJECT IDENTIFIER ::= { hh3cevtModuleSwitchType 1892 } -- Supervisor Engine Board
hh3cevtModuleSw-LSQM2SUPA3                  OBJECT IDENTIFIER ::= { hh3cevtModuleSwitchType 1893 } -- Supervisor Engine Board
hh3cevtModuleSw-LSXM1SFH16E1                OBJECT IDENTIFIER ::= { hh3cevtModuleSwitchType 1894 } -- S12516X-AF Fabric Module,Type H(Class E)
hh3cevtModuleSw-LSXM1SFH16E0                OBJECT IDENTIFIER ::= { hh3cevtModuleSwitchType 1895 } -- S12516X-AF Fabric Module,Type H(Class E)
hh3cevtModuleSw-LSXM1GP40TS8FD3             OBJECT IDENTIFIER ::= { hh3cevtModuleSwitchType 1896 } -- 40-Port 1000BASE-X Optical Interface(SFP,LC)+8-Port 10GBASE-R Ethernet Optical Interface Board(SFP+,LC)
hh3cevtModuleSw-LSQM1MPUS10C0               OBJECT IDENTIFIER ::= { hh3cevtModuleSwitchType 1897 } -- Supervisor Engine Board
hh3cevtModuleSw-LSQM1MPUSA0                 OBJECT IDENTIFIER ::= { hh3cevtModuleSwitchType 1898 } -- Supervisor Engine Board
hh3cevtModuleSw-LSQM2SUPA0                  OBJECT IDENTIFIER ::= { hh3cevtModuleSwitchType 1899 } -- Supervisor Engine Board
hh3cevtModuleSw-LSQM1TGS16FC3               OBJECT IDENTIFIER ::= { hh3cevtModuleSwitchType 1900 } -- 16-Port 10GBASE-R Ethernet SFP+ Optical Interface Board(FC)
hh3cevtModuleSw-LSQM1TGS16FD0               OBJECT IDENTIFIER ::= { hh3cevtModuleSwitchType 1901 } -- 16-Port 10GBASE-R Ethernet SFP+ Optical Interface Board(FD)
hh3cevtModuleSw-LSQM1TGS16FD3               OBJECT IDENTIFIER ::= { hh3cevtModuleSwitchType 1902 } -- 16-Port 10GBASE-R Ethernet SFP+ Optical Interface Board(FD)
hh3cevtModuleSw-LSQM2TGS48SG0               OBJECT IDENTIFIER ::= { hh3cevtModuleSwitchType 1903 } -- 48-Port 10GBASE-R Ethernet SFP+ Optical Interface Board(SG)
hh3cevtModuleSw-LSQM2TGS48SG3               OBJECT IDENTIFIER ::= { hh3cevtModuleSwitchType 1904 } -- 48-Port 10GBASE-R Ethernet SFP+ Optical Interface Board(SG)
hh3cevtModuleSw-LSXM1CGQ48HB1               OBJECT IDENTIFIER ::= { hh3cevtModuleSwitchType 1905 } -- 48-Port 100GBASE Ethernet Optical Interface Module(QSFP+)(HB)
hh3cevtModuleSw-LSQM1MPUS06A8               OBJECT IDENTIFIER ::= { hh3cevtModuleSwitchType 1906 } -- Supervisor Engine Board
hh3cevtModuleSw-LSQM1TGS16FD8               OBJECT IDENTIFIER ::= { hh3cevtModuleSwitchType 1907 } -- 16-Port 10GBASE-R Ethernet SFP+ Optical Interface Board(FD)
hh3cevtModuleSw-LSXM1SFH08E1                OBJECT IDENTIFIER ::= { hh3cevtModuleSwitchType 1908 } -- Fabric Module,Type H(Class E)

hh3cevtModuleSw-LSXM1SFH08CC0               OBJECT IDENTIFIER ::= { hh3cevtModuleSwitchType 1909 } -- S12508M-AF Fabric Module,Type H(Class C)
hh3cevtModuleSw-LSXM1SUP08C0                OBJECT IDENTIFIER ::= { hh3cevtModuleSwitchType 1910 } -- S12508M-AF Supervisor Engine Unit
hh3cevtModuleSw-LSUM2FAB04D0                OBJECT IDENTIFIER ::= { hh3cevtModuleSwitchType 1911 } -- Switching Fabric Module
hh3cevtModuleSw-LSUM2FAB04D3                OBJECT IDENTIFIER ::= { hh3cevtModuleSwitchType 1912 } -- Switching Fabric Module
hh3cevtModuleSw-LSXM2FAB04D3                OBJECT IDENTIFIER ::= { hh3cevtModuleSwitchType 1913 } -- Switching Fabric Module
hh3cevtModuleSw-LSUM2FAB04B0                OBJECT IDENTIFIER ::= { hh3cevtModuleSwitchType 1914 } -- Switching Fabric Module
hh3cevtModuleSw-LSUM2FAB04B3                OBJECT IDENTIFIER ::= { hh3cevtModuleSwitchType 1915 } -- Switching Fabric Module
hh3cevtModuleSw-LSUM2FAB08D0                OBJECT IDENTIFIER ::= { hh3cevtModuleSwitchType 1916 } -- Switching Fabric Module
hh3cevtModuleSw-LSUM2FAB08D3                OBJECT IDENTIFIER ::= { hh3cevtModuleSwitchType 1917 } -- Switching Fabric Module
hh3cevtModuleSw-LSXM2FAB08D3                OBJECT IDENTIFIER ::= { hh3cevtModuleSwitchType 1918 } -- Switching Fabric Module
hh3cevtModuleSw-LSUM2FAB08B0                OBJECT IDENTIFIER ::= { hh3cevtModuleSwitchType 1919 } -- Switching Fabric Module
hh3cevtModuleSw-LSUM2FAB08B3                OBJECT IDENTIFIER ::= { hh3cevtModuleSwitchType 1920 } -- Switching Fabric Module
hh3cevtModuleSw-LSUM2FAB12D0                OBJECT IDENTIFIER ::= { hh3cevtModuleSwitchType 1921 } -- Switching Fabric Module
hh3cevtModuleSw-LSUM2FAB12D3                OBJECT IDENTIFIER ::= { hh3cevtModuleSwitchType 1922 } -- Switching Fabric Module
hh3cevtModuleSw-LSXM2FAB12D3                OBJECT IDENTIFIER ::= { hh3cevtModuleSwitchType 1923 } -- Switching Fabric Module
hh3cevtModuleSw-LSUM2FAB12B0                OBJECT IDENTIFIER ::= { hh3cevtModuleSwitchType 1924 } -- Switching Fabric Module
hh3cevtModuleSw-LSUM2FAB12B3                OBJECT IDENTIFIER ::= { hh3cevtModuleSwitchType 1925 } -- Switching Fabric Module
hh3cevtModuleSw-LSQM1CGS2FE0                OBJECT IDENTIFIER ::= { hh3cevtModuleSwitchType 1926 } -- 2-Port 100GBASE-R Ethernet QSFP28 Optical Interface Board(FE)
hh3cevtModuleSw-LSQM1CGS2FE3                OBJECT IDENTIFIER ::= { hh3cevtModuleSwitchType 1927 } -- 2-Port 100GBASE-R Ethernet QSFP28 Optical Interface Board(FE)
hh3cevtModuleSw-LSQM1CGS2XFE0               OBJECT IDENTIFIER ::= { hh3cevtModuleSwitchType 1928 } -- 2-Port 100GBASE-R Ethernet QSFP28 Optical Interface Board(FE)
hh3cevtModuleSw-LSUM1CGS2FE0                OBJECT IDENTIFIER ::= { hh3cevtModuleSwitchType 1929 } -- 2-Port 100GBASE-R Ethernet QSFP28 Optical Interface Board(FE)
hh3cevtModuleSw-LSUM1CGS2FE3                OBJECT IDENTIFIER ::= { hh3cevtModuleSwitchType 1930 } -- 2-Port 100GBASE-R Ethernet QSFP28 Optical Interface Board(FE)
hh3cevtModuleSw-LSXM1CGS2FE3                OBJECT IDENTIFIER ::= { hh3cevtModuleSwitchType 1931 } -- 2-Port 100GBASE-R Ethernet QSFP28 Optical Interface Board(FE)
hh3cevtModuleSw-LSUM1TGS16FD0               OBJECT IDENTIFIER ::= { hh3cevtModuleSwitchType 1932 } -- 16-Port 10GBASE-R Ethernet SFP+ Optical Interface Board(FD)
hh3cevtModuleSw-LSUM1TGS16FD3               OBJECT IDENTIFIER ::= { hh3cevtModuleSwitchType 1933 } -- 16-Port 10GBASE-R Ethernet SFP+ Optical Interface Board(FD)
hh3cevtModuleSw-LSQM1TGS16XFD0              OBJECT IDENTIFIER ::= { hh3cevtModuleSwitchType 1934 } -- 16-Port 10GBASE-R Ethernet SFP+ Optical Interface Board(FD)
hh3cevtModuleSw-LSQM1GP40TS8FC3             OBJECT IDENTIFIER ::= { hh3cevtModuleSwitchType 1935 } -- 40-Port 1000BASE-X Optical Interface(SFP,LC)+8-Port 10GBASE-R Ethernet Optical Interface Board(SFP+,LC)
hh3cevtModuleSw-S76-16XFSF                  OBJECT IDENTIFIER ::= { hh3cevtModuleSwitchType 1936 } -- 16-Port 10GE Optical Interface Board(SFP+,LC)(SF)
hh3cevtModuleSw-S76-24EP2XFSC-OLT           OBJECT IDENTIFIER ::= { hh3cevtModuleSwitchType 1937 } -- 24-Port 1G EPON OLT Optical Interface(SFP,SC)+2-Port 10GE Optical Interface Board(SFP+,LC)(SC)
hh3cevtModuleSw-DS-3E7600-24T20F4X-SC       OBJECT IDENTIFIER ::= { hh3cevtModuleSwitchType 1938 } -- 24-Port 1000Base-T Gigabit Ethernet Interface Board(RJ45)+20-Port GE Optical Interface(SFP,LC)+4-Port 10GE Optical Interface Board(SFP+,LC)(SC)
hh3cevtModuleSw-LSUM1FAB04E0                OBJECT IDENTIFIER ::= { hh3cevtModuleSwitchType 1939 } -- Switching Fabric Module
hh3cevtModuleSw-LSUM1FAB08E0                OBJECT IDENTIFIER ::= { hh3cevtModuleSwitchType 1940 } -- Switching Fabric Module
hh3cevtModuleSw-LSUM1FAB12E0                OBJECT IDENTIFIER ::= { hh3cevtModuleSwitchType 1941 } -- Switching Fabric Module
hh3cevtModuleSw-LSXM1CGQ8FX1                OBJECT IDENTIFIER ::= { hh3cevtModuleSwitchType 1942 } -- 8-Port 100GBASE Ethernet Optical Interface Module(QSFP28)(FX)
hh3cevtModuleSw-LSQM1IPSDSC0                OBJECT IDENTIFIER ::= { hh3cevtModuleSwitchType 1943 } -- SecBlade IV Intrusion Prevention System Module
hh3cevtModuleSw-LSQM2ACGDSC0                OBJECT IDENTIFIER ::= { hh3cevtModuleSwitchType 1944 } -- SecBlade IV Application Control Module
hh3cevtModuleSw-LSQM1ADEDSC0                OBJECT IDENTIFIER ::= { hh3cevtModuleSwitchType 1945 } -- SecBlade IV Load Balancing Module
hh3cevtModuleSw-LSWM1ADED0                  OBJECT IDENTIFIER ::= { hh3cevtModuleSwitchType 1946 } -- SecBlade IV Load Balancing Card
hh3cevtModuleSw-LSWM1IPSD0                  OBJECT IDENTIFIER ::= { hh3cevtModuleSwitchType 1947 } -- SecBlade IV Intrusion Prevention System Card
hh3cevtModuleSw-LSQM1GP40TS8FD3             OBJECT IDENTIFIER ::= { hh3cevtModuleSwitchType 1948 } -- 40-Port 1000BASE-X Optical Interface(SFP,LC)+8-Port 10GBASE-R Ethernet Optical Interface Board(SFP+,LC)
hh3cevtModuleSw-LSUM1SUPXD0                 OBJECT IDENTIFIER ::= { hh3cevtModuleSwitchType 1949 } -- Supervisor Engine Board
hh3cevtModuleSw-LSUM1CQGS32SF0              OBJECT IDENTIFIER ::= { hh3cevtModuleSwitchType 1950 } -- 32-Port 40GBASE-R QSFP+ or 16-Port 100GBASE-R QSFP28 Optical Interface Board(SF)
hh3cevtModuleSw-LSUM1TGS48XSG0              OBJECT IDENTIFIER ::= { hh3cevtModuleSwitchType 1951 } -- 48-Port 10GBASE-R Ethernet SFP+ Optical Interface Board(SG)
hh3cevtModuleSw-LSUM1FAB08XE0               OBJECT IDENTIFIER ::= { hh3cevtModuleSwitchType 1952 } -- Switching Fabric Module
hh3cevtModuleSw-LSUM1FAB16XD0               OBJECT IDENTIFIER ::= { hh3cevtModuleSwitchType 1953 } -- Switching Fabric Module
hh3cevtModuleSw-LSXM1SFH02E0                OBJECT IDENTIFIER ::= { hh3cevtModuleSwitchType 1954 } -- Switching Fabric Module
hh3cevtModuleSw-LSXM1SFH02E1                OBJECT IDENTIFIER ::= { hh3cevtModuleSwitchType 1955 } -- Switching Fabric Module
hh3cevtModuleSw-LSXM1SFH12C0                OBJECT IDENTIFIER ::= { hh3cevtModuleSwitchType 1956 } -- Fabric Module,Type H(Class C)
hh3cevtModuleSw-LSXM1SFH12C1                OBJECT IDENTIFIER ::= { hh3cevtModuleSwitchType 1957 } -- Fabric Module,Type H(Class C)
hh3cevtModuleSw-LSUM1CQGS12XSG0             OBJECT IDENTIFIER ::= { hh3cevtModuleSwitchType 1958 } -- 12-Port 40GBASE-R QSFP+ or 4-Port 100GBASE-R QSFP28 Optical Interface Board(SG)
hh3cevtModuleSw-LSQM1CTGS24QSFD0            OBJECT IDENTIFIER ::= { hh3cevtModuleSwitchType 1959 } -- Supervisor Engine Board With 24-Port 10GBASE-R SFP+ Optical Interface+2-Port 40GBASE-R QSFP+ Optical Interfaces or 1-Port 100GBASE-R QSFP28 Optical Interfaces
hh3cevtModuleSw-LSQM1TGS24QSFD0             OBJECT IDENTIFIER ::= { hh3cevtModuleSwitchType 1960 } -- 24-Port 10GBASE-R Optical Interface(SFP+,LC)+2-Port 40GBASE-R Optical Interface Board(QSFP+) or 1-Port 100GBASE-R Optical Interface Board(QSFP28)
hh3cevtModuleSw-LSUM1WBCZ720RT              OBJECT IDENTIFIER ::= { hh3cevtModuleSwitchType 1961 } -- Access Controller Service Board
hh3cevtModuleSw-LSQM1WBCZ720                OBJECT IDENTIFIER ::= { hh3cevtModuleSwitchType 1962 } -- Access Controller Service Board
hh3cevtModuleSw-DS-3E7610X-MPU              OBJECT IDENTIFIER ::= { hh3cevtModuleSwitchType 1963 } -- Supervisor Engine Board
hh3cevtModuleSw-DS-3E7610X-CLOS             OBJECT IDENTIFIER ::= { hh3cevtModuleSwitchType 1964 } -- Switching Fabric Module
hh3cevtModuleSw-DS-3E7610X-32X4QX-SF        OBJECT IDENTIFIER ::= { hh3cevtModuleSwitchType 1965 } -- 32-Port 10GBASE-R Ethernet Optical Interface(SFP+,LC)+4-Port 40GBASE-R Ethernet Optical Interface Board(QSFP+,LC)(SF)
hh3cevtModuleSw-DS-3E7610X-16X-SF           OBJECT IDENTIFIER ::= { hh3cevtModuleSwitchType 1966 } -- 16-Port 10GBASE-R Ethernet SFP+ Optical
hh3cevtModuleSw-DS-3E7610X-44F4X-SE         OBJECT IDENTIFIER ::= { hh3cevtModuleSwitchType 1967 } -- 44-Port GE Optical Interface(SFP,LC)+4-Port 10GE Optical Interface Board(SFP+,LC)(SE)
hh3cevtModuleSw-DS-3E7610X-48T-SE           OBJECT IDENTIFIER ::= { hh3cevtModuleSwitchType 1968 } -- 48-Port 1000Base-T Gigabit Ethernet Interface Board(RJ45)(SE)
hh3cevtModuleSw-LSQM2GT24PTSSC8             OBJECT IDENTIFIER ::= { hh3cevtModuleSwitchType 1969 } -- 24-Port 1000Base-T Gigabit Ethernet Interface Board(RJ45)+20-Port GE Optical Interface(SFP,LC)+4-Port 10GE Optical Interface Board(SFP+,LC)(SC)
hh3cevtModuleSw-LSQM1CGP24TSSC8             OBJECT IDENTIFIER ::= { hh3cevtModuleSwitchType 1970 } -- Supervisor Engine Board With 24-Port 1000BASE-X Ethernet SFP Optical Interface+4-Port 10GBASE-R Ethernet SFP+ Optical Interfaces
hh3cevtModuleSw-LSQM1CGT24TSSC8             OBJECT IDENTIFIER ::= { hh3cevtModuleSwitchType 1971 } -- Supervisor Engine Board With 24-Port 10/100/1000BASE-T Ethernet Interface+4-Port 10GBASE-R Ethernet SFP+ Optical Interfaces
hh3cevtModuleSw-LSQM1MPUS06B8               OBJECT IDENTIFIER ::= { hh3cevtModuleSwitchType 1972 } -- Supervisor Engine Board
hh3cevtModuleSw-LSVM1MPUB1                  OBJECT IDENTIFIER ::= { hh3cevtModuleSwitchType 1973 } -- Supervisor Engine Unit
hh3cevtModuleSw-LSXM1TGS24QGMODHB0          OBJECT IDENTIFIER ::= { hh3cevtModuleSwitchType 1974 } -- 24-Port 10GBASE Ethernet Optical Interface(SFP+,LC)+4-Port 40GBASE Ethernet Optical Interface Module(QSFP+)(HB),With 1 Expansion Slot
hh3cevtModuleSw-LSXM1TGS24QGMODHB1          OBJECT IDENTIFIER ::= { hh3cevtModuleSwitchType 1975 } -- 24-Port 10GBASE Ethernet Optical Interface(SFP+,LC)+4-Port 40GBASE Ethernet Optical Interface Module(QSFP+)(HB),With 1 Expansion Slot
hh3cevtModuleSw-LSXM1TGS48QGHA0             OBJECT IDENTIFIER ::= { hh3cevtModuleSwitchType 1976 } -- 48-Port 10GBASE Ethernet Optical Interface(SFP+,LC)+4-Port 40GBASE Ethernet Optical Interface Module(QSFP+)(HA)
hh3cevtModuleSw-LSXM1TGS48QGHA1             OBJECT IDENTIFIER ::= { hh3cevtModuleSwitchType 1977 } -- 48-Port 10GBASE Ethernet Optical Interface(SFP+,LC)+4-Port 40GBASE Ethernet Optical Interface Module(QSFP+)(HA)
hh3cevtModuleSw-LSXM1CGC2A0                 OBJECT IDENTIFIER ::= { hh3cevtModuleSwitchType 1978 } -- 2-Ports 100G CFP Ethernet Optical Interface Module(CFP)
hh3cevtModuleSw-LSXM1CGC2A1                 OBJECT IDENTIFIER ::= { hh3cevtModuleSwitchType 1979 } -- 2-Ports 100G CFP Ethernet Optical Interface Module(CFP)
hh3cevtModuleSw-LSQM2FWDSC0                 OBJECT IDENTIFIER ::= { hh3cevtModuleSwitchType 1980 } -- Firewall Service Board
hh3cevtModuleSw-LSQM1XPT12TSFD0             OBJECT IDENTIFIER ::= { hh3cevtModuleSwitchType 1981 } -- 12-Port 10/1GBASE EPON OLT Optical Interface(XFP,LC)+8-Port 10GBASE-R Ethernet Optical Interface Board(SFP+,LC)
hh3cevtModuleSw-LSXM1QGS24HB0               OBJECT IDENTIFIER ::= { hh3cevtModuleSwitchType 1982 } -- 24-Port 40GBASE Ethernet Optical Interface Module(QSFP+)(HB)
hh3cevtModuleSw-LSXM1QGS24HB1               OBJECT IDENTIFIER ::= { hh3cevtModuleSwitchType 1983 } -- 24-Port 40GBASE Ethernet Optical Interface Module(QSFP+)(HB)
hh3cevtModuleSw-LSXM1QGS24HC0               OBJECT IDENTIFIER ::= { hh3cevtModuleSwitchType 1984 } -- 24-Port 40GBASE Ethernet Optical Interface Module(QSFP+)(HC)
hh3cevtModuleSw-LSXM1SUP01B1                OBJECT IDENTIFIER ::= { hh3cevtModuleSwitchType 1985 } -- Supervisor Engine Board
hh3cevtModuleSw-LSCM1SUP03A0                OBJECT IDENTIFIER ::= { hh3cevtModuleSwitchType 1986 } -- Supervisor Engine Board
hh3cevtModuleSw-LSCM1SUP03A0-Z              OBJECT IDENTIFIER ::= { hh3cevtModuleSwitchType 1987 } -- Supervisor Engine Board
hh3cevtModuleSw-LSCM1MPUS06A0               OBJECT IDENTIFIER ::= { hh3cevtModuleSwitchType 1988 } -- Supervisor Engine Board
hh3cevtModuleSw-LSCM1MPUS06A0-Z             OBJECT IDENTIFIER ::= { hh3cevtModuleSwitchType 1989 } -- Supervisor Engine Board
hh3cevtModuleSw-LSCM1GT48SC0                OBJECT IDENTIFIER ::= { hh3cevtModuleSwitchType 1990 } -- 48-Port 10/100/1000BASE-T Electrical Interface Board(RJ45)(SC)
hh3cevtModuleSw-LSCM1GT48SC0-Z              OBJECT IDENTIFIER ::= { hh3cevtModuleSwitchType 1991 } -- 48-Port 10/100/1000BASE-T Electrical Interface Board(RJ45)(SC)
hh3cevtModuleSw-LSCM1TGS48SE0               OBJECT IDENTIFIER ::= { hh3cevtModuleSwitchType 1992 } -- 48-Port 10GBASE-R Ethernet SFP+ Optical Interface Board(SE)
hh3cevtModuleSw-LSCM1TGS48SE0-Z             OBJECT IDENTIFIER ::= { hh3cevtModuleSwitchType 1993 } -- 48-Port 10GBASE-R Ethernet SFP+ Optical Interface Board(SE)
hh3cevtModuleSw-LSCM1QGS8CSSE0              OBJECT IDENTIFIER ::= { hh3cevtModuleSwitchType 1994 } -- 8-Port 40GBASE-R QSFP+ + 4-Port 100GBASE-R QSFP28 Optical Interface Board(SE)
hh3cevtModuleSw-LSCM1QGS8CSSE0-Z            OBJECT IDENTIFIER ::= { hh3cevtModuleSwitchType 1995 } -- 8-Port 40GBASE-R QSFP+ + 4-Port 100GBASE-R QSFP28 Optical Interface Board(SE)
hh3cevtModuleSw-LSWM2SP4P                   OBJECT IDENTIFIER ::= { hh3cevtModuleSwitchType 1996 } -- 4-Port 10GBASE-R Ethernet SFP+ Optical Interface Module
hh3cevtModuleSw-LSWM2SP4P-Z                 OBJECT IDENTIFIER ::= { hh3cevtModuleSwitchType 1997 } -- 4-Port 10GBASE-R Ethernet SFP+ Optical Interface Module
hh3cevtModuleSw-LSQM1MPUS10B0               OBJECT IDENTIFIER ::= { hh3cevtModuleSwitchType 1998 } -- Supervisor Engine Board
hh3cevtModuleSw-LSQM1MPUS10B3               OBJECT IDENTIFIER ::= { hh3cevtModuleSwitchType 1999 } -- Supervisor Engine Board
hh3cevtModuleSw-LSQM1MPUSC0                 OBJECT IDENTIFIER ::= { hh3cevtModuleSwitchType 2000 } -- Supervisor Engine Board
hh3cevtModuleSw-LSQM1MPUSC3                 OBJECT IDENTIFIER ::= { hh3cevtModuleSwitchType 2001 } -- Supervisor Engine Board
hh3cevtModuleSw-LSQM2GP24TSSC8              OBJECT IDENTIFIER ::= { hh3cevtModuleSwitchType 2002 } -- 24-Port 1000BASE-X Optical Interface(SFP,LC)+4-Port 10GBASE-R Ethernet Optical Interface Board(SFP+,LC)(SC)
hh3cevtModuleSw-LSQM2GT24TSSC8              OBJECT IDENTIFIER ::= { hh3cevtModuleSwitchType 2003 } -- 24-Port 10/100/1000BASE-T Electrical Interface(RJ45)+4-Port 10GBASE-R Ethernet Optical Interface Board(SFP+,LC)(SC)
hh3cevtModuleSw-LSXM1TGS24CGMODHD0          OBJECT IDENTIFIER ::= { hh3cevtModuleSwitchType 2004 } -- 24-Port 10GBASE Ethernet Optical Interface(SFP+,LC)+4-Port 100GBASE Ethernet Optical Interface Module(QSFP28)(HD),With 1 Expansion Slot
hh3cevtModuleSw-LSXM1TGS24CGMODHD1          OBJECT IDENTIFIER ::= { hh3cevtModuleSwitchType 2005 } -- 24-Port 10GBASE Ethernet Optical Interface(SFP+,LC)+4-Port 100GBASE Ethernet Optical Interface Module(QSFP28)(HD),With 1 Expansion Slot
hh3cevtModuleSw-LSQM1TGS16GPSA0             OBJECT IDENTIFIER ::= { hh3cevtModuleSwitchType 2006 } -- 24-Port 1000BASE-R Ethernet Optical Interface(SFP,LC)+16-Port 10GBASE-R Ethernet Optical Interface Board(SFP+,LC)
hh3cevtModuleSw-EWPXM2TGS48SG0              OBJECT IDENTIFIER ::= { hh3cevtModuleSwitchType 2007 } -- 48-Port 10GBASE-R Ethernet SFP+ Optical Interface Board(SG)
hh3cevtModuleSw-EWPXM1TGS16FD0              OBJECT IDENTIFIER ::= { hh3cevtModuleSwitchType 2008 } -- 16-Port 10GBASE-R Ethernet SFP+ Optical Interface Board(FD)
hh3cevtModuleSw-LSXM1CGQ36HF0               OBJECT IDENTIFIER ::= { hh3cevtModuleSwitchType 2009 } -- 36-Port 100GBASE Ethernet Optical Interface Module(QSFP28)(HF)
hh3cevtModuleSw-LSXM2SUPT0                  OBJECT IDENTIFIER ::= { hh3cevtModuleSwitchType 2010 } -- Supervisor Engine Board
hh3cevtModuleSw-LSXM2SUPT1                  OBJECT IDENTIFIER ::= { hh3cevtModuleSwitchType 2011 } -- Supervisor Engine Board
hh3cevtModuleSw-LSXM1SFT16E0                OBJECT IDENTIFIER ::= { hh3cevtModuleSwitchType 2012 } -- Switch Fabric Board
hh3cevtModuleSw-LSXM1SFT16E1                OBJECT IDENTIFIER ::= { hh3cevtModuleSwitchType 2013 } -- Switch Fabric Board
hh3cevtModuleSw-lsxM1CGQ36TD0               OBJECT IDENTIFIER ::= { hh3cevtModuleSwitchType 2014 } -- 36-Port 100GBASE Ethernet Optical Interface Board(QSFP28)
hh3cevtModuleSw-lsxM1CGQ36TD1               OBJECT IDENTIFIER ::= { hh3cevtModuleSwitchType 2015 } -- 36-Port 100GBASE Ethernet Optical Interface Board(QSFP28)
hh3cevtModuleSw-LSQM1TGT24FD0               OBJECT IDENTIFIER ::= { hh3cevtModuleSwitchType 2016 } -- 24-Port 10GBASE-T Ethernet Copper Interface Module(RJ45)(FD)
hh3cevtModuleSw-LSUM1TGT24FD0               OBJECT IDENTIFIER ::= { hh3cevtModuleSwitchType 2017 } -- 24-Port 10GBASE-T Ethernet Copper Interface Module(RJ45)(FD)
hh3cevtModuleSw-LSXM2SFT08E0                OBJECT IDENTIFIER ::= { hh3cevtModuleSwitchType 2018 } -- S12508F-AF Fabric Module,Type T(Class E)
hh3cevtModuleSw-LSXM2SFT08E1                OBJECT IDENTIFIER ::= { hh3cevtModuleSwitchType 2019 } -- S12508F-AF Fabric Module,Type T(Class E)
hh3cevtModuleSw-LSXM1CCP8HF0                OBJECT IDENTIFIER ::= { hh3cevtModuleSwitchType 2020 } -- 8-Port 200GBASE Ethernet Optical Interface Module(CFP2)(HF)
hh3cevtModuleSw-LSXM1CCP8HF1                OBJECT IDENTIFIER ::= { hh3cevtModuleSwitchType 2021 } -- 8-Port 200GBASE Ethernet Optical Interface Module(CFP2)(HF)



hh3cevtModuleSw-S8610-MPU                   OBJECT IDENTIFIER ::= { hh3cevtModuleSwitchType 2028 } -- Supervisor Engine Board
hh3cevtModuleSw-S8610-NET                   OBJECT IDENTIFIER ::= { hh3cevtModuleSwitchType 2029 } -- Switching Fabric Module
hh3cevtModuleSw-S86-44GF4XFSE               OBJECT IDENTIFIER ::= { hh3cevtModuleSwitchType 2030 } -- 44-Port GE Optical Interface(SFP,LC)+4-Port 10GE Optical Interface Board(SFP+,LC)(SE)
hh3cevtModuleSw-S86-48GTSE                  OBJECT IDENTIFIER ::= { hh3cevtModuleSwitchType 2031 } -- 48-Port 1000Base-T Gigabit Ethernet Interface Board(RJ45)(SE)
hh3cevtModuleSw-S86-12QFSG                  OBJECT IDENTIFIER ::= { hh3cevtModuleSwitchType 2032 } -- 12-Port 40GBASE-R Ethernet QSFP+ Optical Interface Board(SG)
hh3cevtModuleSw-S86-48XFSG                  OBJECT IDENTIFIER ::= { hh3cevtModuleSwitchType 2033 } -- 48-Port 10GBASE-R Ethernet SFP+ Optical Interface Board(SG)
hh3cevtModuleSw-LSUM1MPUS06XEC0             OBJECT IDENTIFIER ::= { hh3cevtModuleSwitchType 2034 } -- Supervisor Engine Board
hh3cevtModuleSw-LSUM1MPUS10XE0              OBJECT IDENTIFIER ::= { hh3cevtModuleSwitchType 2035 } -- Supervisor Engine Board
hh3cevtModuleSw-LSUM1MPUS10XEB0             OBJECT IDENTIFIER ::= { hh3cevtModuleSwitchType 2036 } -- Supervisor Engine Board
hh3cevtModuleSw-LSUM1FAB06XEC0              OBJECT IDENTIFIER ::= { hh3cevtModuleSwitchType 2037 } -- Switch Fabric Board
hh3cevtModuleSw-LSUM1FAB10XE0               OBJECT IDENTIFIER ::= { hh3cevtModuleSwitchType 2038 } -- Switch Fabric Board
hh3cevtModuleSw-LSUM1FAB10XEB0              OBJECT IDENTIFIER ::= { hh3cevtModuleSwitchType 2039 } -- Switch Fabric Board
hh3cevtModuleSw-LSUM1FAB08XEB0              OBJECT IDENTIFIER ::= { hh3cevtModuleSwitchType 2040 } -- Switch Fabric Board
hh3cevtModuleSw-LSUM1TGS48SH0               OBJECT IDENTIFIER ::= { hh3cevtModuleSwitchType 2041 } -- 48-Port 10G Ethernet Optical Interface Module(SFP+,LC)(SH)
hh3cevtModuleSw-LSUM1CGS8SH0                OBJECT IDENTIFIER ::= { hh3cevtModuleSwitchType 2042 } -- 8-Port 100G Ethernet Optical Interface Module(QSFP28)(SH)
hh3cevtModuleSw-LSUM1YGS24CSSH0             OBJECT IDENTIFIER ::= { hh3cevtModuleSwitchType 2043 } -- 24-Port 25G Ethernet Optical Interface(SFP28,LC)+4-Port 100G Ethernet Optical Interface Module(QSFP28)(SH)
hh3cevtModuleSw-LSUM1CGS20XSH0              OBJECT IDENTIFIER ::= { hh3cevtModuleSwitchType 2044 } -- 20-Port 100G Ethernet Optical Interface Module(QSFP28)(SH)
hh3cevtModuleSw-LSUM1CGS32XSH0              OBJECT IDENTIFIER ::= { hh3cevtModuleSwitchType 2045 } -- 32-Port 100G Ethernet Optical Interface Module(QSFP28)(SH)
hh3cevtModuleSw-LSUM1CGS8QSSH0              OBJECT IDENTIFIER ::= { hh3cevtModuleSwitchType 2046 } -- 8-Port 100G Ethernet Optical Interface Module(QSFP28) +8-port 40G/4-Port 100G Ethernet Optical Interface Module(QSFP28)(SH)
hh3cevtModuleSw-LSUM1YGS48XSH0              OBJECT IDENTIFIER ::= { hh3cevtModuleSwitchType 2047 } -- 48-Port 25G Ethernet Optical Interface(SFP28,LC)(SH)
hh3cevtModuleSw-LSXM3SUPT1                  OBJECT IDENTIFIER ::= { hh3cevtModuleSwitchType 2048 } -- Comware 9 Type-H Supervisor Engine Unit
hh3cevtModuleSw-LSXM4SUPT1                  OBJECT IDENTIFIER ::= { hh3cevtModuleSwitchType 2049 } -- Comware 9 Type-T Supervisor Engine Unit
hh3cevtModuleSw-LSQM2GP24TSSA0-Z            OBJECT IDENTIFIER ::= { hh3cevtModuleSwitchType 2050 } -- 24-Port GE Optical Interface(SFP,LC)+4-Port 10GE Optical Interface Board(SFP+,LC)(SA)
hh3cevtModuleSw-LSQM2GT48SA0-Z              OBJECT IDENTIFIER ::= { hh3cevtModuleSwitchType 2051 } -- 48-Port 1000Base-T Gigabit Ethernet Interface Board(RJ45)(SA)
hh3cevtModuleSw-LSQM2GP48SA0-Z              OBJECT IDENTIFIER ::= { hh3cevtModuleSwitchType 2052 } -- 48-Port 1000BASE-X Ethernet Optical Interface Board(SFP,LC)(SA)
hh3cevtModuleSw-LSUM2TGS48SG0-Z             OBJECT IDENTIFIER ::= { hh3cevtModuleSwitchType 2053 } -- 48-Port 10GBASE-R Ethernet SFP+ Optical Interface Board(SG)
hh3cevtModuleSw-LSUM2QGS12SG0-Z             OBJECT IDENTIFIER ::= { hh3cevtModuleSwitchType 2054 } -- 12-Port 40GBASE-R Ethernet QSFP+ Optical Interface Board(SG)
hh3cevtModuleSw-LSUM2TGS32QSSG0-Z           OBJECT IDENTIFIER ::= { hh3cevtModuleSwitchType 2055 } -- 32-Port 10GBASE-R Ethernet Optical Interface(SFP+,LC)+4-Port 40GBASE-R Ethernet Optical Interface Board(QSFP+,LC)(SG)
hh3cevtModuleSw-LSUM1TGS48RSH0              OBJECT IDENTIFIER ::= { hh3cevtModuleSwitchType 2056 } -- 48-Port 10GBASE-R Ethernet Optical Interface Module(SFP+,LC)(SH)
hh3cevtModuleSw-LSUM1MPUS06XEB0             OBJECT IDENTIFIER ::= { hh3cevtModuleSwitchType 2057 } -- Supervisor Engine Board
hh3cevtModuleSw-LSUM1MPUS10XEA0             OBJECT IDENTIFIER ::= { hh3cevtModuleSwitchType 2058 } -- Supervisor Engine Board
hh3cevtModuleSw-LSUM1FAB06XEB0              OBJECT IDENTIFIER ::= { hh3cevtModuleSwitchType 2059 } -- Switch Fabric Board
hh3cevtModuleSw-LSUM1FAB10XEA0              OBJECT IDENTIFIER ::= { hh3cevtModuleSwitchType 2060 } -- Switch Fabric Board
hh3cevtModuleSw-EWPXM1WCMX100               OBJECT IDENTIFIER ::= { hh3cevtModuleSwitchType 2061 } -- Access Controller Service Board
hh3cevtModuleSw-LSQM1WBCZ720X               OBJECT IDENTIFIER ::= { hh3cevtModuleSwitchType 2062 } -- Access Controller Service Board
hh3cevtModuleSw-LSUM1WBCZ720XRT             OBJECT IDENTIFIER ::= { hh3cevtModuleSwitchType 2063 } -- Access Controller Service Board
hh3cevtModuleSw-LSXM1CGQ8TD1                OBJECT IDENTIFIER ::= { hh3cevtModuleSwitchType 2064 } -- 8-Port 100GBASE  Ethernet Optical Interface Board(QSFP28)
hh3cevtModuleSw-LSXM1CGQ12TD1               OBJECT IDENTIFIER ::= { hh3cevtModuleSwitchType 2065 } -- 12-Port 100GBASE  Ethernet Optical Interface Board(QSFP28)
hh3cevtModuleSw-LSXM1CGQ18TD1               OBJECT IDENTIFIER ::= { hh3cevtModuleSwitchType 2066 } -- 18-Port 100GBASE  Ethernet Optical Interface Board(QSFP28)
hh3cevtModuleSw-LSXM1QGS24C6TD1             OBJECT IDENTIFIER ::= { hh3cevtModuleSwitchType 2067 } -- 24-Port 40GBASE Ethernet Optical Interface Module (QSFP+) + 6-Port 100GBASE (QSFP28)
hh3cevtModuleSw-LSXM1QGS36TD1               OBJECT IDENTIFIER ::= { hh3cevtModuleSwitchType 2068 } -- 36-Port 40GBASE Ethernet Optical Interface Module(QSFP+)
hh3cevtModuleSw-LSXM1QGS48TD1               OBJECT IDENTIFIER ::= { hh3cevtModuleSwitchType 2069 } -- 48-Port 40GBASE Ethernet Optical Interface Module(QSFP+)
hh3cevtModuleSw-LSXM1TGS48C4TD1             OBJECT IDENTIFIER ::= { hh3cevtModuleSwitchType 2070 } -- 48-Port 10GBASE Ethernet Optical Interface(SFP+,LC)+4-Port 100GBASE Ethernet Optical Interface Module(QSFP28)
hh3cevtModuleSw-LSXM1GP48TD1                OBJECT IDENTIFIER ::= { hh3cevtModuleSwitchType 2071 } -- 48-Port GE BASE Ethernet Optical Interface Module(SFP,LC))
hh3cevtModuleSw-LSXM1TGS48TD1               OBJECT IDENTIFIER ::= { hh3cevtModuleSwitchType 2072 } -- 48-Port 10G BASE Ethernet Optical Interface Module(SFP+,LC))




hh3cevtModuleSw-LSWM124TG2H1               OBJECT IDENTIFIER ::= { hh3cevtModuleSwitchType 2076 }
hh3cevtModuleSw-LSQM2FWDSC8                OBJECT IDENTIFIER ::= { hh3cevtModuleSwitchType 2077 }

hh3cevtModuleSw-IM-MSEX-B                  OBJECT IDENTIFIER ::= { hh3cevtModuleSwitchType 2080 } -- Service Processing Unit(IM-MSEX-B)
hh3cevtModuleSw-IM-MSEX-B-IM-SP-B          OBJECT IDENTIFIER ::= { hh3cevtModuleSwitchType 2081 } -- Service Processing Unit + Universal Line Processing Interface Card(IM-MSEX-B-IM-SP-B)
hh3cevtModuleSw-LSUM1MPUS06XEC0-Z          OBJECT IDENTIFIER ::= { hh3cevtModuleSwitchType 2082 }
hh3cevtModuleSw-LSUM1CGS8SH0-Z             OBJECT IDENTIFIER ::= { hh3cevtModuleSwitchType 2083 }
hh3cevtModuleSw-LSUM1SUPXD0-Z              OBJECT IDENTIFIER ::= { hh3cevtModuleSwitchType 2084 }
hh3cevtModuleSw-LSUM1FAB08XE0-Z            OBJECT IDENTIFIER ::= { hh3cevtModuleSwitchType 2085 }
hh3cevtModuleSw-LSUM1CGS20XSH0-Z           OBJECT IDENTIFIER ::= { hh3cevtModuleSwitchType 2086 }
hh3cevtModuleSw-LSUM1FAB06XEC0-Z           OBJECT IDENTIFIER ::= { hh3cevtModuleSwitchType 2087 }
hh3cevtModuleSw-LSUM1CQGS32SF0-Z           OBJECT IDENTIFIER ::= { hh3cevtModuleSwitchType 2088 }
hh3cevtModuleSw-LSXM1FAB10XE3              OBJECT IDENTIFIER ::= { hh3cevtModuleSwitchType 2089 }
hh3cevtModuleSw-LSXM1FAB08XE3              OBJECT IDENTIFIER ::= { hh3cevtModuleSwitchType 2090 }
hh3cevtModuleSw-LSXM1YGS48XSH3             OBJECT IDENTIFIER ::= { hh3cevtModuleSwitchType 2091 }
hh3cevtModuleSw-LSXM1YGS24CSSH3            OBJECT IDENTIFIER ::= { hh3cevtModuleSwitchType 2092 }
hh3cevtModuleSw-LSXM1CGS8QSSH3             OBJECT IDENTIFIER ::= { hh3cevtModuleSwitchType 2093 }
hh3cevtModuleSw-LSXM1TGS48SH3              OBJECT IDENTIFIER ::= { hh3cevtModuleSwitchType 2094 }
hh3cevtModuleSw-LSXM1MPUS10XE3             OBJECT IDENTIFIER ::= { hh3cevtModuleSwitchType 2095 }
hh3cevtModuleSw-LSXM1FAB06XEC3             OBJECT IDENTIFIER ::= { hh3cevtModuleSwitchType 2096 }
hh3cevtModuleSw-LSXM1MPUS06XEC3            OBJECT IDENTIFIER ::= { hh3cevtModuleSwitchType 2097 }
hh3cevtModuleSw-LSXM1CGS8SH3               OBJECT IDENTIFIER ::= { hh3cevtModuleSwitchType 2098 }
hh3cevtModuleSw-LSXM1SUPXD3                OBJECT IDENTIFIER ::= { hh3cevtModuleSwitchType 2099 }
hh3cevtModuleSw-LSXM1CGS20XSH3             OBJECT IDENTIFIER ::= { hh3cevtModuleSwitchType 2100 }
hh3cevtModuleSw-LSUM1GP48FD0-Z             OBJECT IDENTIFIER ::= { hh3cevtModuleSwitchType 2101 }
hh3cevtModuleSw-LSQM1TGS48RFE0-Z           OBJECT IDENTIFIER ::= { hh3cevtModuleSwitchType 2102 }
hh3cevtModuleSw-LSXM1CGS32XSH3             OBJECT IDENTIFIER ::= { hh3cevtModuleSwitchType 2103 }
hh3cevtModuleSw-LSQM2GP40TS8FD0            OBJECT IDENTIFIER ::= { hh3cevtModuleSwitchType 2104 }
hh3cevtModuleSw-LSUM1SUPXES0               OBJECT IDENTIFIER ::= { hh3cevtModuleSwitchType 2105 }
hh3cevtModuleSw-LSQM2SUPB0                 OBJECT IDENTIFIER ::= { hh3cevtModuleSwitchType 2106 }
hh3cevtModuleSw-LSUM2GP40TS8FD0            OBJECT IDENTIFIER ::= { hh3cevtModuleSwitchType 2107 }
hh3cevtModuleSw-LSXM1YGS48XXSH3            OBJECT IDENTIFIER ::= { hh3cevtModuleSwitchType 2108 }
hh3cevtModuleSw-LSXM2SFT08E2               OBJECT IDENTIFIER ::= { hh3cevtModuleSwitchType 2109 }
hh3cevtModuleSw-LSXM1TGS48TD2              OBJECT IDENTIFIER ::= { hh3cevtModuleSwitchType 2110 }
hh3cevtModuleSw-LSXM1CGQ36TD2              OBJECT IDENTIFIER ::= { hh3cevtModuleSwitchType 2111 }
hh3cevtModuleSw-RX-NIC-LGQ4L               OBJECT IDENTIFIER ::= { hh3cevtModuleSwitchType 2112 } -- 4-port 50G Ethernet Optical Interface Card(QSFP28,LC)(RX-NIC)
hh3cevtModuleSw-LSXM1CDQ24KB1              OBJECT IDENTIFIER ::= { hh3cevtModuleSwitchType 2113 }
hh3cevtModuleSw-LSXM1SUP02L1               OBJECT IDENTIFIER ::= { hh3cevtModuleSwitchType 2114 }
hh3cevtModuleSw-LSXM1CGQ48KB1              OBJECT IDENTIFIER ::= { hh3cevtModuleSwitchType 2115 }
hh3cevtModuleSw-LSXM1SFK08F1               OBJECT IDENTIFIER ::= { hh3cevtModuleSwitchType 2116 }
hh3cevtModuleSw-CSPEX-1214X                OBJECT IDENTIFIER ::= { hh3cevtModuleSwitchType 2117 }
hh3cevtModuleSw-MIC-CQ1L1                  OBJECT IDENTIFIER ::= { hh3cevtModuleSwitchType 2118 } -- 1-port 100G Ethernet Optical Interface Card(QSFP28)
hh3cevtModuleSw-DS-3E7600-16X-SCB          OBJECT IDENTIFIER ::= { hh3cevtModuleSwitchType 2119 }
hh3cevtModuleSw-DS-3E12508-MPU             OBJECT IDENTIFIER ::= { hh3cevtModuleSwitchType 2120 }
hh3cevtModuleSw-DS-3E12500-7610-48T-SE     OBJECT IDENTIFIER ::= { hh3cevtModuleSwitchType 2121 }
hh3cevtModuleSw-DS-3E7603-MPU              OBJECT IDENTIFIER ::= { hh3cevtModuleSwitchType 2122 }
hh3cevtModuleSw-DS-3E12500-7610-16X-SF     OBJECT IDENTIFIER ::= { hh3cevtModuleSwitchType 2123 }
hh3cevtModuleSw-DS-3E12500-24T20F4X-SE     OBJECT IDENTIFIER ::= { hh3cevtModuleSwitchType 2124 }
hh3cevtModuleSw-DS-3E12500-12Q-SG          OBJECT IDENTIFIER ::= { hh3cevtModuleSwitchType 2125 }
hh3cevtModuleSw-DS-3E12500-48X-SG          OBJECT IDENTIFIER ::= { hh3cevtModuleSwitchType 2126 }
hh3cevtModuleSw-DS-3E12500-7610-32X4QX-SF  OBJECT IDENTIFIER ::= { hh3cevtModuleSwitchType 2127 }
hh3cevtModuleSw-DS-3E12500-7610-44F4X-SE   OBJECT IDENTIFIER ::= { hh3cevtModuleSwitchType 2128 }
hh3cevtModuleSw-DS-3E12508-CLOS            OBJECT IDENTIFIER ::= { hh3cevtModuleSwitchType 2129 }
hh3cevtModuleSw-LSXM2SUPT2                 OBJECT IDENTIFIER ::= { hh3cevtModuleSwitchType 2130 }
hh3cevtModuleSw-CSR05SRP1P3A               OBJECT IDENTIFIER ::= { hh3cevtModuleSwitchType 2131 } -- CR16000-FA Main Processing Unit(1P3A)
hh3cevtModuleSw-CSFC-08E1A                 OBJECT IDENTIFIER ::= { hh3cevtModuleSwitchType 2132 } -- CR16010H-FA Fabric Module(E Type)
hh3cevtModuleSw-CSFC-16EA                  OBJECT IDENTIFIER ::= { hh3cevtModuleSwitchType 2133 } -- CR16018-FA Fabric Module(E Type)
hh3cevtModuleSw-CSPEX-1602XA               OBJECT IDENTIFIER ::= { hh3cevtModuleSwitchType 2134 } -- Service Processing Unit(1602XA)
hh3cevtModuleSw-CEPC-CP4RXA                OBJECT IDENTIFIER ::= { hh3cevtModuleSwitchType 2135 } -- 4-port 100GBASE Ethernet Optical Interface Line Processing Unit A(CFP2)
hh3cevtModuleSw-CSPEX-1504XA               OBJECT IDENTIFIER ::= { hh3cevtModuleSwitchType 2136 } -- Service Processing Unit(1504XA)
hh3cevtModuleSw-CSPEX-1804XA               OBJECT IDENTIFIER ::= { hh3cevtModuleSwitchType 2137 } -- Service Processing Unit(1804XA)
hh3cevtModuleSw-MIC-GP10LA                 OBJECT IDENTIFIER ::= { hh3cevtModuleSwitchType 2138 } -- 10-port 1000BASE-X Ethernet Optical Interface Card A(SFP,LC)
hh3cevtModuleSw-MIC-GT20LA                 OBJECT IDENTIFIER ::= { hh3cevtModuleSwitchType 2139 } -- 20-port 1000BASE-X Ethernet Copper Interface Card A(RJ45)
hh3cevtModuleSw-MIC-XP20LA                 OBJECT IDENTIFIER ::= { hh3cevtModuleSwitchType 2140 } -- 20-port 10GBASE-R/W Ethernet Optical Interface Card A(SFP+,LC)

hh3cevtModuleSw-LSDM1QGS12SE0-Z            OBJECT IDENTIFIER ::= { hh3cevtModuleSwitchType 2142 }
hh3cevtModuleSw-LSDM1TGS48SE0-Z            OBJECT IDENTIFIER ::= { hh3cevtModuleSwitchType 2143 }
hh3cevtModuleSw-LSDM1SUPA0-Z               OBJECT IDENTIFIER ::= { hh3cevtModuleSwitchType 2144 }
hh3cevtModuleSw-LSDM1FAB08D0-Z             OBJECT IDENTIFIER ::= { hh3cevtModuleSwitchType 2145 }
hh3cevtModuleSw-LSDM1GT24GPSE0-Z           OBJECT IDENTIFIER ::= { hh3cevtModuleSwitchType 2146 }
hh3cevtModuleSw-LSXM1CGQ18TD2              OBJECT IDENTIFIER ::= { hh3cevtModuleSwitchType 2147 }
hh3cevtModuleSw-LSXM1QGS36TD2              OBJECT IDENTIFIER ::= { hh3cevtModuleSwitchType 2148 }
hh3cevtModuleSw-RP-S-G                     OBJECT IDENTIFIER ::= { hh3cevtModuleSwitchType 2149 }
hh3cevtModuleSw-MOD20-G                    OBJECT IDENTIFIER ::= { hh3cevtModuleSwitchType 2150 }
hh3cevtModuleSw-MPA-PSP4L-G                OBJECT IDENTIFIER ::= { hh3cevtModuleSwitchType 2151 }
hh3cevtModuleSw-MPA-TCP8L-G                OBJECT IDENTIFIER ::= { hh3cevtModuleSwitchType 2152 }
hh3cevtModuleSw-MPA-ET16L-G                OBJECT IDENTIFIER ::= { hh3cevtModuleSwitchType 2153 }
hh3cevtModuleSw-MPA-GP10L-G                OBJECT IDENTIFIER ::= { hh3cevtModuleSwitchType 2154 }
hh3cevtModuleSw-MPA-XP4L-G                 OBJECT IDENTIFIER ::= { hh3cevtModuleSwitchType 2155 }
hh3cevtModuleSw-LSXM1SFH04DR1              OBJECT IDENTIFIER ::= { hh3cevtModuleSwitchType 2156 }
hh3cevtModuleSw-LSXM1SFH08CR1              OBJECT IDENTIFIER ::= { hh3cevtModuleSwitchType 2157 }
hh3cevtModuleSw-LSXM1SFH08DR1              OBJECT IDENTIFIER ::= { hh3cevtModuleSwitchType 2158 }
hh3cevtModuleSw-LSXM1SFH16CR1              OBJECT IDENTIFIER ::= { hh3cevtModuleSwitchType 2159 }
hh3cevtModuleSw-LSXM1SFH16ER1              OBJECT IDENTIFIER ::= { hh3cevtModuleSwitchType 2160 }
hh3cevtModuleSw-LSXM1TGS48HFR1             OBJECT IDENTIFIER ::= { hh3cevtModuleSwitchType 2161 }
hh3cevtModuleSw-LSXM1CGQ18QGHFR1           OBJECT IDENTIFIER ::= { hh3cevtModuleSwitchType 2162 }
hh3cevtModuleSw-LSXM1SUP04TR1              OBJECT IDENTIFIER ::= { hh3cevtModuleSwitchType 2163 }
hh3cevtModuleSw-LSXM1CGQ36HBR1             OBJECT IDENTIFIER ::= { hh3cevtModuleSwitchType 2164 }
hh3cevtModuleSw-LSXM1CGQ36HFR1             OBJECT IDENTIFIER ::= { hh3cevtModuleSwitchType 2165 }
hh3cevtModuleSw-LSXM1CGQ6QGHFR1            OBJECT IDENTIFIER ::= { hh3cevtModuleSwitchType 2166 }
hh3cevtModuleSw-LSXM1TGS48HBR1             OBJECT IDENTIFIER ::= { hh3cevtModuleSwitchType 2167 }
hh3cevtModuleSw-LSXM1CGQ18QGHBR1           OBJECT IDENTIFIER ::= { hh3cevtModuleSwitchType 2168 }
hh3cevtModuleSw-LSXM1SUPER1                OBJECT IDENTIFIER ::= { hh3cevtModuleSwitchType 2169 }
hh3cevtModuleSw-LSQM1SDNB0                 OBJECT IDENTIFIER ::= { hh3cevtModuleSwitchType 2170 } -- SDN-engine Blade
hh3cevtModuleSw-LSUM1SDNB0                 OBJECT IDENTIFIER ::= { hh3cevtModuleSwitchType 2171 } -- SDN-engine Blade
hh3cevtModuleSw-LSQM1EPSB0                 OBJECT IDENTIFIER ::= { hh3cevtModuleSwitchType 2172 } -- EPS-engine Blade
hh3cevtModuleSw-LSUM1EPSB0                 OBJECT IDENTIFIER ::= { hh3cevtModuleSwitchType 2173 } -- EPS-engine Blade
hh3cevtModuleSw-LSXM2TGS48HB2              OBJECT IDENTIFIER ::= { hh3cevtModuleSwitchType 2174 }
hh3cevtModuleSw-LSXM2CGQ18QGHB2            OBJECT IDENTIFIER ::= { hh3cevtModuleSwitchType 2175 }
hh3cevtModuleSw-LSUM1CGS8SH3               OBJECT IDENTIFIER ::= { hh3cevtModuleSwitchType 2176 }
hh3cevtModuleSw-LSUM1GT48FC3               OBJECT IDENTIFIER ::= { hh3cevtModuleSwitchType 2177 }
hh3cevtModuleSw-LSUM1FAB10XEA3             OBJECT IDENTIFIER ::= { hh3cevtModuleSwitchType 2178 }
hh3cevtModuleSw-LSUM1TGS48SH3              OBJECT IDENTIFIER ::= { hh3cevtModuleSwitchType 2179 }
hh3cevtModuleSw-LSUM1MPUS10XE3             OBJECT IDENTIFIER ::= { hh3cevtModuleSwitchType 2180 }
hh3cevtModuleSw-LSUM1GP48FC3               OBJECT IDENTIFIER ::= { hh3cevtModuleSwitchType 2181 }
hh3cevtModuleSw-LSQM1TGS16FD0-Z            OBJECT IDENTIFIER ::= { hh3cevtModuleSwitchType 2182 }
hh3cevtModuleSw-LSQM2SUPA0-Z               OBJECT IDENTIFIER ::= { hh3cevtModuleSwitchType 2183 }
hh3cevtModuleSw-LSUM1TGS16FD0-Z            OBJECT IDENTIFIER ::= { hh3cevtModuleSwitchType 2184 }
hh3cevtModuleSw-LSWM2FPGAB                 OBJECT IDENTIFIER ::= { hh3cevtModuleSwitchType 2185 }
hh3cevtModuleSw-LSWM2EC                    OBJECT IDENTIFIER ::= { hh3cevtModuleSwitchType 2186 } -- EScaner
hh3cevtModuleSw-LSWM2FPGA                  OBJECT IDENTIFIER ::= { hh3cevtModuleSwitchType 2187 }
hh3cevtModuleSw-LSWM2ZSP4P                 OBJECT IDENTIFIER ::= { hh3cevtModuleSwitchType 2188 }
hh3cevtModuleSw-LSXM1CGQ8TD2               OBJECT IDENTIFIER ::= { hh3cevtModuleSwitchType 2189 }
hh3cevtModuleSw-LSXM1TGS48C4TD2            OBJECT IDENTIFIER ::= { hh3cevtModuleSwitchType 2190 }
hh3cevtModuleSw-LSXM1QGS24C6TD2            OBJECT IDENTIFIER ::= { hh3cevtModuleSwitchType 2191 }
hh3cevtModuleSw-LSCM1MPUS06A8              OBJECT IDENTIFIER ::= { hh3cevtModuleSwitchType 2192 }
hh3cevtModuleSw-LSCM1TGS48SC8              OBJECT IDENTIFIER ::= { hh3cevtModuleSwitchType 2193 }
hh3cevtModuleSw-LSQM1MPUS06S0              OBJECT IDENTIFIER ::= { hh3cevtModuleSwitchType 2194 }
hh3cevtModuleSw-LSQM1SRP4Y06A0             OBJECT IDENTIFIER ::= { hh3cevtModuleSwitchType 2195 }
hh3cevtModuleSw-S76-16XFSF-E               OBJECT IDENTIFIER ::= { hh3cevtModuleSwitchType 2196 }
hh3cevtModuleSw-S7603-MPU                  OBJECT IDENTIFIER ::= { hh3cevtModuleSwitchType 2197 }
hh3cevtModuleSw-LSCM2MPUS06AS8             OBJECT IDENTIFIER ::= { hh3cevtModuleSwitchType 2198 }  -- Supervisor Engine Board
hh3cevtModuleSw-LSCM2CGT24TSSC8            OBJECT IDENTIFIER ::= { hh3cevtModuleSwitchType 2199 }  -- Supervisor Engine Board With 24-Port 10/100/1000BASE-T Ethernet Interface+4-Port 10GBASE-R Ethernet SFP+ Optical Interfaces
hh3cevtModuleSw-LSCM2CGP24TSSC8            OBJECT IDENTIFIER ::= { hh3cevtModuleSwitchType 2200 }  -- Supervisor Engine Board With 24-Port 1000BASE-X Ethernet SFP Optical Interface+4-Port 10GBASE-R Ethernet SFP+ Optical Interfaces
hh3cevtModuleSw-LSCM2CTGS12GTSC8           OBJECT IDENTIFIER ::= { hh3cevtModuleSwitchType 2201 }  -- Supervisor Engine Board With 16-Port 10/100/1000BASE-T Ethernet Interface+12-Port 10GBASE-R Ethernet SFP+ Optical Interfaces
hh3cevtModuleSw-LSCM2CTGS12GPSC8           OBJECT IDENTIFIER ::= { hh3cevtModuleSwitchType 2202 }  -- Supervisor Engine Board With 16-Port 1000BASE-X Ethernet SFP Optical Interface+12-Port 10GBASE-R Ethernet SFP+ Optical Interfaces
hh3cevtModuleSw-LSCM2GT24GPTSSC8           OBJECT IDENTIFIER ::= { hh3cevtModuleSwitchType 2203 }  -- 24-Port 10/100/1000BASE-T Ethernet Interface Board(RJ45)+20-Port 1000BASE-X Ethernet SFP Optical Interface(SFP,LC)+4-Port 10GBASE-R Optical Interface Board(SFP+,LC)(SC)
hh3cevtModuleSw-LSCM2GT24GPSC8             OBJECT IDENTIFIER ::= { hh3cevtModuleSwitchType 2204 }  -- 24-Port 10/100/1000BASE-T Ethernet Interface Board(RJ45)+8-Port 1000BASE-X Ethernet SFP Optical Interface(SFP,LC)(SC)
hh3cevtModuleSw-LSCM2GP24GTSC8             OBJECT IDENTIFIER ::= { hh3cevtModuleSwitchType 2205 }  -- 8-Port 10/100/1000BASE-T Ethernet Interface Board(RJ45)+24-Port 1000BASE-X Ethernet SFP Optical Interface(SFP,LC)(SC)
hh3cevtModuleSw-LSCM2GT48SC8               OBJECT IDENTIFIER ::= { hh3cevtModuleSwitchType 2206 }  -- 48-Port 10/100/1000BASE-T Ethernet Interface Board(RJ45)(SC)
hh3cevtModuleSw-LSCM2GP48SC8               OBJECT IDENTIFIER ::= { hh3cevtModuleSwitchType 2207 }  -- 48-Port 1000BASE-X Ethernet Optical Interface Board(SFP,LC)
hh3cevtModuleSw-LSCM2TGS16GPSC8            OBJECT IDENTIFIER ::= { hh3cevtModuleSwitchType 2208 }  -- 24-Port 1000BASE-R Ethernet Optical Interface(SFP,LC)+16-Port 10GBASE-R Ethernet Optical Interface Board(SFP+,LC)

hh3cevtModuleSw-LSXM2SFH16CR1              OBJECT IDENTIFIER ::= { hh3cevtModuleSwitchType 2209 }  -- Fabric Module,Type H(Class C)
hh3cevtModuleSw-LSXM1SEERBXC2              OBJECT IDENTIFIER ::= { hh3cevtModuleSwitchType 2210 }
hh3cevtModuleSw-LSXM1SEERBG2               OBJECT IDENTIFIER ::= { hh3cevtModuleSwitchType 2211 }
hh3cevtModuleSw-LSXM1SEERBXD2              OBJECT IDENTIFIER ::= { hh3cevtModuleSwitchType 2212 }
hh3cevtModuleSw-LSXM1SFK08FR1              OBJECT IDENTIFIER ::= { hh3cevtModuleSwitchType 2213 }
hh3cevtModuleSw-LSXM1CDQ24KBR1             OBJECT IDENTIFIER ::= { hh3cevtModuleSwitchType 2214 }
hh3cevtModuleSw-LSXM1SUP02LR1              OBJECT IDENTIFIER ::= { hh3cevtModuleSwitchType 2215 }
hh3cevtModuleSw-LSXM1CGQ48KBR1             OBJECT IDENTIFIER ::= { hh3cevtModuleSwitchType 2216 }
hh3cevtModuleSw-LSXM1CGQ36HC0              OBJECT IDENTIFIER ::= { hh3cevtModuleSwitchType 2217 }
hh3cevtModuleSw-LSXM1TGS48TE2              OBJECT IDENTIFIER ::= { hh3cevtModuleSwitchType 2218 }
hh3cevtModuleSw-LSXM1CGQ36TE2              OBJECT IDENTIFIER ::= { hh3cevtModuleSwitchType 2219 }
hh3cevtModuleSw-LSXM1SFT16F1               OBJECT IDENTIFIER ::= { hh3cevtModuleSwitchType 2220 }
hh3cevtModuleSw-LSXM1CGQ18TE2              OBJECT IDENTIFIER ::= { hh3cevtModuleSwitchType 2221 }
hh3cevtModuleSw-LSXM1CGQ8TE2               OBJECT IDENTIFIER ::= { hh3cevtModuleSwitchType 2222 }
hh3cevtModuleSw-LSWM116H                   OBJECT IDENTIFIER ::= { hh3cevtModuleSwitchType 2223 }
hh3cevtModuleSw-LSWM1M4CD                  OBJECT IDENTIFIER ::= { hh3cevtModuleSwitchType 2224 }
hh3cevtModuleSw-LSXM1QGS36TE2              OBJECT IDENTIFIER ::= { hh3cevtModuleSwitchType 2225 }
hh3cevtModuleSw-LSXM1SFT16F2               OBJECT IDENTIFIER ::= { hh3cevtModuleSwitchType 2226 }
hh3cevtModuleSw-CSPEX-1812X-E              OBJECT IDENTIFIER ::= { hh3cevtModuleSwitchType 2227 } -- Service Processing Unit(1812X-E)
hh3cevtModuleSw-MOD20-A3                   OBJECT IDENTIFIER ::= { hh3cevtModuleSwitchType 2228 } -- R9900-S-G,SR0MZLF1DQM1,Service Processing Unit(MOD20-G),Domestic&Overseas Version
hh3cevtModuleSw-RP-S-G-A3                  OBJECT IDENTIFIER ::= { hh3cevtModuleSwitchType 2229 } -- R9900-S-G,SR0MZSRP1A4,Main Processing Unit,Domestic Version
hh3cevtModuleSw-LSXM1SFT16EA1              OBJECT IDENTIFIER ::= { hh3cevtModuleSwitchType 2230 } -- Switch Fabric Board
hh3cevtModuleSw-RP1-S-G                    OBJECT IDENTIFIER ::= { hh3cevtModuleSwitchType 2231 } -- R9900-S-G,SR0MZSRP1A3A,Main Processing Unit(S Type),Domestic&Overseas Version
hh3cevtModuleSw-MOD21-G                    OBJECT IDENTIFIER ::= { hh3cevtModuleSwitchType 2232 } -- R9900-S1-G,SR0MZLF1DQM1,Service Processing Unit(MOD21-G),Domestic&Overseas Version
hh3cevtModuleSw-LSXM1SUPKR1                OBJECT IDENTIFIER ::= { hh3cevtModuleSwitchType 2233 } -- Supervisor Engine Module
hh3cevtModuleSw-LSXM1CDQ36KBR1             OBJECT IDENTIFIER ::= { hh3cevtModuleSwitchType 2234 } -- 36-Port 400GBASE Ethernet Optical Interface Module(QSFP-DD)(KB)
hh3cevtModuleSw-LSXM1CMUR1                 OBJECT IDENTIFIER ::= { hh3cevtModuleSwitchType 2235 } -- Board Monitor Unit
hh3cevtModuleSw-LSXM1SFK16GR1              OBJECT IDENTIFIER ::= { hh3cevtModuleSwitchType 2236 } -- Switch Fabric Board,Type K(Class G)
hh3cevtModuleSw-CSR05SRP1R3                OBJECT IDENTIFIER ::= { hh3cevtModuleSwitchType 2237 } -- CR16000-F,CSR05SRP1R3,Main Processing Unit(1R3)
hh3cevtModuleSw-MIC-TCP8L                  OBJECT IDENTIFIER ::= { hh3cevtModuleSwitchType 2238 } -- SR8800-X, SR0MDTCP8LA1,8-port OC-3c/OC-12c POS Optical Interface Card(SFP,LC),Domestic&Overseas Version
hh3cevtModuleSw-MIC-PSP4L                  OBJECT IDENTIFIER ::= { hh3cevtModuleSwitchType 2239 } -- SR8800-X , SR0MDPSP4LA1,4-port OC-48c/STM-16c POS Optical Interface Card(SFP,LC),Domestic&Overseas Version



hh3cevtModuleSw-LSUM1MPU06B8               OBJECT IDENTIFIER ::= { hh3cevtModuleSwitchType 2240 } -- Supervisor Engine Board
hh3cevtModuleSw-LSUM1MPU10C8               OBJECT IDENTIFIER ::= { hh3cevtModuleSwitchType 2241 } -- Supervisor Engine Board
hh3cevtModuleSw-LSUM1FAB06C8               OBJECT IDENTIFIER ::= { hh3cevtModuleSwitchType 2242 } -- Switching Fabric Module
hh3cevtModuleSw-LSUM1FAB10C8               OBJECT IDENTIFIER ::= { hh3cevtModuleSwitchType 2243 } -- Switching Fabric Module
hh3cevtModuleSw-LSUM1MPU10A8               OBJECT IDENTIFIER ::= { hh3cevtModuleSwitchType 2244 } -- Supervisor Engine Board
hh3cevtModuleSw-LSUM1FAB10A8               OBJECT IDENTIFIER ::= { hh3cevtModuleSwitchType 2245 } -- Switching Fabric Module
hh3cevtModuleSw-LSUM1TGS16FD8              OBJECT IDENTIFIER ::= { hh3cevtModuleSwitchType 2246 } -- 16-Port 10GBASE-R Ethernet SFP+ Optical Interface Board(FD)
hh3cevtModuleSw-LSUM1GP48FD8               OBJECT IDENTIFIER ::= { hh3cevtModuleSwitchType 2247 } -- 48-Port 1000BASE-X Optical Interface Board(SFP,LC)
hh3cevtModuleSw-LSUM1GT48FD8               OBJECT IDENTIFIER ::= { hh3cevtModuleSwitchType 2248 } -- 48-Port 10/100/1000BASE-T Electrical Interface Board(RJ45)
hh3cevtModuleSw-LSUM1GP40TS8FD8            OBJECT IDENTIFIER ::= { hh3cevtModuleSwitchType 2249 } -- 40-Port 1000BASE-X Optical Interface(SFP,LC)+8-Port 10GBASE-R Ethernet Optical Interface Board(SFP+,LC)
hh3cevtModuleSw-LSUM1TGS48RSH8             OBJECT IDENTIFIER ::= { hh3cevtModuleSwitchType 2250 } -- 48-Port 10GBASE-R Ethernet Optical Interface Module(SFP+,LC)(SH)
hh3cevtModuleSw-LSDM1GP48SE0-Z             OBJECT IDENTIFIER ::= { hh3cevtModuleSwitchType 2251 } -- 48-Port 1000BASE-X Ethernet Optical Interface Board(SFP,LC)
hh3cevtModuleSw-LSDM1GT48SE0-Z             OBJECT IDENTIFIER ::= { hh3cevtModuleSwitchType 2252 } -- 48-Port 10/100/1000BASE-T Ethernet Interface Board(RJ45)(SE)
hh3cevtModuleSw-LSDM1CGS8SE0-Z             OBJECT IDENTIFIER ::= { hh3cevtModuleSwitchType 2253 } -- 8-Port 100GBASE-R Ethernet Optical Interface Board(QSFP28,LC)
hh3cevtModuleSw-LSXM1SUP04T2               OBJECT IDENTIFIER ::= { hh3cevtModuleSwitchType 2254 } -- Supervisor Engine Board
hh3cevtModuleSw-LSXM1SFT04F2               OBJECT IDENTIFIER ::= { hh3cevtModuleSwitchType 2255 } -- Switch Fabric Board
hh3cevtModuleSw-LSXM1SFT08F2               OBJECT IDENTIFIER ::= { hh3cevtModuleSwitchType 2256 } -- Switch Fabric Board
hh3cevtModuleSw-RX-NIC-CQ2LF-E             OBJECT IDENTIFIER ::= { hh3cevtModuleSwitchType 2257 } -- 2-port 100G Flexible Ethernet Optical Interface Card(QSFP28,LC)(RX-NIC)
hh3cevtModuleSw-LSUM1TGS24FD8              OBJECT IDENTIFIER ::= { hh3cevtModuleSwitchType 2258 } -- 24-Port 10GBASE-R Ethernet Optical Interface Board(SFP+,LC)
hh3cevtModuleSw-RX-SPE400-E                OBJECT IDENTIFIER ::= { hh3cevtModuleSwitchType 2259 } -- Service Processing Unit(SPE400-E)
hh3cevtModuleSw-LSXM1SFK08GR1              OBJECT IDENTIFIER ::= { hh3cevtModuleSwitchType 2260 } -- Switch Fabric Board,Type K(Class G)
hh3cevtModuleSw-RX-SFC-16T1                OBJECT IDENTIFIER ::= { hh3cevtModuleSwitchType 2261 } -- 1Tbps Fabric Module(16)
hh3cevtModuleSw-LSCM3SUP03A0-Z             OBJECT IDENTIFIER ::= { hh3cevtModuleSwitchType 2262 } -- Supervisor Engine Board
hh3cevtModuleSw-LSCM3MPUS06A0-Z            OBJECT IDENTIFIER ::= { hh3cevtModuleSwitchType 2263 } -- Supervisor Engine Board
hh3cevtModuleSw-LSCM3GT48SC0-Z             OBJECT IDENTIFIER ::= { hh3cevtModuleSwitchType 2264 } -- 48-Port 10/100/1000BASE-T Electrical Interface Board(RJ45)(SC)
hh3cevtModuleSw-LSCM3TGS48SE0-Z            OBJECT IDENTIFIER ::= { hh3cevtModuleSwitchType 2265 } -- 48-Port 10GBASE-R Ethernet SFP+ Optical Interface Board(SE)
hh3cevtModuleSw-LSCM3QGS8CSSE0-Z           OBJECT IDENTIFIER ::= { hh3cevtModuleSwitchType 2266 } -- 8-Port 40GBASE-R QSFP+ + 4-Port 100GBASE-R QSFP28 Optical Interface Board(SE)
hh3cevtModuleSw-LSDM3QGS12SE0-Z            OBJECT IDENTIFIER ::= { hh3cevtModuleSwitchType 2267 } -- 12-Port 40GBASE-R Ethernet QSFP+ Optical Interface Board(SE)
hh3cevtModuleSw-LSDM3TGS48SE0-Z            OBJECT IDENTIFIER ::= { hh3cevtModuleSwitchType 2268 } -- 48-Port 10GBASE-R Ethernet SFP+ Optical Interface Board(SE)
hh3cevtModuleSw-LSDM3SUPA0-Z               OBJECT IDENTIFIER ::= { hh3cevtModuleSwitchType 2269 } -- Supervisor Engine Board
hh3cevtModuleSw-LSDM3FAB08D0-Z             OBJECT IDENTIFIER ::= { hh3cevtModuleSwitchType 2270 } -- Switch Fabric Board
hh3cevtModuleSw-LSDM3GT24GPSE0-Z           OBJECT IDENTIFIER ::= { hh3cevtModuleSwitchType 2271 } -- 24-Port 10/100/1000BASE-T Electrical Interface(RJ45)+24-Port 1000BASE-X Ethernet Optical Interface Board(SFP,LC)(SE)
hh3cevtModuleSw-LSDM3GP48SE0-Z             OBJECT IDENTIFIER ::= { hh3cevtModuleSwitchType 2272 } -- 48-Port 1000BASE-X Ethernet Optical Interface Board(SFP,LC)
hh3cevtModuleSw-LSDM3GT48SE0-Z             OBJECT IDENTIFIER ::= { hh3cevtModuleSwitchType 2273 } -- 48-Port 10/100/1000BASE-T Ethernet Interface Board(RJ45)(SE)
hh3cevtModuleSw-LSDM3CGS8SE0-Z             OBJECT IDENTIFIER ::= { hh3cevtModuleSwitchType 2274 } -- 8-Port 100GBASE-R Ethernet Optical Interface Board(QSFP28,LC)
hh3cevtModuleSw-RX-CEPC-CQ8LF              OBJECT IDENTIFIER ::= { hh3cevtModuleSwitchType 2275 } -- 8-port 100G Flexible Ethernet Optical Interface Line Processing Unit(QSFP28,LC)
hh3cevtModuleSw-RX-SPE200-E                OBJECT IDENTIFIER ::= { hh3cevtModuleSwitchType 2276 } -- Service Processing Unit(SPE200-E)

hh3cevtModuleSw-DSH7503-MP                 OBJECT IDENTIFIER ::= { hh3cevtModuleSwitchType 2277 } -- Supervisor Engine Board
hh3cevtModuleSw-DSH7506-MP                 OBJECT IDENTIFIER ::= { hh3cevtModuleSwitchType 2278 } -- Supervisor Engine Board
hh3cevtModuleSw-DSH7510-MP                 OBJECT IDENTIFIER ::= { hh3cevtModuleSwitchType 2279 } -- Supervisor Engine Board
hh3cevtModuleSw-DSH7500-48T-P              OBJECT IDENTIFIER ::= { hh3cevtModuleSwitchType 2280 } -- 48-Port 1000Base-T Gigabit Ethernet Interface Board(RJ45)-POE
hh3cevtModuleSw-DSH7500-16X                OBJECT IDENTIFIER ::= { hh3cevtModuleSwitchType 2281 } -- 16-Port 10GBASE-R Ethernet SFP+ Optical Interface Board
hh3cevtModuleSw-DSH7500-48F                OBJECT IDENTIFIER ::= { hh3cevtModuleSwitchType 2282 } -- 48-Port 1000BASE-X Optical Interface Board(SFP,LC)
hh3cevtModuleSw-DSH7500-12QX4Q28           OBJECT IDENTIFIER ::= { hh3cevtModuleSwitchType 2283 } -- 12-Port 40GBASE-R QSFP+ or 4-Port 100GBASE-R QSFP28 Optical Interface Board
hh3cevtModuleSw-DSH7500-24F4X              OBJECT IDENTIFIER ::= { hh3cevtModuleSwitchType 2284 } -- 24-Port GE Optical Interface(SFP,LC)+4-Port 10GE Optical Interface Board(SFP+,LC)
hh3cevtModuleSw-DSH7500-24QX               OBJECT IDENTIFIER ::= { hh3cevtModuleSwitchType 2285 } -- 24-Port 40GBASE-R Ethernet QSFP+ Optical Interface Board
hh3cevtModuleSw-DSH7500-24T4X              OBJECT IDENTIFIER ::= { hh3cevtModuleSwitchType 2286 } -- 24-Port 1000Base-T Gigabit Ethernet Interface Board(RJ45)+4-Port 10GE Optical Interface Board(SFP+,LC)
hh3cevtModuleSw-DSH7500-24X2QX1Q28         OBJECT IDENTIFIER ::= { hh3cevtModuleSwitchType 2287 } -- 24-Port 10GBASE-R Optical Interface(SFP+,LC)+2-Port 40GBASE-R Optical Interface Board(QSFP+) or 1-Port 100GBASE-R Optical Interface Board(QSFP28)
hh3cevtModuleSw-DSH7500-2Q28               OBJECT IDENTIFIER ::= { hh3cevtModuleSwitchType 2288 } -- 2-Port 100GBASE-R Ethernet QSFP28 Optical Interface Board
hh3cevtModuleSw-DSH7500-44F4X              OBJECT IDENTIFIER ::= { hh3cevtModuleSwitchType 2289 } -- 44-Port GE Optical Interface(SFP,LC)+4-Port 10GE Optical Interface Board(SFP+,LC)
hh3cevtModuleSw-DSH7500-48T                OBJECT IDENTIFIER ::= { hh3cevtModuleSwitchType 2290 } -- 48-Port 10/100/1000BASE-T Electrical Interface Board(RJ45)
hh3cevtModuleSw-DSH7500-48X                OBJECT IDENTIFIER ::= { hh3cevtModuleSwitchType 2291 } -- 48-Port 10GBASE-R Ethernet SFP+ Optical Interface Board
hh3cevtModuleSw-LSWM2-iMC                  OBJECT IDENTIFIER ::= { hh3cevtModuleSwitchType 2292 } -- Intelligent Network Management Module
hh3cevtModuleSw-LSWM2ZQP2P-Z               OBJECT IDENTIFIER ::= { hh3cevtModuleSwitchType 2293 } -- 2-Port QSFP28 Interface Module
hh3cevtModuleSw-LSWM2ZSP4P-Z               OBJECT IDENTIFIER ::= { hh3cevtModuleSwitchType 2294 } -- 4-Port SFP28 Interface Module
hh3cevtModuleSw-LSWM2ZSP8P-Z               OBJECT IDENTIFIER ::= { hh3cevtModuleSwitchType 2295 } -- 8-Port SFP28 Interface Module
hh3cevtModuleSw-LSDM3SUP04A0-Z             OBJECT IDENTIFIER ::= { hh3cevtModuleSwitchType 2296 } -- Supervisor Engine Board
hh3cevtModuleSw-LSDM3FAB04E0-Z             OBJECT IDENTIFIER ::= { hh3cevtModuleSwitchType 2297 } -- Switching Fabric Module
hh3cevtModuleSw-LSDM3FAB08E0-Z             OBJECT IDENTIFIER ::= { hh3cevtModuleSwitchType 2298 } -- Switching Fabric Module
hh3cevtModuleSw-LSDM3QGS36SE0-Z            OBJECT IDENTIFIER ::= { hh3cevtModuleSwitchType 2299 } -- 36-Port 40GBASE-R Ethernet QSFP+ Optical Interface Board
hh3cevtModuleSw-LSDM3CGS12SE0-Z            OBJECT IDENTIFIER ::= { hh3cevtModuleSwitchType 2300 } -- 12-Port 100GBASE-R Ethernet QSFP28 Optical Interface Board
hh3cevtModuleSw-LSQM2XPT12TSFD0            OBJECT IDENTIFIER ::= { hh3cevtModuleSwitchType 2301 } -- 12-Port 10/1GBASE-PR/PRX Ethernet Optical(SFP+,LC) and 8-Port 10GBASE-R SFP+ Optical Interface Board
hh3cevtModuleSw-CSPEX-1702X                OBJECT IDENTIFIER ::= { hh3cevtModuleSwitchType 2302 } -- Service Processing Unit(1702X)
hh3cevtModuleSw-CSR05SRP1P1                OBJECT IDENTIFIER ::= { hh3cevtModuleSwitchType 2303 } -- H3C CR16000-F CSR05SRP1P1 Main Processing Unit(1P1)
hh3cevtModuleSw-NIC-GP24L1                 OBJECT IDENTIFIER ::= { hh3cevtModuleSwitchType 2304 } -- 24-port 1000BASE-X Ethernet Optical Interface Card(SFP,LC)(NIC)
hh3cevtModuleSw-NIC-GP24LA                 OBJECT IDENTIFIER ::= { hh3cevtModuleSwitchType 2305 } -- 24-port 1000BASE-X Ethernet Optical Interface Card A(SFP,LC)(NIC)
hh3cevtModuleSw-NIC-XP20L1                 OBJECT IDENTIFIER ::= { hh3cevtModuleSwitchType 2306 } -- 20-port 10GBASE-R/W Ethernet Optical Interface Card(SFP+,LC)(NIC)
hh3cevtModuleSw-NIC-XP20LA                 OBJECT IDENTIFIER ::= { hh3cevtModuleSwitchType 2307 } -- 20-port 10GBASE-R/W Ethernet Optical Interface Card A(SFP+,LC)(NIC)
hh3cevtModuleSw-RX-NIC-LGQ4LF              OBJECT IDENTIFIER ::= { hh3cevtModuleSwitchType 2308 } -- 4-port 50G Flexible Ethernet Optical Interface Card(QSFP28,LC)(RX-NIC)
hh3cevtModuleSw-CSR05SRP1R3A               OBJECT IDENTIFIER ::= { hh3cevtModuleSwitchType 2309 } -- H3C CR16000-FA Main Processing Unit(1R3A)
hh3cevtModuleSw-CEPC-CQ8L                  OBJECT IDENTIFIER ::= { hh3cevtModuleSwitchType 2310 } -- 8-port 100G Ethernet Optical Interface Line Processing Unit(QSFP28,LC)
hh3cevtModuleSw-CEPC-CQ8LA                 OBJECT IDENTIFIER ::= { hh3cevtModuleSwitchType 2311 } -- 8-port 100G Ethernet Optical Interface Line Processing Unit A(QSFP28,LC)
hh3cevtModuleSw-CSPEX-1802XA               OBJECT IDENTIFIER ::= { hh3cevtModuleSwitchType 2312 } -- Service Processing Unit(1802XA)
hh3cevtModuleSw-CSPEX-1802XB               OBJECT IDENTIFIER ::= { hh3cevtModuleSwitchType 2313 } -- Service Processing Unit(1802XB)
hh3cevtModuleSw-CSPEX-1502XA               OBJECT IDENTIFIER ::= { hh3cevtModuleSwitchType 2314 } -- Service Processing Unit(1502XA)
hh3cevtModuleSw-CSPEX-1512XB               OBJECT IDENTIFIER ::= { hh3cevtModuleSwitchType 2315 } -- Service Processing Unit(1512XB)

hh3cevtModuleSw-NIC-XP20L1A                OBJECT IDENTIFIER ::= { hh3cevtModuleSwitchType 2317 } -- 20-port 10GBASE-R/W Ethernet Optical Interface Card A(SFP+,LC)(NIC)
hh3cevtModuleSw-NIC-XP20L1B                OBJECT IDENTIFIER ::= { hh3cevtModuleSwitchType 2318 } -- 20-port 10GBASE-R/W Ethernet Optical Interface Card B(SFP+,LC)(NIC)

hh3cevtModuleSw-NIC-GP24L1A                OBJECT IDENTIFIER ::= { hh3cevtModuleSwitchType 2320 } -- 24-port 1000BASE-X Ethernet Optical Interface Card A(SFP,LC)(NIC)
hh3cevtModuleSw-NIC-GP24L1B                OBJECT IDENTIFIER ::= { hh3cevtModuleSwitchType 2321 } -- 24-port 1000BASE-X Ethernet Optical Interface Card B(SFP,LC)(NIC)
hh3cevtModuleSw-NIC-CQ2LA                  OBJECT IDENTIFIER ::= { hh3cevtModuleSwitchType 2322 } -- 2-port 100G Ethernet Optical Interface Card A(QSFP28)(NIC)
hh3cevtModuleSw-NIC-CQ2LB                  OBJECT IDENTIFIER ::= { hh3cevtModuleSwitchType 2323 } -- 2-port 100G Ethernet Optical Interface Card B(QSFP28)(NIC)
hh3cevtModuleSw-NIC-XP5LA                  OBJECT IDENTIFIER ::= { hh3cevtModuleSwitchType 2324 } -- 5-port 10GBASE-R/W Ethernet Optical Interface Card A(SFP+,LC)(NIC)
hh3cevtModuleSw-NIC-XP5LB                  OBJECT IDENTIFIER ::= { hh3cevtModuleSwitchType 2325 } -- 5-port 10GBASE-R/W Ethernet Optical Interface Card B(SFP+,LC)(NIC)
hh3cevtModuleSw-CSFC-16T1                  OBJECT IDENTIFIER ::= { hh3cevtModuleSwitchType 2326 } -- CR16018-F Fabric Module(T Type)
hh3cevtModuleSw-LSUM1MPUS10XEC0            OBJECT IDENTIFIER ::= { hh3cevtModuleSwitchType 2327 } -- Supervisor Engine Board
hh3cevtModuleSw-LSUM1MPUS10XEC3            OBJECT IDENTIFIER ::= { hh3cevtModuleSwitchType 2328 } -- Supervisor Engine Board
hh3cevtModuleSw-LSUM1MPUS06XEC3            OBJECT IDENTIFIER ::= { hh3cevtModuleSwitchType 2329 } -- Supervisor Engine Board
hh3cevtModuleSw-LSUM1FAB10XEC0             OBJECT IDENTIFIER ::= { hh3cevtModuleSwitchType 2330 } -- Switching Fabric Module
hh3cevtModuleSw-LSCM2MPUS06AS0-Z           OBJECT IDENTIFIER ::= { hh3cevtModuleSwitchType 2331 } -- Supervisor Engine Board
hh3cevtModuleSw-LSCM2CGT24TSSC0-Z          OBJECT IDENTIFIER ::= { hh3cevtModuleSwitchType 2332 } -- Supervisor Engine Board With 24-Port 10/100/1000BASE-T Ethernet Interface+4-Port 10GBASE-R Ethernet SFP+ Optical Interfaces
hh3cevtModuleSw-LSCM2CGP24TSSC0-Z          OBJECT IDENTIFIER ::= { hh3cevtModuleSwitchType 2333 } -- Supervisor Engine Board With 24-Port 1000BASE-X Ethernet SFP Optical Interface+4-Port 10GBASE-R Ethernet SFP+ Optical Interfaces
hh3cevtModuleSw-LSCM2CTGS12GTSC0-Z         OBJECT IDENTIFIER ::= { hh3cevtModuleSwitchType 2334 } -- Supervisor Engine Board With 16-Port 10/100/1000BASE-T Ethernet Interface+12-Port 10GBASE-R Ethernet SFP+ Optical Interfaces
hh3cevtModuleSw-LSCM2CTGS12GPSC0-Z         OBJECT IDENTIFIER ::= { hh3cevtModuleSwitchType 2335 } -- Supervisor Engine Board With 16-Port 1000BASE-X Ethernet SFP Optical Interface+12-Port 10GBASE-R Ethernet SFP+ Optical Interfaces
hh3cevtModuleSw-LSCM2GT24GPTSSC0-Z         OBJECT IDENTIFIER ::= { hh3cevtModuleSwitchType 2336 } -- 24-Port 10/100/1000BASE-T Ethernet Interface Board(RJ45)+20-Port 1000BASE-X Ethernet SFP Optical Interface(SFP,LC)+4-Port 10GBASE-R Optical Interface Board(SFP+,LC)(SC)
hh3cevtModuleSw-LSCM2GT24GPSC0-Z           OBJECT IDENTIFIER ::= { hh3cevtModuleSwitchType 2337 } -- 24-Port 10/100/1000BASE-T Ethernet Interface Board(RJ45)+8-Port 1000BASE-X Ethernet SFP Optical Interface(SFP,LC)(SC)
hh3cevtModuleSw-LSCM2GP24GTSC0-Z           OBJECT IDENTIFIER ::= { hh3cevtModuleSwitchType 2338 } -- 8-Port 10/100/1000BASE-T Ethernet Interface Board(RJ45)+24-Port 1000BASE-X Ethernet SFP Optical Interface(SFP,LC)(SC)
hh3cevtModuleSw-LSCM2GT48SC0-Z             OBJECT IDENTIFIER ::= { hh3cevtModuleSwitchType 2339 } -- 48-Port 10/100/1000BASE-T Ethernet Interface Board(RJ45)(SC)
hh3cevtModuleSw-LSCM2GP48SC0-Z             OBJECT IDENTIFIER ::= { hh3cevtModuleSwitchType 2340 } -- 48-Port 1000BASE-X Ethernet Optical Interface Board(SFP,LC)
hh3cevtModuleSw-LSCM2TGS16GPSC0-Z          OBJECT IDENTIFIER ::= { hh3cevtModuleSwitchType 2341 } -- 24-Port 1000BASE-R Ethernet Optical Interface(SFP,LC)+16-Port 10GBASE-R Ethernet Optical Interface Board(SFP+,LC)
hh3cevtModuleSw-LSWM2SP2PM-Z               OBJECT IDENTIFIER ::= { hh3cevtModuleSwitchType 2342 } -- 2-Port SFP+ Interface Module with MACsec
hh3cevtModuleSw-LSWM2QP2P-Z                OBJECT IDENTIFIER ::= { hh3cevtModuleSwitchType 2343 } -- 2-Port QSFP+ Interface Module
hh3cevtModuleSw-LSWM2SP8P-Z                OBJECT IDENTIFIER ::= { hh3cevtModuleSwitchType 2344 } -- 8-Port SFP+ Interface Module
hh3cevtModuleSw-LSCM2MPUS06AS0             OBJECT IDENTIFIER ::= { hh3cevtModuleSwitchType 2345 }  -- Supervisor Engine Board
hh3cevtModuleSw-LSCM2CGT24TSSC0            OBJECT IDENTIFIER ::= { hh3cevtModuleSwitchType 2346 }  -- Supervisor Engine Board With 24-Port 10/100/1000BASE-T Ethernet Interface+4-Port 10GBASE-R Ethernet SFP+ Optical Interfaces
hh3cevtModuleSw-LSCM2CGP24TSSC0            OBJECT IDENTIFIER ::= { hh3cevtModuleSwitchType 2347 }  -- Supervisor Engine Board With 24-Port 1000BASE-X Ethernet SFP Optical Interface+4-Port 10GBASE-R Ethernet SFP+ Optical Interfaces
hh3cevtModuleSw-LSCM2CTGS12GTSC0           OBJECT IDENTIFIER ::= { hh3cevtModuleSwitchType 2348 }  -- Supervisor Engine Board With 16-Port 10/100/1000BASE-T Ethernet Interface+12-Port 10GBASE-R Ethernet SFP+ Optical Interfaces
hh3cevtModuleSw-LSCM2CTGS12GPSC0           OBJECT IDENTIFIER ::= { hh3cevtModuleSwitchType 2349 }  -- Supervisor Engine Board With 16-Port 1000BASE-X Ethernet SFP Optical Interface+12-Port 10GBASE-R Ethernet SFP+ Optical Interfaces
hh3cevtModuleSw-LSCM2GT24GPTSSC0           OBJECT IDENTIFIER ::= { hh3cevtModuleSwitchType 2350 }  -- 24-Port 10/100/1000BASE-T Ethernet Interface Board(RJ45)+20-Port 1000BASE-X Ethernet SFP Optical Interface(SFP,LC)+4-Port 10GBASE-R Optical Interface Board(SFP+,LC)(SC)
hh3cevtModuleSw-LSCM2GT24GPSC0             OBJECT IDENTIFIER ::= { hh3cevtModuleSwitchType 2351 }  -- 24-Port 10/100/1000BASE-T Ethernet Interface Board(RJ45)+8-Port 1000BASE-X Ethernet SFP Optical Interface(SFP,LC)(SC)
hh3cevtModuleSw-LSCM2GP24GTSC0             OBJECT IDENTIFIER ::= { hh3cevtModuleSwitchType 2352 }  -- 8-Port 10/100/1000BASE-T Ethernet Interface Board(RJ45)+24-Port 1000BASE-X Ethernet SFP Optical Interface(SFP,LC)(SC)
hh3cevtModuleSw-LSCM2GT48SC0               OBJECT IDENTIFIER ::= { hh3cevtModuleSwitchType 2353 }  -- 48-Port 10/100/1000BASE-T Ethernet Interface Board(RJ45)(SC)
hh3cevtModuleSw-LSCM2GP48SC0               OBJECT IDENTIFIER ::= { hh3cevtModuleSwitchType 2354 }  -- 48-Port 1000BASE-X Ethernet Optical Interface Board(SFP,LC)
hh3cevtModuleSw-LSCM2TGS16GPSC0            OBJECT IDENTIFIER ::= { hh3cevtModuleSwitchType 2355 }  -- 24-Port 1000BASE-R Ethernet Optical Interface(SFP,LC)+16-Port 10GBASE-R Ethernet Optical Interface Board(SFP+,LC)
hh3cevtModuleSw-LSXM1SFK04FR1              OBJECT IDENTIFIER ::= { hh3cevtModuleSwitchType 2356 } -- S12504R Fabric Module
hh3cevtModuleSw-LSXM1SFK08ER1              OBJECT IDENTIFIER ::= { hh3cevtModuleSwitchType 2357 } -- S12508CR Fabric Module
hh3cevtModuleSw-LSXM1SFK16ER1              OBJECT IDENTIFIER ::= { hh3cevtModuleSwitchType 2358 } -- S12516CR Fabric Module
hh3cevtModuleSw-LSXM1CCQ48KBR1             OBJECT IDENTIFIER ::= { hh3cevtModuleSwitchType 2359 } --  48-Port 200GBASE Ethernet Optical Interface Module (QSFP56)(KB)
hh3cevtModuleSw-LSQM3SUPA0                 OBJECT IDENTIFIER ::= { hh3cevtModuleSwitchType 2360 }  -- Supervisor Engine Board
hh3cevtModuleSw-LSQM3SUPA3                 OBJECT IDENTIFIER ::= { hh3cevtModuleSwitchType 2361 }  -- Supervisor Engine Board
hh3cevtModuleSw-LSXM1YGS24CGMODTE2         OBJECT IDENTIFIER ::= { hh3cevtModuleSwitchType 2362 }  -- 24-Port 25G Ethernet Optical Interface(SFP28)+4-Port 100G Ethernet Optical Interface Module (QSFP28),With 1 Expansion Slot
hh3cevtModuleSw-LSXM1SUPE1                 OBJECT IDENTIFIER ::= { hh3cevtModuleSwitchType 2363 }  -- Supervisor Engine Unit

hh3cevtModuleSw-LSUM2TGS48SH0              OBJECT IDENTIFIER ::= { hh3cevtModuleSwitchType 2364 } -- 48-Port 10G Ethernet Optical Interface Module(SFP+,LC)(SH)
hh3cevtModuleSw-LSCM3SUP03A0               OBJECT IDENTIFIER ::= { hh3cevtModuleSwitchType 2365 } -- Supervisor Engine Board
hh3cevtModuleSw-LSCM3MPUS06A0              OBJECT IDENTIFIER ::= { hh3cevtModuleSwitchType 2366 } -- Supervisor Engine Board
hh3cevtModuleSw-LSCM3TGS48SE0              OBJECT IDENTIFIER ::= { hh3cevtModuleSwitchType 2367 } -- 48-Port 10GBASE-R Ethernet SFP+ Optical Interface Board(SE)
hh3cevtModuleSw-LSCM3QGS8CSSE0             OBJECT IDENTIFIER ::= { hh3cevtModuleSwitchType 2368 } -- 8-Port 40GBASE-R QSFP+ + 4-Port 100GBASE-R QSFP28 Optical Interface Board(SE)
hh3cevtModuleSw-LSCM3SUP03A0-ZE            OBJECT IDENTIFIER ::= { hh3cevtModuleSwitchType 2369 } -- Supervisor Engine Board
hh3cevtModuleSw-LSCM3GT48SC0-ZE            OBJECT IDENTIFIER ::= { hh3cevtModuleSwitchType 2370 } -- 48-Port 10/100/1000BASE-T Electrical Interface Board(RJ45)(SC)
hh3cevtModuleSw-LSCM3TGS48SE0-ZE           OBJECT IDENTIFIER ::= { hh3cevtModuleSwitchType 2371 } -- 48-Port 10GBASE-R Ethernet SFP+ Optical Interface Board(SE)
hh3cevtModuleSw-LSCM3QGS8CSSE0-ZE          OBJECT IDENTIFIER ::= { hh3cevtModuleSwitchType 2372 } -- 8-Port 40GBASE-R QSFP+ + 4-Port 100GBASE-R QSFP28 Optical Interface Board(SE)
hh3cevtModuleSw-LSDM3FAB04G0-Z             OBJECT IDENTIFIER ::= { hh3cevtModuleSwitchType 2373 } -- Switch Fabric Board
hh3cevtModuleSw-LSDM3FAB08G0-Z             OBJECT IDENTIFIER ::= { hh3cevtModuleSwitchType 2374 } -- Switch Fabric Board
hh3cevtModuleSw-LSDM3FAB16G0-Z             OBJECT IDENTIFIER ::= { hh3cevtModuleSwitchType 2375 } -- Switch Fabric Board
hh3cevtModuleSw-LSDM3CGS36SF0-Z            OBJECT IDENTIFIER ::= { hh3cevtModuleSwitchType 2376 } -- 36-Port 100GBASE-R Ethernet Optical Interface Board(QSFP28,LC)
hh3cevtModuleSw-LSDM3YGS48SF0-Z            OBJECT IDENTIFIER ::= { hh3cevtModuleSwitchType 2377 } -- 48-Port 25GBASE-R Ethernet Optical Interface Board(SFP28,LC)
hh3cevtModuleSw-LSCM3MPUS10B0              OBJECT IDENTIFIER ::= { hh3cevtModuleSwitchType 2378 } -- Supervisor Engine Board
hh3cevtModuleSw-LSCM3MPUS10B0-Z            OBJECT IDENTIFIER ::= { hh3cevtModuleSwitchType 2379 } -- Supervisor Engine Board
hh3cevtModuleSw-LSUM1CGS8QSSH8             OBJECT IDENTIFIER ::= { hh3cevtModuleSwitchType 2380 } -- 8-Port 100G Ethernet Optical Interface Module(QSFP28) +8-port 40G/4-Port 100G Ethernet Optical Interface Module(QSFP28)(SH)
hh3cevtModuleSw-LSDM3TGS48SF0-Z            OBJECT IDENTIFIER ::= { hh3cevtModuleSwitchType 2381 } -- 48-Port 10GBASE-R Ethernet SFP+ Optical Interface Board(SF)
hh3cevtModuleSw-LSDM1SUPA0                 OBJECT IDENTIFIER ::= { hh3cevtModuleSwitchType 2382 } -- Supervisor Engine Board
hh3cevtModuleSw-LSDM1FAB08D0               OBJECT IDENTIFIER ::= { hh3cevtModuleSwitchType 2383 } -- Switch Fabric Board
hh3cevtModuleSw-LSDM1TGS48SE0              OBJECT IDENTIFIER ::= { hh3cevtModuleSwitchType 2384 } -- 48-Port 10GBASE-R Ethernet SFP+ Optical Interface Board(SE)
hh3cevtModuleSw-LSDM1GT24GPSE0             OBJECT IDENTIFIER ::= { hh3cevtModuleSwitchType 2385 } -- 24-Port 10/100/1000BASE-T Electrical Interface(RJ45)+24-Port 1000BASE-X Ethernet Optical Interface Board(SFP,LC)(SE)
hh3cevtModuleSw-LSDM1GT48SE0               OBJECT IDENTIFIER ::= { hh3cevtModuleSwitchType 2386 } -- 48-Port 10/100/1000BASE-T Ethernet Interface Board(RJ45)(SE)
hh3cevtModuleSw-LSDM1GP48SE0               OBJECT IDENTIFIER ::= { hh3cevtModuleSwitchType 2387 } -- 48-Port 1000BASE-X Ethernet Optical Interface Board(SFP,LC)
hh3cevtModuleSw-LSDM3SUPA0                 OBJECT IDENTIFIER ::= { hh3cevtModuleSwitchType 2388 } -- Supervisor Engine Board
hh3cevtModuleSw-LSDM3FAB08D0               OBJECT IDENTIFIER ::= { hh3cevtModuleSwitchType 2389 } -- Switch Fabric Board
hh3cevtModuleSw-LSDM3TGS48SE0              OBJECT IDENTIFIER ::= { hh3cevtModuleSwitchType 2390 } -- 48-Port 10GBASE-R Ethernet SFP+ Optical Interface Board(SE)
hh3cevtModuleSw-LSDM3GT24GPSE0             OBJECT IDENTIFIER ::= { hh3cevtModuleSwitchType 2391 } -- 24-Port 10/100/1000BASE-T Electrical Interface(RJ45)+24-Port 1000BASE-X Ethernet Optical Interface Board(SFP,LC)(SE)
hh3cevtModuleSw-LSDM3GT48SE0               OBJECT IDENTIFIER ::= { hh3cevtModuleSwitchType 2392 } -- 48-Port 10/100/1000BASE-T Ethernet Interface Board(RJ45)(SE)
hh3cevtModuleSw-LSDM3GP48SE0               OBJECT IDENTIFIER ::= { hh3cevtModuleSwitchType 2393 } -- 48-Port 1000BASE-X Ethernet Optical Interface Board(SFP,LC)
hh3cevtModuleSw-SR07MPUA3-M                OBJECT IDENTIFIER ::= { hh3cevtModuleSwitchType 2394 } -- H3C CR16000-M Management and Route Process Board(UA3-M)
hh3cevtModuleSw-SFE-A                      OBJECT IDENTIFIER ::= { hh3cevtModuleSwitchType 2395 } -- Network Processing Unit(A)
hh3cevtModuleSw-MIC-CQ1L-M                 OBJECT IDENTIFIER ::= { hh3cevtModuleSwitchType 2396 } -- 1-Port 100G Ethernet Optical Interface Card(QSFP28,LC)
hh3cevtModuleSw-MIC-CQ2L-M                 OBJECT IDENTIFIER ::= { hh3cevtModuleSwitchType 2397 } -- 2-Port 100G Ethernet Optical Interface Card(QSFP28,LC)


hh3cevtModuleSw-LSXM1CGQ18C1               OBJECT IDENTIFIER ::= { hh3cevtModuleSwitchType 2398 } -- 18-Port 100GBASE Ethernet Optical Interface Module (QSFP28)
hh3cevtModuleSw-LSXM1CGQMS18B1             OBJECT IDENTIFIER ::= { hh3cevtModuleSwitchType 2399 } -- 18-Port 100GBASE MACsec Ethernet Optical Interface Module(QSFP28)
hh3cevtModuleSw-LSXM1MOD48KBR1             OBJECT IDENTIFIER ::= { hh3cevtModuleSwitchType 2400 } -- 48KBR Flexible Line Processing Platform Module
hh3cevtModuleSw-LSXM1CDQ36KB1              OBJECT IDENTIFIER ::= { hh3cevtModuleSwitchType 2401 } -- 36-Port 400GBASE Ethernet Optical Interface Module(QSFP-DD)(KB)
hh3cevtModuleSw-LSXM1SUP02TR1              OBJECT IDENTIFIER ::= { hh3cevtModuleSwitchType 2402 } -- Supervisor Engine Unit
hh3cevtModuleSw-LSCM2SUP03B0               OBJECT IDENTIFIER ::= { hh3cevtModuleSwitchType 2407 } -- Supervisor Engine Board
hh3cevtModuleSw-LSCM2SUP03B0-Z             OBJECT IDENTIFIER ::= { hh3cevtModuleSwitchType 2408 } -- Supervisor Engine Board
hh3cevtModuleSw-LSWM2QP4P                  OBJECT IDENTIFIER ::= { hh3cevtModuleSwitchType 2409 } -- 4-Port QSFP+ Interface Module
hh3cevtModuleSw-LSXM1SUPS2                 OBJECT IDENTIFIER ::= { hh3cevtModuleSwitchType 2410 } -- Supervisor Engine Board
hh3cevtModuleSw-LSXM1SFS08D2               OBJECT IDENTIFIER ::= { hh3cevtModuleSwitchType 2411 } -- Switch Fabric Board
hh3cevtModuleSw-LSXM1TGS48SE2              OBJECT IDENTIFIER ::= { hh3cevtModuleSwitchType 2412 } -- 48-Port 10GBASE-R Ethernet SFP+ Optical Interface Board(SE)
hh3cevtModuleSw-LSXM1GT24GPSE2             OBJECT IDENTIFIER ::= { hh3cevtModuleSwitchType 2413 } -- 24-Port 10/100/1000BASE-T Electrical Interface(RJ45)+24-Port 1000BASE-X Ethernet Optical Interface Board(SFP,LC)(SE)
hh3cevtModuleSw-LSXM1GT48SE2               OBJECT IDENTIFIER ::= { hh3cevtModuleSwitchType 2414 } -- 48-Port 10/100/1000BASE-T Ethernet Interface Board(RJ45)(SE)
hh3cevtModuleSw-LSXM1GP48SE2               OBJECT IDENTIFIER ::= { hh3cevtModuleSwitchType 2415 } -- 48-Port 1000BASE-X Ethernet Optical Interface Board(SFP,LC)
hh3cevtModuleSw-LSXM3SUPS2                 OBJECT IDENTIFIER ::= { hh3cevtModuleSwitchType 2416 } -- Supervisor Engine Board
hh3cevtModuleSw-LSXM3SFS08D2               OBJECT IDENTIFIER ::= { hh3cevtModuleSwitchType 2417 } -- Switch Fabric Board
hh3cevtModuleSw-LSXM3TGS48SE2              OBJECT IDENTIFIER ::= { hh3cevtModuleSwitchType 2418 } -- 48-Port 10GBASE-R Ethernet SFP+ Optical Interface Board(SE)
hh3cevtModuleSw-LSXM3GT24GPSE2             OBJECT IDENTIFIER ::= { hh3cevtModuleSwitchType 2419 } -- 24-Port 10/100/1000BASE-T Electrical Interface(RJ45)+24-Port 1000BASE-X Ethernet Optical Interface Board(SFP,LC)(SE)
hh3cevtModuleSw-LSXM3GT48SE2               OBJECT IDENTIFIER ::= { hh3cevtModuleSwitchType 2420 } -- 48-Port 10/100/1000BASE-T Ethernet Interface Board(RJ45)(SE)
hh3cevtModuleSw-LSXM3GP48SE2               OBJECT IDENTIFIER ::= { hh3cevtModuleSwitchType 2421 } -- 48-Port 1000BASE-X Ethernet Optical Interface Board(SFP,LC)
hh3cevtModuleSw-LSXM3SUP04S2               OBJECT IDENTIFIER ::= { hh3cevtModuleSwitchType 2422 } -- Supervisor Engine Board
hh3cevtModuleSw-LSXM3SFS04G2               OBJECT IDENTIFIER ::= { hh3cevtModuleSwitchType 2423 } -- Switch Fabric Board
hh3cevtModuleSw-LSXM3SFS08G2               OBJECT IDENTIFIER ::= { hh3cevtModuleSwitchType 2424 } -- Switch Fabric Board
hh3cevtModuleSw-LSXM3SFS16G2               OBJECT IDENTIFIER ::= { hh3cevtModuleSwitchType 2425 } -- Switch Fabric Board
hh3cevtModuleSw-LSXM3CGQ36SF2              OBJECT IDENTIFIER ::= { hh3cevtModuleSwitchType 2426 } -- 36-Port 100GBASE-R Ethernet Optical Interface Board(QSFP28,LC)
hh3cevtModuleSw-LSXM3YGS48SF2              OBJECT IDENTIFIER ::= { hh3cevtModuleSwitchType 2427 } -- 48-Port 25GBASE-R Ethernet Optical Interface Board(SFP28,LC)
hh3cevtModuleSw-LSXM3TGS48SF2              OBJECT IDENTIFIER ::= { hh3cevtModuleSwitchType 2428 } -- 48-Port 10GBASE-R Ethernet SFP+ Optical Interface Board(SF)


-- Here define submodule for routers
hh3cevtSubModuleRouter       OBJECT IDENTIFIER ::= { hh3cevtModule 5 }


-- Here define submodule for switches
hh3cevtSubModuleSwitch       OBJECT IDENTIFIER ::= { hh3cevtModule 6 }
-- Here define Compact Flash
hh3cevtModuleCFCard          OBJECT IDENTIFIER ::= { hh3cevtModule 7 }

-- Here define Secure Digital Memory Card
hh3cevtModuleSDCard          OBJECT IDENTIFIER ::= { hh3cevtModule 8 }

--
-- hh3cevtPort section:
--
hh3cevtPort          OBJECT IDENTIFIER ::= { hh3cEntityVendortypeObjects 10 }

hh3cevtPortUnknownPorts      OBJECT IDENTIFIER ::= { hh3cevtPort 1 }
hh3cevtPortCommonPorts       OBJECT IDENTIFIER ::= { hh3cevtPort 2 }
hh3cevtPortRouterType        OBJECT IDENTIFIER ::= { hh3cevtPort 3 }
hh3cevtPortSwitchType        OBJECT IDENTIFIER ::= { hh3cevtPort 4 }


-- Below are ports used to router
hh3cevtPortRt-Async          OBJECT IDENTIFIER ::= { hh3cevtPortRouterType 1 }    -- Async interface
hh3cevtPortRt-Analogmodem    OBJECT IDENTIFIER ::= { hh3cevtPortRouterType 2 }    -- Analog modem interface
hh3cevtPortRt-Atm            OBJECT IDENTIFIER ::= { hh3cevtPortRouterType 3 }
hh3cevtPortRt-AtmAdsl        OBJECT IDENTIFIER ::= { hh3cevtPortRouterType 4 }
hh3cevtPortRt-AtmShdsl       OBJECT IDENTIFIER ::= { hh3cevtPortRouterType 5 }
hh3cevtPortRt-AtmE1          OBJECT IDENTIFIER ::= { hh3cevtPortRouterType 6 }
hh3cevtPortRt-AtmT1          OBJECT IDENTIFIER ::= { hh3cevtPortRouterType 7 }
hh3cevtPortRt-AtmE3          OBJECT IDENTIFIER ::= { hh3cevtPortRouterType 8 }
hh3cevtPortRt-AtmT3          OBJECT IDENTIFIER ::= { hh3cevtPortRouterType 9 }
hh3cevtPortRt-Atm622M        OBJECT IDENTIFIER ::= { hh3cevtPortRouterType 10 }
hh3cevtPortRt-AtmImaE1       OBJECT IDENTIFIER ::= { hh3cevtPortRouterType 11 }
hh3cevtPortRt-AtmImaT1       OBJECT IDENTIFIER ::= { hh3cevtPortRouterType 12 }
hh3cevtPortRt-Atm25M         OBJECT IDENTIFIER ::= { hh3cevtPortRouterType 13 }
hh3cevtPortRt-Bri            OBJECT IDENTIFIER ::= { hh3cevtPortRouterType 14 }
hh3cevtPortRt-Console        OBJECT IDENTIFIER ::= { hh3cevtPortRouterType 15 }
hh3cevtPortRt-E1             OBJECT IDENTIFIER ::= { hh3cevtPortRouterType 16 }
hh3cevtPortRt-E3             OBJECT IDENTIFIER ::= { hh3cevtPortRouterType 17 }
hh3cevtPortRt-T1             OBJECT IDENTIFIER ::= { hh3cevtPortRouterType 18 }
hh3cevtPortRt-T3             OBJECT IDENTIFIER ::= { hh3cevtPortRouterType 19 }
hh3cevtPortRt-Cpos           OBJECT IDENTIFIER ::= { hh3cevtPortRouterType 20 }
hh3cevtPortRt-Ethernet       OBJECT IDENTIFIER ::= { hh3cevtPortRouterType 21 }
hh3cevtPortRt-Serial         OBJECT IDENTIFIER ::= { hh3cevtPortRouterType 22 }
hh3cevtPortRt-E1f            OBJECT IDENTIFIER ::= { hh3cevtPortRouterType 23 }
hh3cevtPortRt-T1f            OBJECT IDENTIFIER ::= { hh3cevtPortRouterType 24 }
hh3cevtPortRt-Pos            OBJECT IDENTIFIER ::= { hh3cevtPortRouterType 25 }
hh3cevtPortRt-Ge             OBJECT IDENTIFIER ::= { hh3cevtPortRouterType 26 }
hh3cevtPortRt-Aux            OBJECT IDENTIFIER ::= { hh3cevtPortRouterType 27 }
-- hh3cevtPortRt-Null         OBJECT IDENTIFIER ::= { hh3cevtPortRouterType 28 }   reserved
-- hh3cevtPortRt-Max          OBJECT IDENTIFIER ::= { hh3cevtPortRouterType 29 }   reserved
hh3cevtPortRt-VG-Fxs         OBJECT IDENTIFIER ::= { hh3cevtPortRouterType 30 }
hh3cevtPortRt-VG-Fxo         OBJECT IDENTIFIER ::= { hh3cevtPortRouterType 31 }
hh3cevtPortRt-VG-E1vi        OBJECT IDENTIFIER ::= { hh3cevtPortRouterType 32 }
hh3cevtPortRt-VG-T1vi        OBJECT IDENTIFIER ::= { hh3cevtPortRouterType 33 }
hh3cevtPortRt-Usb            OBJECT IDENTIFIER ::= { hh3cevtPortRouterType 34 }
hh3cevtPortRt-Ndec           OBJECT IDENTIFIER ::= { hh3cevtPortRouterType 35 }   -- NDEC port, Encrypt card version 1.0
hh3cevtPortRt-Cavium         OBJECT IDENTIFIER ::= { hh3cevtPortRouterType 36 }   -- NDEC port, Encrypt card version 2.0
hh3cevtPortRt-Fcm            OBJECT IDENTIFIER ::= { hh3cevtPortRouterType 37 }   -- POS/Fast connect module port
hh3cevtPortRt-E1vi           OBJECT IDENTIFIER ::= { hh3cevtPortRouterType 38 }   -- E1VI port
hh3cevtPortRt-T1vi           OBJECT IDENTIFIER ::= { hh3cevtPortRouterType 39 }   -- T1VI port
hh3cevtPortRt-Vi             OBJECT IDENTIFIER ::= { hh3cevtPortRouterType 40 }   -- Voice port
hh3cevtPortRt-Adls2Plus      OBJECT IDENTIFIER ::= { hh3cevtPortRouterType 41 }   -- ADSL2Plus port
hh3cevtPortRt-RADIO-AG       OBJECT IDENTIFIER ::= { hh3cevtPortRouterType 42 }   -- 802.11ag Radio port
hh3cevtPortRt-1exp           OBJECT IDENTIFIER ::= { hh3cevtPortRouterType 43 }   -- 10GBASE-R/W Ethernet port
hh3cevtPortRt-G-SHDSL-BIS    OBJECT IDENTIFIER ::= { hh3cevtPortRouterType 44 }   -- 4 wire G.SHDSL.BIS interface
hh3cevtPortRt-ONU-1000BASE-BX-SFF-SC    OBJECT IDENTIFIER ::= { hh3cevtPortRouterType 45 }   -- 1000 BASE-BX SFF SC ONU Interface
hh3cevtPortRt-CELLULAR       OBJECT IDENTIFIER ::= { hh3cevtPortRouterType 46 }   -- 3G Wireless WAN Interface
hh3cevtPortRt-CELLULAR-ETHERNET         OBJECT IDENTIFIER ::= { hh3cevtPortRouterType 47 }   -- 3G Wireless WAN Interface for Ethernet mode
hh3cevtPortRt-VGe            OBJECT IDENTIFIER ::= { hh3cevtPortRouterType 48 } -- virtual Ge port
hh3cevtPortRt-VXGe           OBJECT IDENTIFIER ::= { hh3cevtPortRouterType 49 } -- virtual XGe port
hh3cevtPortRt-Xpos           OBJECT IDENTIFIER ::= { hh3cevtPortRouterType 50 } -- 10G POS port
hh3cevtPortRt-Fge            OBJECT IDENTIFIER ::= { hh3cevtPortRouterType 51 } -- 40G Ethernet port
hh3cevtPortRt-XGe            OBJECT IDENTIFIER ::= { hh3cevtPortRouterType 52 } -- 10G Ethernet port
hh3cevtPortRt-HgeQsfp28Lc    OBJECT IDENTIFIER ::= { hh3cevtPortRouterType 53 } -- 100G Ethernet Port with QSFP28 Form Factor and LC Connector
hh3cevtPortRt-HgeCfp2Lc      OBJECT IDENTIFIER ::= { hh3cevtPortRouterType 54 } -- 100G Ethernet Port with CFP2 Form Factor and LC Connector
hh3cevtPortRt-HgeCfpLc       OBJECT IDENTIFIER ::= { hh3cevtPortRouterType 55 } -- 100G Ethernet Port with CFP Form Factor and LC Connector
hh3cevtPortRt-GeM12          OBJECT IDENTIFIER ::= { hh3cevtPortRouterType 56 } -- Gigabit Ethernet Port with M12 Form Connector
hh3cevtPortRt-VMEth          OBJECT IDENTIFIER ::= { hh3cevtPortRouterType 57 } -- Virtual Machine Ethernet Port
hh3cevtPortRt-FiberGe        OBJECT IDENTIFIER ::= { hh3cevtPortRouterType 58 } -- 1G Fiber Ethernet port
hh3cevtPortRt-GeOptic        OBJECT IDENTIFIER ::= { hh3cevtPortRouterType 59 }
hh3cevtPortRt-25Ge           OBJECT IDENTIFIER ::= { hh3cevtPortRouterType 60 } -- 25G Ethernet port with SFP28
hh3cevtPortRt-50Ge           OBJECT IDENTIFIER ::= { hh3cevtPortRouterType 61 } -- 50G Ethernet port with QSFP28
hh3cevtPortRt-FlexE-50-100G  OBJECT IDENTIFIER ::= { hh3cevtPortRouterType 62 } -- 50-100G FlexE port with QSFP28
hh3cevtPortRt-50-100Ge       OBJECT IDENTIFIER ::= { hh3cevtPortRouterType 63 } -- 50-100G Ethernet port with QSFP28
hh3cevtPortRt-FlexE          OBJECT IDENTIFIER ::= { hh3cevtPortRouterType 64 } -- FlexE port with QSFP28
hh3cevtPortRt-100Ge          OBJECT IDENTIFIER ::= { hh3cevtPortRouterType 65 } -- 100G Ethernet port with QSFP28
hh3cevtPortRt-FlexE-50G      OBJECT IDENTIFIER ::= { hh3cevtPortRouterType 66 } -- 50G FlexE port with QSFP28
hh3cevtPortRt-Async-Phoenix  OBJECT IDENTIFIER ::= { hh3cevtPortRouterType 67 } -- Async interface
hh3cevtPortRt-FlexE-100G     OBJECT IDENTIFIER ::= { hh3cevtPortRouterType 68 } -- 100G FlexE port with QSFP28

-- Below are ports used to switches
--hh3cevtPortSw-Unknown              OBJECT IDENTIFIER ::= { hh3cevtPortSwitchType 0 }
hh3cevtPortSw-10or100M               OBJECT IDENTIFIER ::= { hh3cevtPortSwitchType 1 }
hh3cevtPortSw-1000BaseLxSm           OBJECT IDENTIFIER ::= { hh3cevtPortSwitchType 2 }
hh3cevtPortSw-1000BaseSxMm           OBJECT IDENTIFIER ::= { hh3cevtPortSwitchType 3 }
hh3cevtPortSw-1000BaseTx             OBJECT IDENTIFIER ::= { hh3cevtPortSwitchType 4 }
hh3cevtPortSw-100MSinglemodeFx       OBJECT IDENTIFIER ::= { hh3cevtPortSwitchType 5 }
hh3cevtPortSw-100MMultimodeFx        OBJECT IDENTIFIER ::= { hh3cevtPortSwitchType 6 }
hh3cevtPortSw-100M100BaseTx          OBJECT IDENTIFIER ::= { hh3cevtPortSwitchType 7 }
hh3cevtPortSw-100MHub                OBJECT IDENTIFIER ::= { hh3cevtPortSwitchType 8 }
hh3cevtPortSw-Vdsl                   OBJECT IDENTIFIER ::= { hh3cevtPortSwitchType 9 }
hh3cevtPortSw-Stack                  OBJECT IDENTIFIER ::= { hh3cevtPortSwitchType 10 }
hh3cevtPortSw-1000BaseZenithFx       OBJECT IDENTIFIER ::= { hh3cevtPortSwitchType 11 }
hh3cevtPortSw-1000BaseLongFx         OBJECT IDENTIFIER ::= { hh3cevtPortSwitchType 12 }
hh3cevtPortSw-Adsl                   OBJECT IDENTIFIER ::= { hh3cevtPortSwitchType 13 }
hh3cevtPortSw-10or100MDb             OBJECT IDENTIFIER ::= { hh3cevtPortSwitchType 14 }
hh3cevtPortSw-10GBaseLrSm            OBJECT IDENTIFIER ::= { hh3cevtPortSwitchType 15 }
hh3cevtPortSw-10GBaseLx4Mm           OBJECT IDENTIFIER ::= { hh3cevtPortSwitchType 16 }
hh3cevtPortSw-10GBaseLx4Sm           OBJECT IDENTIFIER ::= { hh3cevtPortSwitchType 17 }
hh3cevtPortSw-100MLongFx             OBJECT IDENTIFIER ::= { hh3cevtPortSwitchType 18 }
hh3cevtPortSw-1000BaseCx             OBJECT IDENTIFIER ::= { hh3cevtPortSwitchType 19 }
hh3cevtPortSw-1000BaseZenithFxLc     OBJECT IDENTIFIER ::= { hh3cevtPortSwitchType 20 }
hh3cevtPortSw-1000BaseLongFxLc       OBJECT IDENTIFIER ::= { hh3cevtPortSwitchType 21 }
hh3cevtPortSw-100MSmFxSc             OBJECT IDENTIFIER ::= { hh3cevtPortSwitchType 22 }
hh3cevtPortSw-100MMmFxSc             OBJECT IDENTIFIER ::= { hh3cevtPortSwitchType 23 }
hh3cevtPortSw-100MSmFxLc             OBJECT IDENTIFIER ::= { hh3cevtPortSwitchType 24 }
hh3cevtPortSw-100MMmFxLc             OBJECT IDENTIFIER ::= { hh3cevtPortSwitchType 25 }
hh3cevtPortSw-GbicNoConnector        OBJECT IDENTIFIER ::= { hh3cevtPortSwitchType 26 }
hh3cevtPortSw-Gbic1000BaseT          OBJECT IDENTIFIER ::= { hh3cevtPortSwitchType 27 }
hh3cevtPortSw-Gbic1000BaseLx         OBJECT IDENTIFIER ::= { hh3cevtPortSwitchType 28 }
hh3cevtPortSw-Gbic1000BaseSx         OBJECT IDENTIFIER ::= { hh3cevtPortSwitchType 29 }
hh3cevtPortSw-Gbic1000BaseZx         OBJECT IDENTIFIER ::= { hh3cevtPortSwitchType 30 }
hh3cevtPortSw-ComboNoConnector       OBJECT IDENTIFIER ::= { hh3cevtPortSwitchType 31 }
hh3cevtPortSw-Combo1000BaseLx        OBJECT IDENTIFIER ::= { hh3cevtPortSwitchType 32 }
hh3cevtPortSw-Combo1000BaseLxFiber   OBJECT IDENTIFIER ::= { hh3cevtPortSwitchType 33 }
hh3cevtPortSw-Combo1000BaseLxCopper  OBJECT IDENTIFIER ::= { hh3cevtPortSwitchType 34 }
hh3cevtPortSw-Combo1000BaseSx        OBJECT IDENTIFIER ::= { hh3cevtPortSwitchType 35 }
hh3cevtPortSw-Combo1000BaseSxFiber   OBJECT IDENTIFIER ::= { hh3cevtPortSwitchType 36 }
hh3cevtPortSw-Combo1000BaseSxCopper  OBJECT IDENTIFIER ::= { hh3cevtPortSwitchType 37 }
hh3cevtPortSw-Combo1000BaseZx        OBJECT IDENTIFIER ::= { hh3cevtPortSwitchType 38 }
hh3cevtPortSw-Combo1000BaseZxFiber   OBJECT IDENTIFIER ::= { hh3cevtPortSwitchType 39 }
hh3cevtPortSw-Combo1000BaseZxCopper  OBJECT IDENTIFIER ::= { hh3cevtPortSwitchType 40 }
hh3cevtPortSw-155PosSxMmf            OBJECT IDENTIFIER ::= { hh3cevtPortSwitchType 41 }
hh3cevtPortSw-155PosLxSmf            OBJECT IDENTIFIER ::= { hh3cevtPortSwitchType 42 }

-- added by Garibaldi
hh3cevtPortSw-1000BASE-T             OBJECT IDENTIFIER ::= { hh3cevtPortSwitchType 43 }  -- 1000 Base-T Port
hh3cevtPortSw-1000BASE-SX-SFP        OBJECT IDENTIFIER ::= { hh3cevtPortSwitchType 44 }  -- 1000 Base-SX SFP Port
hh3cevtPortSw-1000BASE-LX-SFP        OBJECT IDENTIFIER ::= { hh3cevtPortSwitchType 45 }  -- 1000 Base-LX SFP Port
hh3cevtPortSw-1000BASE-T-AN-SFP      OBJECT IDENTIFIER ::= { hh3cevtPortSwitchType 46 }  -- 1000 Base-T AN SFP Port
hh3cevtPortSw-10GBASE-LX4-XENPAK     OBJECT IDENTIFIER ::= { hh3cevtPortSwitchType 47 }  -- 10G Base-LX4 XENPAK Port
hh3cevtPortSw-10GBASE-LR-XENPAK      OBJECT IDENTIFIER ::= { hh3cevtPortSwitchType 48 }  -- 10G Base-LR XENPAK Port
hh3cevtPortSw-10GBASE-CX4            OBJECT IDENTIFIER ::= { hh3cevtPortSwitchType 49 }  -- 10G Base-CX4 Port
hh3cevtPortSw-1000BASE-ZX-SFP        OBJECT IDENTIFIER ::= { hh3cevtPortSwitchType 50 }  -- 1000 Base-ZX SFP Port
hh3cevtPortSw-1000BASE-MM-SFP        OBJECT IDENTIFIER ::= { hh3cevtPortSwitchType 51 }  -- 1000 Base-MM SFP Port
hh3cevtPortSw-100BASE-SX-SFP         OBJECT IDENTIFIER ::= { hh3cevtPortSwitchType 52 }  -- 100 Base-SX SFP Port
hh3cevtPortSw-100BASE-LX-SFP         OBJECT IDENTIFIER ::= { hh3cevtPortSwitchType 53 }  -- 100 Base-LX SFP Port
hh3cevtPortSw-100BASE-T-AN-SFP       OBJECT IDENTIFIER ::= { hh3cevtPortSwitchType 54 }  -- 100 Base-T SFP Port
hh3cevtPortSw-100BASE-ZX-SFP         OBJECT IDENTIFIER ::= { hh3cevtPortSwitchType 55 }  -- 100 Base-ZX SFP Port
hh3cevtPortSw-100BASE-MM-SFP         OBJECT IDENTIFIER ::= { hh3cevtPortSwitchType 56 }  -- 100 Base-MM SFP Port
hh3cevtPortSw-SFP-NO-CONNECTOR       OBJECT IDENTIFIER ::= { hh3cevtPortSwitchType 57 }  -- No Connector SFP Port
hh3cevtPortSw-SFP-UNKNOWN-CONNECTOR  OBJECT IDENTIFIER ::= { hh3cevtPortSwitchType 58 }  -- Unknown SFP Port
hh3cevtPortSw-POS-NO-CONNECTOR       OBJECT IDENTIFIER ::= { hh3cevtPortSwitchType 59 }  -- POS no connector
hh3cevtPortSw-10G-BASE-SR            OBJECT IDENTIFIER ::= { hh3cevtPortSwitchType 60 }  -- 10GBASE-SR Fiber Optic Transceivers with SC Connector
hh3cevtPortSw-10G-BASE-ER            OBJECT IDENTIFIER ::= { hh3cevtPortSwitchType 61 }  -- 10GBASE-ER Fiber Optic Transceivers with SC Connector
hh3cevtPortSw-10G-BASE-LX4           OBJECT IDENTIFIER ::= { hh3cevtPortSwitchType 62 }  -- 10GBASE-LX4 Fiber Optic Transceivers with SC Connector
hh3cevtPortSw-10G-BASE-SW            OBJECT IDENTIFIER ::= { hh3cevtPortSwitchType 63 }  -- 10GBASE-SW Fiber Optic Transceivers with SC Connector
hh3cevtPortSw-10G-BASE-LW            OBJECT IDENTIFIER ::= { hh3cevtPortSwitchType 64 }  -- 10GBASE-LW Fiber Optic Transceivers with SC Connector
hh3cevtPortSw-10G-BASE-EW            OBJECT IDENTIFIER ::= { hh3cevtPortSwitchType 65 }  -- 10GBASE-EW Fiber Optic Transceivers with SC Connector
hh3cevtPortSw-10G-LR-SM-LC           OBJECT IDENTIFIER ::= { hh3cevtPortSwitchType 66 }  -- 10GBASE-LR Single Mode Fiber Optic Transceivers with LC Connector
hh3cevtPortSw-10G-SR-MM-LC           OBJECT IDENTIFIER ::= { hh3cevtPortSwitchType 67 }  -- 10GBASE-SR Multi Mode Fiber Optic Transceivers with LC Connector
hh3cevtPortSw-10G-ER-SM-LC           OBJECT IDENTIFIER ::= { hh3cevtPortSwitchType 68 }  -- 10GBASE-ER Single Mode Fiber Optic Transceivers with LC Connector
hh3cevtPortSw-10G-LW-SM-LC           OBJECT IDENTIFIER ::= { hh3cevtPortSwitchType 69 }  -- 10GBASE-LW Single Mode Fiber Optic Transceivers with LC Connector
hh3cevtPortSw-10G-SW-MM-LC           OBJECT IDENTIFIER ::= { hh3cevtPortSwitchType 70 }  -- 10GBASE-SW Multi Mode Fiber Optic Transceivers with LC Connector
hh3cevtPortSw-10G-EW-SM-LC           OBJECT IDENTIFIER ::= { hh3cevtPortSwitchType 71 }  -- 10GBASE-EW Single Mode Fiber Optic Transceivers with LC Connector
hh3cevtPortSw-100BASE-SM-MTRJ        OBJECT IDENTIFIER ::= { hh3cevtPortSwitchType 72 }  -- 100 Base-SM MTRJ Port
hh3cevtPortSw-100BASE-MM-MTRJ        OBJECT IDENTIFIER ::= { hh3cevtPortSwitchType 73 }  -- 100 Base-MM MTRJ Port
hh3cevtPortSw-XFP-NO-CONNECTOR       OBJECT IDENTIFIER ::= { hh3cevtPortSwitchType 74 }  -- XFP without Transceiver
hh3cevtPortSw-XFP-10GBASE-SR         OBJECT IDENTIFIER ::= { hh3cevtPortSwitchType 75 }  -- 10GBASE-SR XFP Transceiver
hh3cevtPortSw-XFP-10GBASE-LR         OBJECT IDENTIFIER ::= { hh3cevtPortSwitchType 76 }  -- 10GBASE-LR XFP Transceiver
hh3cevtPortSw-XFP-10GBASE-ER         OBJECT IDENTIFIER ::= { hh3cevtPortSwitchType 77 }  -- 10GBASE-ER XFP Transceiver
hh3cevtPortSw-XFP-10GBASE-SW         OBJECT IDENTIFIER ::= { hh3cevtPortSwitchType 78 }  -- 10GBASE-SW XFP Transceiver
hh3cevtPortSw-XFP-10GBASE-LW         OBJECT IDENTIFIER ::= { hh3cevtPortSwitchType 79 }  -- 10GBASE-LW XFP Transceiver
hh3cevtPortSw-XFP-10GBASE-EW         OBJECT IDENTIFIER ::= { hh3cevtPortSwitchType 80 }  -- 10GBASE-EW XFP Transceiver
hh3cevtPortSw-XFP-10GBASE-CX4        OBJECT IDENTIFIER ::= { hh3cevtPortSwitchType 81 }  -- 10GBASE-CX4 XFP Transceiver
hh3cevtPortSw-XFP-10GBASE-LX4        OBJECT IDENTIFIER ::= { hh3cevtPortSwitchType 82 }  -- 10GBASE-LX4 XFP Transceiver
hh3cevtPortSw-XFP-UNKNOWN            OBJECT IDENTIFIER ::= { hh3cevtPortSwitchType 83 }  -- Unknown  XFP Transceiver
hh3cevtPortSw-XPK-NOCONNECTOR        OBJECT IDENTIFIER ::= { hh3cevtPortSwitchType 84 }  -- Xenpak without Transceiver
hh3cevtPortSw-XPK-10GBASE-SR         OBJECT IDENTIFIER ::= { hh3cevtPortSwitchType 85 }  -- 10GBASE-SR Xenpak Transceiver
hh3cevtPortSw-XPK-10GBASE-LR         OBJECT IDENTIFIER ::= { hh3cevtPortSwitchType 86 }  -- 10GBASE-LR Xenpak Transceiver
hh3cevtPortSw-XPK-10GBASE-ER         OBJECT IDENTIFIER ::= { hh3cevtPortSwitchType 87 }  -- 10GBASE-ER Xenpak Transceiver
hh3cevtPortSw-XPK-10GBASE-SW         OBJECT IDENTIFIER ::= { hh3cevtPortSwitchType 88 }  -- 10GBASE-SW Xenpak Transceiver
hh3cevtPortSw-XPK-10GBASE-LW         OBJECT IDENTIFIER ::= { hh3cevtPortSwitchType 89 }  -- 10GBASE-LW Xenpak Transceiver
hh3cevtPortSw-XPK-10GBASE-EW         OBJECT IDENTIFIER ::= { hh3cevtPortSwitchType 90 }  -- 10GBASE-EW Xenpak Transceiver
hh3cevtPortSw-XPK-10GBASE-CX4        OBJECT IDENTIFIER ::= { hh3cevtPortSwitchType 91 }  -- 10GBASE-CX4 Xenpak Transceiver
hh3cevtPortSw-XPK-10GBASE-LX4        OBJECT IDENTIFIER ::= { hh3cevtPortSwitchType 92 }  -- 10GBASE-LX4 Xenpak Transceiver
hh3cevtPortSw-XPK-UNKNOWN            OBJECT IDENTIFIER ::= { hh3cevtPortSwitchType 93 }  -- Unknown Xenpak Transceiver
hh3cevtPortSw-POS-OC48-SR-SM-LC      OBJECT IDENTIFIER ::= { hh3cevtPortSwitchType 94 }  -- OC48-SR Single Mode Fiber Optic Transceivers with LC Connector
hh3cevtPortSw-POS-OC48-IR-SM-LC      OBJECT IDENTIFIER ::= { hh3cevtPortSwitchType 95 }  -- OC48-IR Single Mode Fiber Optic Transceivers with LC Connector
hh3cevtPortSw-POS-OC48-LR-SM-LC      OBJECT IDENTIFIER ::= { hh3cevtPortSwitchType 96 }  -- OC48-LR Single Mode Fiber Optic Transceivers with LC Connector
hh3cevtPortSw-10G-BASE-CX4           OBJECT IDENTIFIER ::= { hh3cevtPortSwitchType 97 }  -- 10G BASE-CX4 Electrical Interface
hh3cevtPortSw-OLT-1000BASE-BX-SFF-SC OBJECT IDENTIFIER ::= { hh3cevtPortSwitchType 98 }  -- 1000 BASE-BX SFF SC OLT Interface
hh3cevtPortSw-ONU-1000BASE-BX-SFF-SC OBJECT IDENTIFIER ::= { hh3cevtPortSwitchType 99 }  -- 1000 BASE-BX SFF SC ONU Interface
hh3cevtPortSw-24G-CASCADE            OBJECT IDENTIFIER ::= { hh3cevtPortSwitchType 100 }  -- 24G Cascade port
hh3cevtPortSw-POS-OC3-SR-MM          OBJECT IDENTIFIER ::= { hh3cevtPortSwitchType 101 }  -- STM1/OC3 Short Reach Multi Mode Fiber Optic Transceivers with LC Connector
hh3cevtPortSw-POS-OC3-IR-SM          OBJECT IDENTIFIER ::= { hh3cevtPortSwitchType 102 }  -- STM1/OC3 Intermediate Reach Single Mode Fiber Optic Transceivers with LC Connector
hh3cevtPortSw-POS-OC3-IR-1-SM        OBJECT IDENTIFIER ::= { hh3cevtPortSwitchType 103 }  -- STM1/OC3 Intermediate Reach Single Mode Fiber Optic Transceivers with LC Connector(variation 1)
hh3cevtPortSw-POS-OC3-IR-2-SM        OBJECT IDENTIFIER ::= { hh3cevtPortSwitchType 104 }  -- STM1/OC3 Intermediate Reach Single Mode Fiber Optic Transceivers with LC Connector(variation 2)
hh3cevtPortSw-POS-OC3-LR-SM          OBJECT IDENTIFIER ::= { hh3cevtPortSwitchType 105 }  -- STM1/OC3 Long Reach Single Mode Fiber Optic Transceivers with LC Connector
hh3cevtPortSw-POS-OC3-LR-1-SM        OBJECT IDENTIFIER ::= { hh3cevtPortSwitchType 106 }  -- STM1/OC3 Long Reach Single Mode Fiber Optic Transceivers with LC Connector(variation 1)
hh3cevtPortSw-POS-OC3-LR-2-SM        OBJECT IDENTIFIER ::= { hh3cevtPortSwitchType 107 }  -- STM1/OC3 Long Reach Single Mode Fiber Optic Transceivers with LC Connector(variation 2)
hh3cevtPortSw-POS-OC3-LR-3-SM        OBJECT IDENTIFIER ::= { hh3cevtPortSwitchType 108 }  -- STM1/OC3 Long Reach Single Mode Fiber Optic Transceivers with LC Connector(variation 3)
hh3cevtPortSw-POS-OC12-SR-MM         OBJECT IDENTIFIER ::= { hh3cevtPortSwitchType 109 }  -- STM4/OC12 Short Reach Multi Mode Fiber Optic Transceivers with LC Connector
hh3cevtPortSw-POS-OC12-IR-SM         OBJECT IDENTIFIER ::= { hh3cevtPortSwitchType 110 }  -- STM4/OC12 Intermediate Reach Single Mode Fiber Optic Transceivers with LC Connector
hh3cevtPortSw-POS-OC12-IR-1-SM       OBJECT IDENTIFIER ::= { hh3cevtPortSwitchType 111 }  -- STM4/OC12 Intermediate Reach Single Mode Fiber Optic Transceivers with LC Connector(variation 1)
hh3cevtPortSw-POS-OC12-IR-2-SM       OBJECT IDENTIFIER ::= { hh3cevtPortSwitchType 112 }  -- STM4/OC12 Intermediate Reach Single Mode Fiber Optic Transceivers with LC Connector(variation 2)
hh3cevtPortSw-POS-OC12-LR-SM         OBJECT IDENTIFIER ::= { hh3cevtPortSwitchType 113 }  -- STM4/OC12 Long Reach Single Mode Fiber Optic Transceivers with LC Connector
hh3cevtPortSw-POS-OC12-LR-1-SM       OBJECT IDENTIFIER ::= { hh3cevtPortSwitchType 114 }  -- STM4/OC12 Long Reach Single Mode Fiber Optic Transceivers with LC Connector(variation 1)
hh3cevtPortSw-POS-OC12-LR-2-SM       OBJECT IDENTIFIER ::= { hh3cevtPortSwitchType 115 }  -- STM4/OC12 Long Reach Single Mode Fiber Optic Transceivers with LC Connector(variation 2)
hh3cevtPortSw-POS-OC12-LR-3-SM       OBJECT IDENTIFIER ::= { hh3cevtPortSwitchType 116 }  -- STM4/OC12 Long Reach Single Mode Fiber Optic Transceivers with LC Connector(variation 3)
hh3cevtPortSw-POS-OC48-SR-SM         OBJECT IDENTIFIER ::= { hh3cevtPortSwitchType 117 }  -- STM16/OC48 Short Reach Single Mode Fiber Optic Transceivers with LC Connector
hh3cevtPortSw-POS-OC48-IR-SM         OBJECT IDENTIFIER ::= { hh3cevtPortSwitchType 118 }  -- STM16/OC48 Intermediate Reach Single Mode Fiber Optic Transceivers with LC Connector
hh3cevtPortSw-POS-OC48-IR-1-SM       OBJECT IDENTIFIER ::= { hh3cevtPortSwitchType 119 }  -- STM16/OC48 Intermediate Reach Single Mode Fiber Optic Transceivers with LC Connector(variation 1)
hh3cevtPortSw-POS-OC48-IR-2-SM       OBJECT IDENTIFIER ::= { hh3cevtPortSwitchType 120 }  -- STM16/OC48 Intermediate Reach Single Mode Fiber Optic Transceivers with LC Connector(variation 2)
hh3cevtPortSw-POS-OC48-LR-SM         OBJECT IDENTIFIER ::= { hh3cevtPortSwitchType 121 }  -- STM16/OC48 Long Reach Single Mode Fiber Optic Transceivers with LC Connector
hh3cevtPortSw-POS-OC48-LR-1-SM       OBJECT IDENTIFIER ::= { hh3cevtPortSwitchType 122 }  -- STM16/OC48 Long Reach Single Mode Fiber Optic Transceivers with LC Connector(variation 1)
hh3cevtPortSw-POS-OC48-LR-2-SM       OBJECT IDENTIFIER ::= { hh3cevtPortSwitchType 123 }  -- STM16/OC48 Long Reach Single Mode Fiber Optic Transceivers with LC Connector(variation 2)
hh3cevtPortSw-POS-OC48-LR-3-SM       OBJECT IDENTIFIER ::= { hh3cevtPortSwitchType 124 }  -- STM16/OC48 Long Reach Single Mode Fiber Optic Transceivers with LC Connector(variation 3)
hh3cevtPortSw-POS-I-64-1             OBJECT IDENTIFIER ::= { hh3cevtPortSwitchType 125 }  -- STM64/OC192 Interconnect Fiber Optic Transceivers with LC Connector(wavelength 1310nm G.652 fiber)
hh3cevtPortSw-POS-I-64-2             OBJECT IDENTIFIER ::= { hh3cevtPortSwitchType 126 }  -- STM64/OC192 Interconnect Fiber Optic Transceivers with LC Connector(wavelength 1550nm G.652 fiber)
hh3cevtPortSw-POS-I-64-3             OBJECT IDENTIFIER ::= { hh3cevtPortSwitchType 127 }  -- STM64/OC192 Interconnect Fiber Optic Transceivers with LC Connector(wavelength 1550nm G.653 fiber)
hh3cevtPortSw-POS-I-64-5             OBJECT IDENTIFIER ::= { hh3cevtPortSwitchType 128 }  -- STM64/OC192 Interconnect Fiber Optic Transceivers with LC Connector(wavelength 1550nm G.655 fiber)
hh3cevtPortSw-POS-S-64-1             OBJECT IDENTIFIER ::= { hh3cevtPortSwitchType 129 }  -- STM64/OC192 Short Haul Fiber Optic Transceivers with LC Connector(wavelength 1310nm G.652 fiber)
hh3cevtPortSw-POS-S-64-2             OBJECT IDENTIFIER ::= { hh3cevtPortSwitchType 130 }  -- STM64/OC192 Short Haul Fiber Optic Transceivers with LC Connector(wavelength 1550nm G.652 fiber)
hh3cevtPortSw-POS-S-64-3             OBJECT IDENTIFIER ::= { hh3cevtPortSwitchType 131 }  -- STM64/OC192 Short Haul Fiber Optic Transceivers with LC Connector(wavelength 1550nm G.653 fiber)
hh3cevtPortSw-POS-S-64-5             OBJECT IDENTIFIER ::= { hh3cevtPortSwitchType 132 }  -- STM64/OC192 Short Haul Fiber Optic Transceivers with LC Connector(wavelength 1550nm G.655 fiber)
hh3cevtPortSw-POS-L-64-1             OBJECT IDENTIFIER ::= { hh3cevtPortSwitchType 133 }  -- STM64/OC192 Long Haul Fiber Optic Transceivers with LC Connector(wavelength 1310nm G.652 fiber)
hh3cevtPortSw-POS-L-64-2             OBJECT IDENTIFIER ::= { hh3cevtPortSwitchType 134 }  -- STM64/OC192 Long Haul Fiber Optic Transceivers with LC Connector(wavelength 1550nm G.652 fiber)
hh3cevtPortSw-POS-L-64-3             OBJECT IDENTIFIER ::= { hh3cevtPortSwitchType 135 }  -- STM64/OC192 Long Haul Fiber Optic Transceivers with LC Connector(wavelength 1550nm G.653 fiber)
hh3cevtPortSw-POS-V-64-2             OBJECT IDENTIFIER ::= { hh3cevtPortSwitchType 136 }  -- STM64/OC192 Very Long Haul Fiber Optic Transceivers with LC Connector(wavelength 1550nm G.652 fiber)
hh3cevtPortSw-POS-V-64-3             OBJECT IDENTIFIER ::= { hh3cevtPortSwitchType 137 }  -- STM64/OC192 Very Long Haul Fiber Optic Transceivers with LC Connector(wavelength 1550nm G.653 fiber)
hh3cevtPortSw-100BASE-FX-BIDI        OBJECT IDENTIFIER ::= { hh3cevtPortSwitchType 138 }  -- 100 BASE-FX BIDI Port
hh3cevtPortSw-100BASE-BX10-U-SFP     OBJECT IDENTIFIER ::= { hh3cevtPortSwitchType 139 }  -- 100 BASE-BX10-U-SFP Port
hh3cevtPortSw-100BASE-BX10-D-SFP     OBJECT IDENTIFIER ::= { hh3cevtPortSwitchType 140 }  -- 100 BASE-BX10-D-SFP Port
hh3cevtPortSw-1000BASE-BX10-U-SFP    OBJECT IDENTIFIER ::= { hh3cevtPortSwitchType 141 }  -- 1000 BASE-BX10-U-SFP Port
hh3cevtPortSw-1000BASE-BX10-D-SFP    OBJECT IDENTIFIER ::= { hh3cevtPortSwitchType 142 }  -- 1000 BASE-BX10-D-SFP Port
hh3cevtPortSw-STK-1000BASE-T         OBJECT IDENTIFIER ::= { hh3cevtPortSwitchType 143 }  -- 1000 BASE-T Stack Port
hh3cevtPortSw-RPR-PHYPOS-CONNECTOR     OBJECT IDENTIFIER ::= { hh3cevtPortSwitchType 144 }  -- Resilient Packet Ring POS physical port
hh3cevtPortSw-RPR-PHY10GE-CONNECTOR    OBJECT IDENTIFIER ::= { hh3cevtPortSwitchType 145 }  -- 10G Resilient Packet Ring physical port
hh3cevtPortSw-RPR-LOGICPOS-CONNECTOR   OBJECT IDENTIFIER ::= { hh3cevtPortSwitchType 146 }  -- Resilient Packet Ring POS logical port
hh3cevtPortSw-RPR-LOGIC10GE-CONNECTOR  OBJECT IDENTIFIER ::= { hh3cevtPortSwitchType 147 }  -- 10G Resilient Packet Ring logical port
hh3cevtPortSw-10GBASE-ZR               OBJECT IDENTIFIER ::= { hh3cevtPortSwitchType 148 }  -- Fiber Optic Transceivers with SC Connector, XENPAK
hh3cevtPortSw-TYPE-ERROR-CONNECTOR     OBJECT IDENTIFIER ::= { hh3cevtPortSwitchType 149 }  -- Error Optic Transceivers type
hh3cevtPortSw-10G-STACK                OBJECT IDENTIFIER ::= { hh3cevtPortSwitchType 150 }  -- 10G Stack Port
hh3cevtPortSw-155-ATM-SX-MMF             OBJECT IDENTIFIER ::= { hh3cevtPortSwitchType 151 }  -- ATM OC-3 Multi-mode Short Reach Optical Transceiver
hh3cevtPortSw-155-ATM-LX-SMF             OBJECT IDENTIFIER ::= { hh3cevtPortSwitchType 152 }  -- ATM OC-3 Single Mode Long Reach Optical Transceiver
hh3cevtPortSw-622-ATM-SX-MMF             OBJECT IDENTIFIER ::= { hh3cevtPortSwitchType 153 }  -- ATM OC-12 Multi-mode Short Reach Optical Transceiver
hh3cevtPortSw-622-ATM-LX-SMF             OBJECT IDENTIFIER ::= { hh3cevtPortSwitchType 154 }  -- ATM OC-12 Single Mode Long Reach Optical Transceiver
hh3cevtPortSw-155-ATM-NO-CONNECTOR       OBJECT IDENTIFIER ::= { hh3cevtPortSwitchType 155 }  -- ATM OC-3 No Connector
hh3cevtPortSw-622-ATM-NO-CONNECTOR       OBJECT IDENTIFIER ::= { hh3cevtPortSwitchType 156 }  -- ATM OC-12 No Connector
hh3cevtPortSw-155-CPOS-E1-NO-CONNECTOR   OBJECT IDENTIFIER ::= { hh3cevtPortSwitchType 157 }  -- CPOS(E1) OC-3 No Connector
hh3cevtPortSw-155-CPOS-T1-NO-CONNECTOR   OBJECT IDENTIFIER ::= { hh3cevtPortSwitchType 158 }  -- CPOS(T1) OC-3 No Connector
hh3cevtPortSw-622-CPOS-E1-NO-CONNECTOR   OBJECT IDENTIFIER ::= { hh3cevtPortSwitchType 159 }  -- CPOS(E1) OC-12 No Connector
hh3cevtPortSw-622-CPOS-T1-NO-CONNECTOR   OBJECT IDENTIFIER ::= { hh3cevtPortSwitchType 160 }  -- CPOS(T1) OC-12 No Connector
hh3cevtPortSw-155-CPOS-E1-SX-MMF         OBJECT IDENTIFIER ::= { hh3cevtPortSwitchType 161 }  -- CPOS(E1) OC-3 Multi-mode Short Reach Optical Transceiver
hh3cevtPortSw-155-CPOS-T1-SX-MMF         OBJECT IDENTIFIER ::= { hh3cevtPortSwitchType 162 }  -- CPOS(T1) OC-3 Multi-mode Short Reach Optical Transceiver
hh3cevtPortSw-155-CPOS-E1-LX-SMF         OBJECT IDENTIFIER ::= { hh3cevtPortSwitchType 163 }  -- CPOS(E1) OC-3 Single Mode Long Reach Optical Transceiver
hh3cevtPortSw-155-CPOS-T1-LX-SMF         OBJECT IDENTIFIER ::= { hh3cevtPortSwitchType 164 }  -- CPOS(T1) OC-3 Single Mode Long Reach Optical Transceiver
hh3cevtPortSw-622-CPOS-E1-SX-MMF         OBJECT IDENTIFIER ::= { hh3cevtPortSwitchType 165 }  -- CPOS(E1) OC-12 Multi-mode Short Reach Optical Transceiver
hh3cevtPortSw-622-CPOS-T1-SX-MMF         OBJECT IDENTIFIER ::= { hh3cevtPortSwitchType 166 }  -- CPOS(T1) OC-12 Multi-mode Short Reach Optical Transceiver
hh3cevtPortSw-622-CPOS-E1-LX-SMF         OBJECT IDENTIFIER ::= { hh3cevtPortSwitchType 167 }  -- CPOS(E1) OC-12 Multi-mode Short Reach Optical Transceiver
hh3cevtPortSw-622-CPOS-T1-LX-SMF         OBJECT IDENTIFIER ::= { hh3cevtPortSwitchType 168 }  -- CPOS(T1) OC-12 Single Mode Long Reach Optical Transceiver
hh3cevtPortSw-E1-CONNECTOR               OBJECT IDENTIFIER ::= { hh3cevtPortSwitchType 169 }  -- E1 RJ45 Transceiver
hh3cevtPortSw-T1-CONNECTOR               OBJECT IDENTIFIER ::= { hh3cevtPortSwitchType 170 }  -- T1 RJ45 Transceiver
hh3cevtPortSw-1000BASE-STK-SFP           OBJECT IDENTIFIER ::= { hh3cevtPortSwitchType 171 }  -- 1-port 1000 Base-STK SFP Module
hh3cevtPortSw-1000BASE-BIDI-SFP          OBJECT IDENTIFIER ::= { hh3cevtPortSwitchType 172 }  -- 1-port 1000 Base-BIDI SFP Module
hh3cevtPortSw-1000BASE-CWDM-SFP          OBJECT IDENTIFIER ::= { hh3cevtPortSwitchType 173 }  -- 1-port 1000 Base-CWDM SFP Module
hh3cevtPortSw-100BASE-BIDI-SFP           OBJECT IDENTIFIER ::= { hh3cevtPortSwitchType 174 }  -- 1-port 100 Base-BIDI SFP Module
hh3cevtPortSw-OLT-1000BASE-PX-SFP        OBJECT IDENTIFIER ::= { hh3cevtPortSwitchType 175 }  -- 1000BASE-PX SFP OLT Interface
hh3cevtPortSw-OLT-1000BASE-NO-CONNECTOR  OBJECT IDENTIFIER ::= { hh3cevtPortSwitchType 176 }  -- 1000BASE OLT No Connector
hh3cevtPortSw-RPR-PHYGE-CONNECTOR        OBJECT IDENTIFIER ::= { hh3cevtPortSwitchType 177 }  -- Resilient Packet Ring GE physical port
hh3cevtPortSw-RPR-LOGICGE-CONNECTOR      OBJECT IDENTIFIER ::= { hh3cevtPortSwitchType 178 }  -- Resilient Packet Ring GE logical port
hh3cevtPortSw-100M-1550-BIDI             OBJECT IDENTIFIER ::= { hh3cevtPortSwitchType 179 }  -- Single Port 100M Ethernet Bi-direction Optical Interface Module(TX1550nm, RX1310nm, 15km, SC)
hh3cevtPortSw-100M-1310-BIDI             OBJECT IDENTIFIER ::= { hh3cevtPortSwitchType 180 }  -- Single Port 100M Ethernet Bi-direction Optical reverse Interface Module(TX1310nm, RX1550nm, 15km, SC)
hh3cevtPortSw-RPR-PHYOC48-CONNECTOR      OBJECT IDENTIFIER ::= { hh3cevtPortSwitchType 181 }  -- Resilient Packet Ring OC48 physical port
hh3cevtPortSw-RPR-LOGICOC48-CONNECTOR    OBJECT IDENTIFIER ::= { hh3cevtPortSwitchType 182 }  -- Resilient Packet Ring OC48 logical port
hh3cevtPortSw-100-1000-BASE-LX-SMF       OBJECT IDENTIFIER ::= { hh3cevtPortSwitchType 183 }  -- 100BASE-LX/1000BASE-LX Single Mode Fiber Optic Transceivers
hh3cevtPortSw-10G-ZW-SM-LC               OBJECT IDENTIFIER ::= { hh3cevtPortSwitchType 184 }  -- 10GBASE-ZW Single Mode Fiber Optic Transceivers with LC Connector
hh3cevtPortSw-10G-ZR-SM-LC               OBJECT IDENTIFIER ::= { hh3cevtPortSwitchType 185 }  -- 10GBASE-ZR Single Mode Fiber Optic Transceivers with LC Connector
hh3cevtPortSw-XPK-10GBASE-ZR             OBJECT IDENTIFIER ::= { hh3cevtPortSwitchType 186 }  -- 10GBASE-ZR Xenpak Transceiver:LH80,SM1550
hh3cevtPortSw-SGMII-100-BASE-LX-SFP      OBJECT IDENTIFIER ::= { hh3cevtPortSwitchType 187 }  -- SGMII-100-BASE-LX-SFP Transceiver
hh3cevtPortSw-SGMII-100-BASE-FX-SFP      OBJECT IDENTIFIER ::= { hh3cevtPortSwitchType 188 }  -- SGMII-100-BASE-FX-SFP Transceiver
hh3cevtPortSw-WLAN-RADIO                 OBJECT IDENTIFIER ::= { hh3cevtPortSwitchType 189 }  -- WLAN-RADIO Transceiver
hh3cevtPortSw-CABLE                      OBJECT IDENTIFIER ::= { hh3cevtPortSwitchType 190 }  -- Cable Port
hh3cevtPortSw-SFP-PLUS-NO-CONNECTOR      OBJECT IDENTIFIER ::= { hh3cevtPortSwitchType 191 }  -- SFP+ without Transceiver
hh3cevtPortSw-SFP-PLUS-10GBASE-SR        OBJECT IDENTIFIER ::= { hh3cevtPortSwitchType 192 }  -- 10GBASE-SR SFP+ Transceiver
hh3cevtPortSw-SFP-PLUS-10GBASE-LR        OBJECT IDENTIFIER ::= { hh3cevtPortSwitchType 193 }  -- 10GBASE-LR SFP+ Transceiver
hh3cevtPortSw-SFP-PLUS-10GBASE-LRM       OBJECT IDENTIFIER ::= { hh3cevtPortSwitchType 194 }  -- 10GBASE-LRM SFP+ Transceiver
hh3cevtPortSw-SFP-PLUS-10GBASE-Cu        OBJECT IDENTIFIER ::= { hh3cevtPortSwitchType 195 }  -- 10GBASE-Cu SFP+ Transceiver
hh3cevtPortSw-SFP-PLUS-UNKNOWN           OBJECT IDENTIFIER ::= { hh3cevtPortSwitchType 196 }  -- Unknown SFP+ Transceiver
hh3cevtPortSw-SFP-PLUS-STACK-CONNECTOR   OBJECT IDENTIFIER ::= { hh3cevtPortSwitchType 197 }  -- SFP+ STACK Transceiver
hh3cevtPortSw-POS-L-64-4                 OBJECT IDENTIFIER ::= { hh3cevtPortSwitchType 198 }  -- STM64/OC192 Long Haul Fiber Optic Transceivers with LC Connector(wavelength 1550nm G.653 fiber)
hh3cevtPortSw-MINISAS-HD-STACK-CONNECTOR OBJECT IDENTIFIER ::= { hh3cevtPortSwitchType 199 }  -- MiniSAS HD STACK Transceiver
hh3cevtPortSw-ONU-1000BASE-PX-SFF        OBJECT IDENTIFIER ::= { hh3cevtPortSwitchType 200 }  -- 1000BASE-PX SFF ONU Interface
hh3cevtPortSw-RS485                      OBJECT IDENTIFIER ::= { hh3cevtPortSwitchType 201 }  -- RS-485 Interface
hh3cevtPortSw-SFP-PLUS-10GBASE-ER        OBJECT IDENTIFIER ::= { hh3cevtPortSwitchType 202 }  -- 10GBASE-ER SFP+ Transceiver
hh3cevtPortSw-SFP-PLUS-10GBASE-ZR        OBJECT IDENTIFIER ::= { hh3cevtPortSwitchType 203 }  -- 10GBASE-ZR SFP+ Transceiver
hh3cevtPortSw-XFP-10GBASE-ZR             OBJECT IDENTIFIER ::= { hh3cevtPortSwitchType 204 }  -- 10GBASE-ZR XFP Transceiver
hh3cevtPortSw-QSFP-PLUS-40GBASE-SR4      OBJECT IDENTIFIER ::= { hh3cevtPortSwitchType 205 }  -- 40BASE-SR4 QSFP+ Optical Transceiver
hh3cevtPortSw-QSFP-PLUS-STACK-CONNECTOR  OBJECT IDENTIFIER ::= { hh3cevtPortSwitchType 206 }  -- QSFP+ STACK Transceiver
hh3cevtPortSw-QSFP-PLUS-TO-4SFP-PLUS-STACK-CONNECTOR OBJECT IDENTIFIER ::= { hh3cevtPortSwitchType 207 }  -- QSFP+ to 4 SFP+ STACK Transceiver
hh3cevtPortSw-SFP-STACK-CONNECTOR        OBJECT IDENTIFIER ::= { hh3cevtPortSwitchType 208 }  -- SFP STACK Transceiver
hh3cevtPortSw-QSFP-NO-CONNECTOR          OBJECT IDENTIFIER ::= { hh3cevtPortSwitchType 209 }  -- QSFP No Connector
hh3cevtPortSw-10GBase-T                  OBJECT IDENTIFIER ::= { hh3cevtPortSwitchType 210 }  -- 10G Base-T Port
hh3cevtPortSw-CFP-NO-CONNECTOR           OBJECT IDENTIFIER ::= { hh3cevtPortSwitchType 211 }  -- CFP No Connector
hh3cevtPortSw-CFP-40GBASE-LR4            OBJECT IDENTIFIER ::= { hh3cevtPortSwitchType 212 }  -- 40GBASE-LR4 CFP Transceiver
hh3cevtPortSw-QSFP-PLUS-NO-CONNECTOR     OBJECT IDENTIFIER ::= { hh3cevtPortSwitchType 213 }  -- QSFP+ No Connector
hh3cevtPortSw-QSFP-PLUS-40GBASE-LR4      OBJECT IDENTIFIER ::= { hh3cevtPortSwitchType 214 }  -- 40GBASE-LR4 QSFP+ Optical Transceiver
hh3cevtPortSw-CFP-40GBASE-SR4            OBJECT IDENTIFIER ::= { hh3cevtPortSwitchType 215 }  -- 40GBASE-SR4 CFP Optical Transceiver
hh3cevtPortSw-CFP-100GBASE-LR4           OBJECT IDENTIFIER ::= { hh3cevtPortSwitchType 216 }  -- 100GBASE-LR4 CFP Optical Transceiver
hh3cevtPortSw-CFP-100GBASE-SR10          OBJECT IDENTIFIER ::= { hh3cevtPortSwitchType 217 }  -- 100GBASE-SR10 CFP Optical Transceiver
hh3cevtPortSw-CXP-100GBASE-SR10          OBJECT IDENTIFIER ::= { hh3cevtPortSwitchType 218 }  -- 100GBASE-SR10 CXP Optical Transceiver
hh3cevtPortSw-CXP-NO-CONNECTOR           OBJECT IDENTIFIER ::= { hh3cevtPortSwitchType 219 }  -- CXP No Connector
hh3cevtPortSw-TRANSCEIVER-UNKNOWN        OBJECT IDENTIFIER ::= { hh3cevtPortSwitchType 220 }  -- Unknown Transceiver
hh3cevtPortSw-QSFP-PLUS-UNKNOWN          OBJECT IDENTIFIER ::= { hh3cevtPortSwitchType 221 }  -- Unknown QSFP+ Transceiver
hh3cevtPortSw-CFP-UNKNOWN                OBJECT IDENTIFIER ::= { hh3cevtPortSwitchType 222 }  -- Unknown CFP Transceiver
hh3cevtPortSw-QSFP-PLUS-40GBASE-CSR4     OBJECT IDENTIFIER ::= { hh3cevtPortSwitchType 223 }  -- 40GBASE-CSR4 QSFP+ Optical Transceiver
hh3cevtPortSw-CFP-40GBASE-ER4            OBJECT IDENTIFIER ::= { hh3cevtPortSwitchType 224 }  -- 40GBASE-ER4 CFP Optical Transceiver
hh3cevtPortSw-SFP-1000BASE-BIDI          OBJECT IDENTIFIER ::= { hh3cevtPortSwitchType 225 }  -- 1000BASE SFP Bi-direction Optical Transceiver
hh3cevtPortSw-SFP-PLUS-10GBASE-ZR-DWDM   OBJECT IDENTIFIER ::= { hh3cevtPortSwitchType 226 }  -- 10GBase-ZR SFP+ DWDM Optical Transceiver
hh3cevtPortSw-QSFP-PLUS-40GBASE-PSM      OBJECT IDENTIFIER ::= { hh3cevtPortSwitchType 227 }  -- 40GBASE QSFP+ Parallel SingleMode Optical Transceiver
hh3cevtPortSw-SFP-8GFC-SW                OBJECT IDENTIFIER ::= { hh3cevtPortSwitchType 228 }  -- SFP 8G FC Optical Transceiver short wave
hh3cevtPortSw-SFP-8GFC-LW                OBJECT IDENTIFIER ::= { hh3cevtPortSwitchType 229 }  -- SFP 8G FC Optical Transceiver long wave
hh3cevtPortSw-CXP-100GBASE-AOC           OBJECT IDENTIFIER ::= { hh3cevtPortSwitchType 230 }  -- 100GBASE CXP Active Optical Cable
hh3cevtPortSw-QSFP-PLUS-ACTIVE-STACK-CONNECTOR  OBJECT IDENTIFIER ::= { hh3cevtPortSwitchType 231 }  -- QSFP+ Active STACK Transceiver
hh3cevtPortSw-QSFP-PLUS-TO-4SFP-PLUS-ACTIVE-STACK-CONNECTOR  OBJECT IDENTIFIER ::= { hh3cevtPortSwitchType 232 }  -- QSFP+ to 4 SFP+ Active STACK Transceiver
hh3cevtPortSw-CFP2-100GBASE-LR4          OBJECT IDENTIFIER ::= { hh3cevtPortSwitchType 233 }  -- 100GBASE-LR4 CFP2 Optical Transceiver
hh3cevtPortSw-CFP2-100GBASE-SR10         OBJECT IDENTIFIER ::= { hh3cevtPortSwitchType 234 }  -- 100GBASE-SR10 CFP2 Optical Transceiver
hh3cevtPortSw-QSFP-PLUS-ACTIVE-OPTICAL-CABLE  OBJECT IDENTIFIER ::= { hh3cevtPortSwitchType 235 }  -- QSFP+ AOC
hh3cevtPortSw-QSFP-PLUS-TO-4SFP-PLUS-ACTIVE-OPTICAL-CABLE OBJECT IDENTIFIER ::= { hh3cevtPortSwitchType 236 }  -- QSFP+ to 4 SFP+ AOC
hh3cevtPortSw-SFP-PLUS-ACTIVE-OPTICAL-CABLE   OBJECT IDENTIFIER ::= { hh3cevtPortSwitchType 237 }  -- SFP+ AOC
hh3cevtPortSw-CFP2-NO-CONNECTOR         OBJECT IDENTIFIER ::= { hh3cevtPortSwitchType 238 }  -- CFP2 No Connector
hh3cevtPortSw-QSFP28-NO-CONNECTOR       OBJECT IDENTIFIER ::= { hh3cevtPortSwitchType 239 }  -- QSFP28 No Connector
hh3cevtPortSw-QSFP28-100GBASE-SR4       OBJECT IDENTIFIER ::= { hh3cevtPortSwitchType 240 }  -- 100BASE-SR4 QSFP28 Optical Transceiver
hh3cevtPortSw-QSFP28-100GBASE-LR4       OBJECT IDENTIFIER ::= { hh3cevtPortSwitchType 241 }  -- 100GBASE-LR4 QSFP28 Optical Transceiver
hh3cevtPortSw-QSFP28-100GBASE-ER4       OBJECT IDENTIFIER ::= { hh3cevtPortSwitchType 242 }  -- 100GBASE-ER4 QSFP28 Optical Transceiver
hh3cevtPortSw-QSFP28-100GBASE-PSM4      OBJECT IDENTIFIER ::= { hh3cevtPortSwitchType 243 }  -- 100GBASE-PSM4 QSFP28 Optical Transceiver
hh3cevtPortSw-QSFP28-100GBASE-CWDM4     OBJECT IDENTIFIER ::= { hh3cevtPortSwitchType 244 }  -- 100GBASE-CWDM4 QSFP28 Optical Transceiver
hh3cevtPortSw-QSFP28-STACK-CONNECTOR    OBJECT IDENTIFIER ::= { hh3cevtPortSwitchType 245 }  -- QSFP28 STACK Transceiver
hh3cevtPortSw-QSFP28-TO-4SFP28-STACK-CONNECTOR  OBJECT IDENTIFIER ::= { hh3cevtPortSwitchType 246 }  -- QSFP28 to 4 SFP28 STACK Transceiver
hh3cevtPortSw-QSFP28-ACTIVE-STACK-CONNECTOR     OBJECT IDENTIFIER ::= { hh3cevtPortSwitchType 247 }  -- QSFP28 Active STACK Transceiver
hh3cevtPortSw-QSFP28-TO-4SFP28-ACTIVE-STACK-CONNECTOR   OBJECT IDENTIFIER ::= { hh3cevtPortSwitchType 248 }  -- QSFP28 to 4 SFP28 Active STACK Transceiver
hh3cevtPortSw-QSFP28-ACTIVE-OPTICAL-CABLE       OBJECT IDENTIFIER ::= { hh3cevtPortSwitchType 249 }  -- QSFP28 AOC
hh3cevtPortSw-QSFP28-TO-4SFP28-ACTIVE-OPTICAL-CABLE OBJECT IDENTIFIER ::= { hh3cevtPortSwitchType 250 }  -- QSFP28 to 4 SFP28 AOC
hh3cevtPortSw-QSFP-PLUS-40GBASE-LM4     OBJECT IDENTIFIER ::= { hh3cevtPortSwitchType 251 }  -- 40BASE-LM4 QSFP+ Optical Transceiver
hh3cevtPortSw-QSFP-PLUS-40GBASE-SWDM4   OBJECT IDENTIFIER ::= { hh3cevtPortSwitchType 252 }  -- 40BASE-SWDM4 QSFP+ Optical Transceiver
hh3cevtPortSw-CFP-100GBASE-ER4          OBJECT IDENTIFIER ::= { hh3cevtPortSwitchType 253 }  -- 100GBASE-ER4 CFP Transceiver
hh3cevtPortSw-QSFP-PLUS-40GBASE-ER4     OBJECT IDENTIFIER ::= { hh3cevtPortSwitchType 254 }  -- 40BASE-ER4 QSFP+ Optical Transceiver
hh3cevtPortSw-QSFP-PLUS-40GBASE-ER4L    OBJECT IDENTIFIER ::= { hh3cevtPortSwitchType 255 }  -- 40BASE-ER4L QSFP+ Optical Transceiver
hh3cevtPortSw-QSFP-PLUS-40GBASE-BIDI    OBJECT IDENTIFIER ::= { hh3cevtPortSwitchType 256 }  -- 40BASE-BIDI QSFP+ Optical Transceiver
hh3cevtPortSw-QSFP-PLUS-40GBASE-LR4L    OBJECT IDENTIFIER ::= { hh3cevtPortSwitchType 257 }  -- 40BASE-LR4L QSFP+ Optical Transceiver
hh3cevtPortSw-CFP2-100GBASE-eSR10       OBJECT IDENTIFIER ::= { hh3cevtPortSwitchType 258 }  -- 100GBASE-eSR10 CFP2 Optical Transceiver
hh3cevtPortSw-TUNABLE-SFP-PLUS-10GBASE-ZR-DWDM  OBJECT IDENTIFIER ::= { hh3cevtPortSwitchType 259 }  -- 10GBase-ZR Tunable SFP+ DWDM Optical Transceiver
hh3cevtPortSw-SFP28-25GBASE-SR          OBJECT IDENTIFIER ::= { hh3cevtPortSwitchType 260 }  -- 25GBASE-SR SFP28 Optical Transceiver
hh3cevtPortSw-SFP28-ACTIVE-OPTICAL-CABLE    OBJECT IDENTIFIER ::= { hh3cevtPortSwitchType 261 }  -- SFP28 AOC
hh3cevtPortSw-SFP28-STACK-CONNECTOR     OBJECT IDENTIFIER ::= { hh3cevtPortSwitchType 262 }  -- SFP28 STACK Transceiver
hh3cevtPortSw-2DOT5GBASE-T              OBJECT IDENTIFIER ::= { hh3cevtPortSwitchType 263 }  -- 2dot5G Base-T Port
hh3cevtPortSw-QSFP28-100GBASE-SWDM4     OBJECT IDENTIFIER ::= { hh3cevtPortSwitchType 264 }  -- 100GBASE-SWDM4 QSFP28 Optical Transceiver
hh3cevtPortSw-QSFP28-100GBASE-eSWDM4    OBJECT IDENTIFIER ::= { hh3cevtPortSwitchType 265 }  -- 100GBASE-eSWDM4 QSFP28 Optical Transceiver
hh3cevtPortSw-SFP-PLUS-10GBASE-T        OBJECT IDENTIFIER ::= { hh3cevtPortSwitchType 266 }  -- 10GBase-T SFP+ Transceiver
hh3cevtPortSw-QSFP28-100GBASE-eSR4       OBJECT IDENTIFIER ::= { hh3cevtPortSwitchType 267 }  -- 100BASE-eSR4 QSFP28 Optical Transceiver
hh3cevtPortSw-QSFP28-100GBASE-BIDI       OBJECT IDENTIFIER ::= { hh3cevtPortSwitchType 268 }  -- 100GBASE-BIDI QSFP28 Optical Transceiver
hh3cevtPortSw-QSFP28-100GBASE-WDM2       OBJECT IDENTIFIER ::= { hh3cevtPortSwitchType 269 }  -- 100GBASE-WDM2 QSFP28 Optical Transceiver
hh3cevtPortSw-SFP28-25GBASE-LR           OBJECT IDENTIFIER ::= { hh3cevtPortSwitchType 270 }  -- 25GBASE-LR SFP28 Optical Transceiver
hh3cevtPortSw-CFP2-100GBASE-ER4          OBJECT IDENTIFIER ::= { hh3cevtPortSwitchType 271 }  -- 100GBASE-ER4 CFP2 Optical Transceiver
hh3cevtPortSw-CFP2-DCO-200GBASE-ZR          OBJECT IDENTIFIER ::= { hh3cevtPortSwitchType 272 }  -- 200GBASE-ZR CFP2-DCO Optical Transceiver
hh3cevtPortSw-CFP2-100GBASE-ER4L          OBJECT IDENTIFIER ::= { hh3cevtPortSwitchType 273 }  -- 100GBASE-ER4L CFP2 Optical Transceiver
hh3cevtPortSw-SFP-16GFC-SW                OBJECT IDENTIFIER ::= { hh3cevtPortSwitchType 274 }  -- SFP 16G FC Optical Transceiver short wave
hh3cevtPortSw-SFP-16GFC-LW                OBJECT IDENTIFIER ::= { hh3cevtPortSwitchType 275 }  -- SFP 16G FC Optical Transceiver long wave
hh3cevtPortSw-SFP-32GFC-SW                OBJECT IDENTIFIER ::= { hh3cevtPortSwitchType 276 }  -- SFP 32G FC Optical Transceiver short wave
hh3cevtPortSw-SFP-32GFC-LW                OBJECT IDENTIFIER ::= { hh3cevtPortSwitchType 277 }  -- SFP 32G FC Optical Transceiver long wave
hh3cevtPortSw-XFP-10GBASE-PR-D3               OBJECT IDENTIFIER ::= { hh3cevtPortSwitchType 278 }  -- XFP 10GBase PR-D3 Optical Transceiver
hh3cevtPortSw-XFP-10GBASE-PRX-D3               OBJECT IDENTIFIER ::= { hh3cevtPortSwitchType 279 }  -- XFP 10GBase PRX-D3 Optical Transceiver
hh3cevtPortSw-5GBASE-T                    OBJECT IDENTIFIER ::= { hh3cevtPortSwitchType 280 }  -- 5G Base-T Port
hh3cevtPortSw-QSFP28-UNKNOWN              OBJECT IDENTIFIER ::= { hh3cevtPortSwitchType 281 }  -- Unknown QSFP28 Transceiver
hh3cevtPortSw-SFP28-UNKNOWN               OBJECT IDENTIFIER ::= { hh3cevtPortSwitchType 282 }  -- Unknown SFP28 Transceiver
hh3cevtPortSw-SFP28-NO-CONNECTOR          OBJECT IDENTIFIER ::= { hh3cevtPortSwitchType 283 }  -- SFP28 No Connector
hh3cevtPortSw-SFP-PLUS-9-8GCRPI-IR        OBJECT IDENTIFIER ::= { hh3cevtPortSwitchType 284 }  -- 9.8GCRPI-IR SFP+ Transceiver
hh3cevtPortSw-SFP-PLUS-9-8GCRPI-LR        OBJECT IDENTIFIER ::= { hh3cevtPortSwitchType 285 }  -- 9.8GCRPI-LR SFP+ Transceiver
hh3cevtPortSw-50GBase-F                   OBJECT IDENTIFIER ::= { hh3cevtPortSwitchType 286 }  -- 50G Ethernet port with QSFP28
hh3cevtPortSw-QSFP28-50GBASE-PAM4-LR       OBJECT IDENTIFIER ::= { hh3cevtPortSwitchType 287 }  -- 50GBASE-PAM4-LR QSFP28 Optical Transceiver
hh3cevtPortSw-10GBASE-BIDI-SFP             OBJECT IDENTIFIER ::= { hh3cevtPortSwitchType 288 }  -- 10GBASE  SFP+ BIDI Optical Transceiver

hh3cevtPortSw-10GBASE-BIDI-U-SFP-PLUS     OBJECT IDENTIFIER ::= { hh3cevtPortSwitchType 291 }  -- 10GBASE  SFP+ BIDI Up Optical Transceiver
hh3cevtPortSw-10GBASE-BIDI-D-SFP-PLUS     OBJECT IDENTIFIER ::= { hh3cevtPortSwitchType 292 }  -- 10GBASE  SFP+ BIDI Down Optical Transceiver
hh3cevtPortSw-QSFPDD-STACK-CONNECTOR      OBJECT IDENTIFIER ::= { hh3cevtPortSwitchType 293 }  -- QSFPDD-STACK-Transceiver
hh3cevtPortSw-QSFPDD-400GBASE-SR8         OBJECT IDENTIFIER ::= { hh3cevtPortSwitchType 294 }  -- 400GBASE-SR8  QSFP-DD Optical Transceiver
hh3cevtPortSw-QSFP28-100GBASE-ZR2         OBJECT IDENTIFIER ::= { hh3cevtPortSwitchType 295 }   -- 100GBASE-ZR2 QSFP28 Optical Transceiver
hh3cevtPortSw-QSFP28-50GBASE-ER           OBJECT IDENTIFIER ::= { hh3cevtPortSwitchType 296 }  -- 50GBASE ER QSFP28 Optical Transceiver Module
hh3cevtPortSw-SFP28-25GBASE-eLR           OBJECT IDENTIFIER ::= { hh3cevtPortSwitchType 297 }  -- 25GBASE-eLR SFP28 Optical Transceiver
hh3cevtPortSw-QSFP28-100GBASE-ER4-NO-FEC   OBJECT IDENTIFIER ::= { hh3cevtPortSwitchType 298 }  -- 100GBASE-ER4 QSFP28 Optical Transceiver Module
hh3cevtPortSw-QSFP28-100GBASE-ZR4         OBJECT IDENTIFIER ::= { hh3cevtPortSwitchType 299 }  -- 100GBASE-ZR4 QSFP28 Optical Transceiver Module
hh3cevtPortSw-QSFPDD-400GBASE-FR4         OBJECT IDENTIFIER ::= { hh3cevtPortSwitchType 300 }  -- 400GBASE-FR4 QSFP-DD Optical Transceiver
hh3cevtPortSw-QSFP56-200GBASE-FR4         OBJECT IDENTIFIER ::= { hh3cevtPortSwitchType 301 }  -- 200GBASE-FR4 QSFP-56 Optical Transceiver
hh3cevtPortSw-QSFP56-200GBASE-SR4         OBJECT IDENTIFIER ::= { hh3cevtPortSwitchType 302 }  -- 200GBASE-SR4 QSFP-56 Optical Transceiver
hh3cevtPortSw-QSFP56-200GBASE-AOC         OBJECT IDENTIFIER ::= { hh3cevtPortSwitchType 303 }  -- 200GBASE-AOC QSFP-56 Active Optical Cable
hh3cevtPortSw-DSFP-100GBASE-AOC           OBJECT IDENTIFIER ::= { hh3cevtPortSwitchType 304 }  -- 100GBASE-AOC DSFP Active Optical Cable
hh3cevtPortSw-SFP28-25GBASE-CSR           OBJECT IDENTIFIER ::= { hh3cevtPortSwitchType 305 }  -- 25GBASE-CSR SFP28 Optical Transceiver
hh3cevtPortSw-QSFPDD-UNKNOWN              OBJECT IDENTIFIER ::= { hh3cevtPortSwitchType 306 }  -- Unknown QSFPDD Transceiver
hh3cevtPortSw-QSFPDD-NO-CONNECTOR         OBJECT IDENTIFIER ::= { hh3cevtPortSwitchType 307 }  -- QSFPDD No Connector
hh3cevtPortSw-DSFP-UNKNOWN                OBJECT IDENTIFIER ::= { hh3cevtPortSwitchType 308 }  -- Unknown DSFP Transceiver
hh3cevtPortSw-DSFP-NO-CONNECTOR           OBJECT IDENTIFIER ::= { hh3cevtPortSwitchType 309 }  -- DSFP No Connector
hh3cevtPortSw-QSFPDD-400GBASE-ZR          OBJECT IDENTIFIER ::= { hh3cevtPortSwitchType 310 }  -- 400GBASE-ZR QSFP-DD Optical Transceiver
hh3cevtPortSw-QSFPDD-400GBASE-LR8         OBJECT IDENTIFIER ::= { hh3cevtPortSwitchType 311 }  -- 400GBASE-LR8 QSFP-DD Optical Transceiver
--
-- hh3cevtStack section:
--
hh3cevtStack     OBJECT IDENTIFIER ::= { hh3cEntityVendortypeObjects 11 }


END
