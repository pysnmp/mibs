ACOS-CGNV6-HTTP-ALG-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		cgnv6HttpAlgModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "cgnv6HttpAlgModule OID for ACOS"
				::=  {  acosSchema 419 }

httpAlg		 OBJECT IDENTIFIER ::= { cgnv6HttpAlgModule 1}

httpAlgStatsTable OBJECT-TYPE
	 SYNTAX SEQUENCE OF HttpAlgStatsEntry
	 MAX-ACCESS not-accessible
	 STATUS current
	 DESCRIPTION
	 "HTTP-ALG Statistics from object 'cgnv6.http-alg'"
	::= {httpAlg 1}

httpAlgStatsEntry OBJECT-TYPE
	SYNTAX HttpAlgStatsEntry
	MAX-ACCESS not-accessible
	STATUS current
	DESCRIPTION
		"The httpAlgStats stats entry"
	INDEX {
		httpAlgStatsSlotId
	}
	::= { httpAlgStatsTable 1 }

HttpAlgStatsEntry ::=
	SEQUENCE {
		httpAlgStatsSlotId Integer32,
		httpAlgStatsRequestProcessed	 CounterBasedGauge64,
		httpAlgStatsRequestInsertMsisdnPerformed	 CounterBasedGauge64,
		httpAlgStatsRequestInsertClientIpPerformed	 CounterBasedGauge64,
		httpAlgStatsRequestInsertMsisdnUnavailable	 CounterBasedGauge64,
		httpAlgStatsQueuedSessionTooMany	 CounterBasedGauge64,
		httpAlgStatsRadiusQuerySucceed	 CounterBasedGauge64,
		httpAlgStatsRadiusQueryFailed	 CounterBasedGauge64,
		httpAlgStatsRadiusRequstSent	 CounterBasedGauge64,
		httpAlgStatsRadiusRequstDropped	 CounterBasedGauge64,
		httpAlgStatsRadiusResponseReceived	 CounterBasedGauge64,
		httpAlgStatsRadiusResponseDropped	 CounterBasedGauge64,
		httpAlgStatsOutOfMemoryDropped	 CounterBasedGauge64,
		httpAlgStatsQueueLenExceedDropped	 CounterBasedGauge64,
		httpAlgStatsOutOfOrderDropped	 CounterBasedGauge64,
		httpAlgStatsBuffResent	 CounterBasedGauge64,
		httpAlgStatsBuffSpiltFailed	 CounterBasedGauge64,
		httpAlgStatsHeaderInsertionFailed	 CounterBasedGauge64,
		httpAlgStatsHeaderRemovalFailed	 CounterBasedGauge64,
		httpAlgStatsNoQueue	 CounterBasedGauge64
	}

httpAlgStatsSlotId OBJECT-TYPE
	 SYNTAX Integer32
	 MAX-ACCESS read-only
	 STATUS current
	 DESCRIPTION
		 ""
	::= { httpAlgStatsEntry 1 }

httpAlgStatsRequestProcessed OBJECT-TYPE
	 SYNTAX Integer32
	 MAX-ACCESS read-only
	 STATUS current
	 DESCRIPTION
		 "request-processed"
	::= { httpAlgStatsEntry 2 }

httpAlgStatsRequestInsertMsisdnPerformed OBJECT-TYPE
	 SYNTAX Integer32
	 MAX-ACCESS read-only
	 STATUS current
	 DESCRIPTION
		 "request-insert-msisdn-performed"
	::= { httpAlgStatsEntry 3 }

httpAlgStatsRequestInsertClientIpPerformed OBJECT-TYPE
	 SYNTAX Integer32
	 MAX-ACCESS read-only
	 STATUS current
	 DESCRIPTION
		 "request-insert-client-ip-performed"
	::= { httpAlgStatsEntry 4 }

httpAlgStatsRequestInsertMsisdnUnavailable OBJECT-TYPE
	 SYNTAX Integer32
	 MAX-ACCESS read-only
	 STATUS current
	 DESCRIPTION
		 "request-insert-msisdn-unavailable"
	::= { httpAlgStatsEntry 5 }

httpAlgStatsQueuedSessionTooMany OBJECT-TYPE
	 SYNTAX Integer32
	 MAX-ACCESS read-only
	 STATUS current
	 DESCRIPTION
		 "queued-session-too-many"
	::= { httpAlgStatsEntry 6 }

httpAlgStatsRadiusQuerySucceed OBJECT-TYPE
	 SYNTAX Integer32
	 MAX-ACCESS read-only
	 STATUS current
	 DESCRIPTION
		 "radius-query-succeed"
	::= { httpAlgStatsEntry 7 }

httpAlgStatsRadiusQueryFailed OBJECT-TYPE
	 SYNTAX Integer32
	 MAX-ACCESS read-only
	 STATUS current
	 DESCRIPTION
		 "radius-query-failed"
	::= { httpAlgStatsEntry 8 }

httpAlgStatsRadiusRequstSent OBJECT-TYPE
	 SYNTAX Integer32
	 MAX-ACCESS read-only
	 STATUS current
	 DESCRIPTION
		 "radius-requst-sent"
	::= { httpAlgStatsEntry 9 }

httpAlgStatsRadiusRequstDropped OBJECT-TYPE
	 SYNTAX Integer32
	 MAX-ACCESS read-only
	 STATUS current
	 DESCRIPTION
		 "radius-requst-dropped"
	::= { httpAlgStatsEntry 10 }

httpAlgStatsRadiusResponseReceived OBJECT-TYPE
	 SYNTAX Integer32
	 MAX-ACCESS read-only
	 STATUS current
	 DESCRIPTION
		 "radius-response-received"
	::= { httpAlgStatsEntry 11 }

httpAlgStatsRadiusResponseDropped OBJECT-TYPE
	 SYNTAX Integer32
	 MAX-ACCESS read-only
	 STATUS current
	 DESCRIPTION
		 "radius-response-dropped"
	::= { httpAlgStatsEntry 12 }

httpAlgStatsOutOfMemoryDropped OBJECT-TYPE
	 SYNTAX Integer32
	 MAX-ACCESS read-only
	 STATUS current
	 DESCRIPTION
		 "out-of-memory-dropped"
	::= { httpAlgStatsEntry 13 }

httpAlgStatsQueueLenExceedDropped OBJECT-TYPE
	 SYNTAX Integer32
	 MAX-ACCESS read-only
	 STATUS current
	 DESCRIPTION
		 "queue-len-exceed-dropped"
	::= { httpAlgStatsEntry 14 }

httpAlgStatsOutOfOrderDropped OBJECT-TYPE
	 SYNTAX Integer32
	 MAX-ACCESS read-only
	 STATUS current
	 DESCRIPTION
		 "out-of-order-dropped"
	::= { httpAlgStatsEntry 15 }

httpAlgStatsBuffResent OBJECT-TYPE
	 SYNTAX Integer32
	 MAX-ACCESS read-only
	 STATUS current
	 DESCRIPTION
		 "buff-resent"
	::= { httpAlgStatsEntry 16 }

httpAlgStatsBuffSpiltFailed OBJECT-TYPE
	 SYNTAX Integer32
	 MAX-ACCESS read-only
	 STATUS current
	 DESCRIPTION
		 "buff-spilt-failed"
	::= { httpAlgStatsEntry 17 }

httpAlgStatsHeaderInsertionFailed OBJECT-TYPE
	 SYNTAX Integer32
	 MAX-ACCESS read-only
	 STATUS current
	 DESCRIPTION
		 "header-insertion-failed"
	::= { httpAlgStatsEntry 18 }

httpAlgStatsHeaderRemovalFailed OBJECT-TYPE
	 SYNTAX Integer32
	 MAX-ACCESS read-only
	 STATUS current
	 DESCRIPTION
		 "header-removal-failed"
	::= { httpAlgStatsEntry 19 }

httpAlgStatsNoQueue OBJECT-TYPE
	 SYNTAX Integer32
	 MAX-ACCESS read-only
	 STATUS current
	 DESCRIPTION
		 "no-queue"
	::= { httpAlgStatsEntry 20 }

END
