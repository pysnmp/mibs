ACOS-WEBCATEGORY-LICENSE-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		webCategoryLicenseModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "webCategoryLicenseModule OID for ACOS"
				::=  {  acosSchema 278 }

license		 OBJECT IDENTIFIER ::= { webCategoryLicenseModule 1}

licenseOperTable OBJECT-TYPE
	 SYNTAX SEQUENCE OF LicenseOperEntry
	 MAX-ACCESS not-accessible
	 STATUS current
	 DESCRIPTION
		 "License information from object 'web-category.license'"
	::= {license 2}

licenseOperEntry OBJECT-TYPE
	SYNTAX LicenseOperEntry
	MAX-ACCESS not-accessible
	STATUS current
	DESCRIPTION
		"The licenseOper entry"
	INDEX {
		licenseOperSlotId
	}
	::= { licenseOperTable 1 }

LicenseOperEntry ::=
	SEQUENCE {
		licenseOperSlotId Integer32,
		licenseOperModuleStatus	 DisplayString,
		licenseOperLicenseStatus	 DisplayString,
		licenseOperLicenseType	 DisplayString,
		licenseOperLicenseExpiry	 DisplayString,
		licenseOperRemainingPeriod	 DisplayString,
		licenseOperIsGrace	 DisplayString,
		licenseOperGracePeriod	 DisplayString,
		licenseOperSerialNumber	 DisplayString
	}

licenseOperSlotId OBJECT-TYPE
	 SYNTAX Integer32
	 MAX-ACCESS read-only
	 STATUS current
	 DESCRIPTION
		 ""
	::= { licenseOperEntry 1 }

licenseOperModuleStatus OBJECT-TYPE
	 SYNTAX DisplayString
	 MAX-ACCESS read-only
	 STATUS current
	 DESCRIPTION
		 "module-status"
	::= { licenseOperEntry 2 }

licenseOperLicenseStatus OBJECT-TYPE
	 SYNTAX DisplayString
	 MAX-ACCESS read-only
	 STATUS current
	 DESCRIPTION
		 "license-status"
	::= { licenseOperEntry 3 }

licenseOperLicenseType OBJECT-TYPE
	 SYNTAX DisplayString
	 MAX-ACCESS read-only
	 STATUS current
	 DESCRIPTION
		 "license-type"
	::= { licenseOperEntry 4 }

licenseOperLicenseExpiry OBJECT-TYPE
	 SYNTAX DisplayString
	 MAX-ACCESS read-only
	 STATUS current
	 DESCRIPTION
		 "license-expiry"
	::= { licenseOperEntry 5 }

licenseOperRemainingPeriod OBJECT-TYPE
	 SYNTAX DisplayString
	 MAX-ACCESS read-only
	 STATUS current
	 DESCRIPTION
		 "remaining-period"
	::= { licenseOperEntry 6 }

licenseOperIsGrace OBJECT-TYPE
	 SYNTAX DisplayString
	 MAX-ACCESS read-only
	 STATUS current
	 DESCRIPTION
		 "is-grace"
	::= { licenseOperEntry 7 }

licenseOperGracePeriod OBJECT-TYPE
	 SYNTAX DisplayString
	 MAX-ACCESS read-only
	 STATUS current
	 DESCRIPTION
		 "grace-period"
	::= { licenseOperEntry 8 }

licenseOperSerialNumber OBJECT-TYPE
	 SYNTAX DisplayString
	 MAX-ACCESS read-only
	 STATUS current
	 DESCRIPTION
		 "serial-number"
	::= { licenseOperEntry 9 }

END
