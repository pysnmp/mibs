LOWPAN-MIB DEFINITIONS ::= BEGIN

   IMPORTS
       MODULE-IDENTITY, OBJECT-TYPE, Unsigned32, Counter32, mib-2
           FROM SNMPv2-SMI                                 -- RFC 2578
       OBJECT-GROUP, MODULE-COMPLIANCE
           FROM SNMPv2-CONF                                -- RFC 2580
       ifIndex FROM IF-MIB;                                -- RFC 2863

   lowpanMIB    MODULE-IDENTITY
       LAST-UPDATED    "201410100000Z"  -- October 10, 2014
       ORGANIZATION
           "IETF IPv6 over Networks of Resource-constrained Nodes
            Working Group"
       CONTACT-INFO
           "WG Email: 6lo@ietf.org
            WG Web:   http://tools.ietf.org/wg/6lo/

            Juergen Schoenwaelder
            Jacobs University Bremen
            Email: j.schoenwaelder@jacobs-university.de

            Anuj Sehgal
            Jacobs University Bremen
            Email: s.anuj@jacobs-university.de

            Tina Tsou
            Huawei Technologies
            Email: tina.tsou.zouting@huawei.com
            Cathy Zhou
            Huawei Technologies
            Email: cathyzhou@huawei.com"
       DESCRIPTION
           "The MIB module for monitoring nodes implementing the IPv6
            over Low-Power Wireless Personal Area Networks (6LoWPAN)
            protocol.

            Copyright (c) 2014 IETF Trust and the persons identified as
            authors of the code.  All rights reserved.

            Redistribution and use in source and binary forms, with or
            without modification, is permitted pursuant to, and subject
            to the license terms contained in, the Simplified BSD
            License set forth in Section 4.c of the IETF Trust's
            Legal Provisions Relating to IETF Documents
            (http://trustee.ietf.org/license-info)."

       REVISION "201410100000Z" -- October 10, 2014
       DESCRIPTION
           "Initial version, published as RFC 7388."

       ::= { mib-2 226 }

   -- object definitions

   lowpanNotifications     OBJECT IDENTIFIER ::= { lowpanMIB 0 }
   lowpanObjects           OBJECT IDENTIFIER ::= { lowpanMIB 1 }
   lowpanConformance       OBJECT IDENTIFIER ::= { lowpanMIB 2 }

   lowpanStats             OBJECT IDENTIFIER ::= { lowpanObjects 1 }

   lowpanReasmTimeout OBJECT-TYPE
       SYNTAX      Unsigned32
       UNITS       "seconds"
       MAX-ACCESS  read-only
       STATUS      current
       DESCRIPTION
           "The maximum number of seconds that received fragments are
            held while they are awaiting reassembly at this entity."
       ::= { lowpanStats 1 }

   lowpanInReceives OBJECT-TYPE
       SYNTAX      Counter32
       MAX-ACCESS  read-only
       STATUS      current
       DESCRIPTION
           "The total number of 6LoWPAN datagrams received, including
            those received in error."
       ::= { lowpanStats 2 }

   lowpanInHdrErrors OBJECT-TYPE
       SYNTAX      Counter32
       MAX-ACCESS  read-only
       STATUS      current
       DESCRIPTION
           "The number of received 6LoWPAN datagrams discarded due to
            errors in their headers, including unknown dispatch values."
       ::= { lowpanStats 3 }

   lowpanInMeshReceives OBJECT-TYPE
       SYNTAX      Counter32
       MAX-ACCESS  read-only
       STATUS      current
       DESCRIPTION
           "The number of received 6LoWPAN datagrams with a MESH
            header."
       ::= { lowpanStats 4 }

   lowpanInMeshForwds OBJECT-TYPE
       SYNTAX      Counter32
       MAX-ACCESS  read-only
       STATUS      current
       DESCRIPTION
           "The number of received 6LoWPAN datagrams requiring mesh
            forwarding."
       ::= { lowpanStats 5 }

   lowpanInMeshDelivers OBJECT-TYPE
       SYNTAX      Counter32
       MAX-ACCESS  read-only
       STATUS      current
       DESCRIPTION
           "The number of received 6LoWPAN datagrams with a MESH header
            delivered to the local system."
       ::= { lowpanStats 6 }

   lowpanInReasmReqds OBJECT-TYPE
       SYNTAX      Counter32
       MAX-ACCESS  read-only
       STATUS      current
       DESCRIPTION
           "The number of received 6LoWPAN fragments that needed to
            be reassembled.  This includes both FRAG1 and FRAGN 6LoWPAN
            datagrams."
       ::= { lowpanStats 7 }

   lowpanInReasmFails OBJECT-TYPE
       SYNTAX      Counter32
       MAX-ACCESS  read-only
       STATUS      current
       DESCRIPTION
           "The number of failures detected by the re-assembly
            algorithm (e.g., timeouts).  Note that this is not
            necessarily a count of discarded 6LoWPAN fragments
            since implementations can lose track of the number
            of fragments by combining them as received."
       ::= { lowpanStats 8 }

   lowpanInReasmOKs OBJECT-TYPE
       SYNTAX      Counter32
       MAX-ACCESS  read-only
       STATUS      current
       DESCRIPTION
           "The number of IPv6 packets successfully reassembled."
       ::= { lowpanStats 9 }

   lowpanInCompReqds OBJECT-TYPE
       SYNTAX      Counter32
       MAX-ACCESS  read-only
       STATUS      current
       DESCRIPTION
           "The number of 6LoWPAN datagrams requiring header
            decompression."
       ::= { lowpanStats 10 }

   lowpanInCompFails OBJECT-TYPE
       SYNTAX      Counter32
       MAX-ACCESS  read-only
       STATUS      current
       DESCRIPTION
           "The number of 6LoWPAN datagrams where header decompression
            failed (e.g., because the necessary context information was
            not available)."
       ::= { lowpanStats 11 }
   lowpanInCompOKs OBJECT-TYPE
       SYNTAX      Counter32
       MAX-ACCESS  read-only
       STATUS      current
       DESCRIPTION
           "The number of 6LoWPAN datagrams where header decompression
            was successful."
       ::= { lowpanStats 12 }

   lowpanInDiscards OBJECT-TYPE
       SYNTAX      Counter32
       MAX-ACCESS  read-only
       STATUS      current
       DESCRIPTION
           "The number of received 6LoWPAN datagrams that were
            discarded (e.g., for lack of buffer space) even though no
            problems were encountered to prevent their continued
            processing.  Note that this counter does not include any
            datagrams discarded due to a reassembly failure or a
            compression failure."
       ::= { lowpanStats 13 }

   lowpanInDelivers OBJECT-TYPE
       SYNTAX      Counter32
       MAX-ACCESS  read-only
       STATUS      current
       DESCRIPTION
           "The total number of IPv6 packets successfully delivered
            to the IPv6 layer."
       ::= { lowpanStats 14 }

   lowpanOutRequests OBJECT-TYPE
       SYNTAX      Counter32
       MAX-ACCESS  read-only
       STATUS      current
       DESCRIPTION
           "The total number of IPv6 packets supplied by the IPv6
            layer."
       ::= { lowpanStats 15 }

   lowpanOutCompReqds OBJECT-TYPE
       SYNTAX      Counter32
       MAX-ACCESS  read-only
       STATUS      current
       DESCRIPTION
           "The total number of IPv6 packets for which header
            compression was attempted."
       ::= { lowpanStats 16 }
   lowpanOutCompFails OBJECT-TYPE
       SYNTAX      Counter32
       MAX-ACCESS  read-only
       STATUS      current
       DESCRIPTION
           "The total number of IPv6 packets for which header
            compression failed."
       ::= { lowpanStats 17 }

   lowpanOutCompOKs OBJECT-TYPE
       SYNTAX      Counter32
       MAX-ACCESS  read-only
       STATUS      current
       DESCRIPTION
           "The total number of IPv6 packets for which header
            compression was successful."
       ::= { lowpanStats 18 }

   lowpanOutFragReqds OBJECT-TYPE
       SYNTAX      Counter32
       MAX-ACCESS  read-only
       STATUS      current
       DESCRIPTION
           "The number of IPv6 packets that required fragmentation
            in order to be transmitted."
       ::= { lowpanStats 19 }

   lowpanOutFragFails OBJECT-TYPE
       SYNTAX      Counter32
       MAX-ACCESS  read-only
       STATUS      current
       DESCRIPTION
           "The number of IPv6 packets that have been discarded because
            fragmentation failed."
       ::= { lowpanStats 20 }

   lowpanOutFragOKs OBJECT-TYPE
       SYNTAX      Counter32
       MAX-ACCESS  read-only
       STATUS      current
       DESCRIPTION
           "The number of IPv6 packets that have been successfully
            fragmented."
       ::= { lowpanStats 21 }

   lowpanOutFragCreates OBJECT-TYPE
       SYNTAX      Counter32
       MAX-ACCESS  read-only
       STATUS      current
       DESCRIPTION
           "The number of 6LoWPAN fragments that have been
            generated as a result of fragmentation.  This includes
            both FRAG1 and FRAGN 6LoWPAN datagrams."
       ::= { lowpanStats 22 }

   lowpanOutMeshHopLimitExceeds OBJECT-TYPE
       SYNTAX      Counter32
       MAX-ACCESS  read-only
       STATUS      current
       DESCRIPTION
           "The number of 6LoWPAN datagrams with a MESH header that
            were dropped because the hop limit was exceeded."
       ::= { lowpanStats 23 }

   lowpanOutMeshNoRoutes OBJECT-TYPE
       SYNTAX      Counter32
       MAX-ACCESS  read-only
       STATUS      current
       DESCRIPTION
           "The number of 6LoWPAN datagrams with a MESH header that
            were dropped because there was no forwarding information
            available."
       ::= { lowpanStats 24 }

   lowpanOutMeshRequests OBJECT-TYPE
       SYNTAX      Counter32
       MAX-ACCESS  read-only
       STATUS      current
       DESCRIPTION
           "The number of 6LoWPAN datagrams requiring MESH header
            encapsulation."
       ::= { lowpanStats 25 }

   lowpanOutMeshForwds OBJECT-TYPE
       SYNTAX      Counter32
       MAX-ACCESS  read-only
       STATUS      current
       DESCRIPTION
           "The number of 6LoWPAN datagrams with a MESH header for
            which suitable forwarding information was available."
       ::= { lowpanStats 26 }

   lowpanOutMeshTransmits OBJECT-TYPE
       SYNTAX      Counter32
       MAX-ACCESS  read-only
       STATUS      current
       DESCRIPTION
           "The number of 6LoWPAN datagrams with a MESH header
            created."
       ::= { lowpanStats 27 }

   lowpanOutDiscards OBJECT-TYPE
       SYNTAX      Counter32
       MAX-ACCESS  read-only
       STATUS      current
       DESCRIPTION
           "The number of IPv6 packets that were discarded (e.g.,
            for lack of buffer space) even though no problem was
            encountered to prevent their transmission to their
            destination."
       ::= { lowpanStats 28 }

   lowpanOutTransmits OBJECT-TYPE
       SYNTAX      Counter32
       MAX-ACCESS  read-only
       STATUS      current
       DESCRIPTION
           "The total number of 6LoWPAN datagram that this entity
            supplied to the lower layers for transmission."
       ::= { lowpanStats 29 }

   lowpanIfStatsTable OBJECT-TYPE
       SYNTAX      SEQUENCE OF LowpanIfStatsEntry
       MAX-ACCESS  not-accessible
       STATUS      current
       DESCRIPTION
           "A table providing per-interface statistics."
       ::= { lowpanObjects 2 }

   lowpanIfStatsEntry OBJECT-TYPE
       SYNTAX      LowpanIfStatsEntry
       MAX-ACCESS  not-accessible
       STATUS      current
       DESCRIPTION
           "An entry providing statistics for a specific interface."
       INDEX       { ifIndex }
       ::= { lowpanIfStatsTable 1 }

   LowpanIfStatsEntry ::= SEQUENCE {
       lowpanIfReasmTimeout           Unsigned32,
       lowpanIfInReceives             Counter32,
       lowpanIfInHdrErrors            Counter32,
       lowpanIfInMeshReceives         Counter32,
       lowpanIfInMeshForwds           Counter32,
       lowpanIfInMeshDelivers         Counter32,
       lowpanIfInReasmReqds           Counter32,
       lowpanIfInReasmFails           Counter32,
       lowpanIfInReasmOKs             Counter32,
       lowpanIfInCompReqds            Counter32,
       lowpanIfInCompFails            Counter32,
       lowpanIfInCompOKs              Counter32,
       lowpanIfInDiscards             Counter32,
       lowpanIfInDelivers             Counter32,
       lowpanIfOutRequests            Counter32,
       lowpanIfOutCompReqds           Counter32,
       lowpanIfOutCompFails           Counter32,
       lowpanIfOutCompOKs             Counter32,
       lowpanIfOutFragReqds           Counter32,
       lowpanIfOutFragFails           Counter32,
       lowpanIfOutFragOKs             Counter32,
       lowpanIfOutFragCreates         Counter32,
       lowpanIfOutMeshHopLimitExceeds Counter32,
       lowpanIfOutMeshNoRoutes        Counter32,
       lowpanIfOutMeshRequests        Counter32,
       lowpanIfOutMeshForwds          Counter32,
       lowpanIfOutMeshTransmits       Counter32,
       lowpanIfOutDiscards            Counter32,
       lowpanIfOutTransmits           Counter32
   }

   lowpanIfReasmTimeout OBJECT-TYPE
       SYNTAX      Unsigned32
       UNITS       "seconds"
       MAX-ACCESS  read-only
       STATUS      current
       DESCRIPTION
           "The maximum number of seconds that received fragments are
            held while they are awaiting reassembly at this interface."
       ::= { lowpanIfStatsEntry 1 }

   lowpanIfInReceives OBJECT-TYPE
       SYNTAX      Counter32
       MAX-ACCESS  read-only
       STATUS      current
       DESCRIPTION
           "The total number of 6LoWPAN datagrams received on this
            interface, including those received in error."
       ::= { lowpanIfStatsEntry 2 }

   lowpanIfInHdrErrors OBJECT-TYPE
       SYNTAX      Counter32
       MAX-ACCESS  read-only
       STATUS      current
       DESCRIPTION
           "The number of 6LoWPAN datagrams received on this
            interface that were discarded due to errors in
            their headers, including unknown dispatch values."
       ::= { lowpanIfStatsEntry 3 }

   lowpanIfInMeshReceives OBJECT-TYPE
       SYNTAX      Counter32
       MAX-ACCESS  read-only
       STATUS      current
       DESCRIPTION
           "The number of 6LoWPAN datagrams received on this
            interface with a MESH header."
       ::= { lowpanIfStatsEntry 4 }

   lowpanIfInMeshForwds OBJECT-TYPE
       SYNTAX      Counter32
       MAX-ACCESS  read-only
       STATUS      current
       DESCRIPTION
           "The number of 6LoWPAN datagrams received on this
            interface requiring mesh forwarding."
       ::= { lowpanIfStatsEntry 5 }

   lowpanIfInMeshDelivers OBJECT-TYPE
       SYNTAX      Counter32
       MAX-ACCESS  read-only
       STATUS      current
       DESCRIPTION
           "The number of 6LoWPAN datagrams received on this
            interface with a MESH header delivered to the local
            system."
       ::= { lowpanIfStatsEntry 6 }

   lowpanIfInReasmReqds OBJECT-TYPE
       SYNTAX      Counter32
       MAX-ACCESS  read-only
       STATUS      current
       DESCRIPTION
           "The number of 6LoWPAN fragments received on this
            interface that needed to be reassembled.  This
            includes both FRAG1 and FRAGN 6LoWPAN datagrams."
       ::= { lowpanIfStatsEntry 7 }

   lowpanIfInReasmFails OBJECT-TYPE
       SYNTAX      Counter32
       MAX-ACCESS  read-only
       STATUS      current
       DESCRIPTION
           "The number of failures detected by the reassembly
            algorithm (e.g., timeouts) for datagrams received
            on this interface.  Note that this is not necessarily
            a count of discarded 6LoWPAN fragments since
            implementations can lose track of the number
            of fragments by combining them as received."
       ::= { lowpanIfStatsEntry 8 }

   lowpanIfInReasmOKs OBJECT-TYPE
       SYNTAX      Counter32
       MAX-ACCESS  read-only
       STATUS      current
       DESCRIPTION
           "The number of IPv6 packets successfully reassembled
            from fragments received on this interface."
       ::= { lowpanIfStatsEntry 9 }

   lowpanIfInCompReqds OBJECT-TYPE
       SYNTAX      Counter32
       MAX-ACCESS  read-only
       STATUS      current
       DESCRIPTION
           "The number of 6LoWPAN datagrams received on this
            interface requiring header decompression."
       ::= { lowpanIfStatsEntry 10 }

   lowpanIfInCompFails OBJECT-TYPE
       SYNTAX      Counter32
       MAX-ACCESS  read-only
       STATUS      current
       DESCRIPTION
           "The number of 6LoWPAN datagrams received on this
            interface where header decompression failed (e.g.,
            because the necessary context information was
            not available)."
       ::= { lowpanIfStatsEntry 11 }

   lowpanIfInCompOKs OBJECT-TYPE
       SYNTAX      Counter32
       MAX-ACCESS  read-only
       STATUS      current
       DESCRIPTION
           "The number of 6LoWPAN datagrams received on this
            interface where header decompression was successful."
       ::= { lowpanIfStatsEntry 12 }
   lowpanIfInDiscards OBJECT-TYPE
       SYNTAX      Counter32
       MAX-ACCESS  read-only
       STATUS      current
       DESCRIPTION
           "The number of 6LoWPAN datagrams received on this
            interface that were discarded (e.g., for lack of buffer
            space) even though no problems were encountered to
            prevent their continued processing.  Note that this
            counter does not include any datagrams discarded due
            to a reassembly failure or a compression failure."
       ::= { lowpanIfStatsEntry 13 }

   lowpanIfInDelivers OBJECT-TYPE
       SYNTAX      Counter32
       MAX-ACCESS  read-only
       STATUS      current
       DESCRIPTION
           "The total number of IPv6 packets received on this
            interface that were successfully delivered to the
            IPv6 layer."
       ::= { lowpanIfStatsEntry 14 }

   lowpanIfOutRequests OBJECT-TYPE
       SYNTAX      Counter32
       MAX-ACCESS  read-only
       STATUS      current
       DESCRIPTION
           "The total number of IPv6 packets supplied by the IPv6
            layer to be sent over this interface."
       ::= { lowpanIfStatsEntry 15 }

   lowpanIfOutCompReqds OBJECT-TYPE
       SYNTAX      Counter32
       MAX-ACCESS  read-only
       STATUS      current
       DESCRIPTION
           "The total number of IPv6 packets to be sent over
            this interface for which header compression was
            attempted."
       ::= { lowpanIfStatsEntry 16 }

   lowpanIfOutCompFails OBJECT-TYPE
       SYNTAX      Counter32
       MAX-ACCESS  read-only
       STATUS      current
       DESCRIPTION
           "The total number of IPv6 packets to be sent over
            this interface for which header compression failed."
       ::= { lowpanIfStatsEntry 17 }

   lowpanIfOutCompOKs OBJECT-TYPE
       SYNTAX      Counter32
       MAX-ACCESS  read-only
       STATUS      current
       DESCRIPTION
           "The total number of IPv6 packets to be sent over
            this interface for which header compression was
            successful."
       ::= { lowpanIfStatsEntry 18 }

   lowpanIfOutFragReqds OBJECT-TYPE
       SYNTAX      Counter32
       MAX-ACCESS  read-only
       STATUS      current
       DESCRIPTION
           "The number of IPv6 packets to be sent over this
            interface that required fragmentation in order
            to be transmitted."
       ::= { lowpanIfStatsEntry 19 }

   lowpanIfOutFragFails OBJECT-TYPE
       SYNTAX      Counter32
       MAX-ACCESS  read-only
       STATUS      current
       DESCRIPTION
           "The number of IPv6 packets to be sent over this
            interface that have been discarded because
            fragmentation failed."
       ::= { lowpanIfStatsEntry 20 }

   lowpanIfOutFragOKs OBJECT-TYPE
       SYNTAX      Counter32
       MAX-ACCESS  read-only
       STATUS      current
       DESCRIPTION
           "The number of IPv6 packets to be sent over this
            interface that have been successfully fragmented."
       ::= { lowpanIfStatsEntry 21 }

   lowpanIfOutFragCreates OBJECT-TYPE
       SYNTAX      Counter32
       MAX-ACCESS  read-only
       STATUS      current
       DESCRIPTION
           "The number of 6LoWPAN fragments that have been
            generated on this interface as a result of
            fragmentation.  This includes both FRAG1 and FRAGN
            6LoWPAN datagrams."
       ::= { lowpanIfStatsEntry 22 }

   lowpanIfOutMeshHopLimitExceeds OBJECT-TYPE
       SYNTAX      Counter32
       MAX-ACCESS  read-only
       STATUS      current
       DESCRIPTION
           "The number of 6LoWPAN datagrams to be sent on this
            interface with a MESH header that were dropped
            because the hop limit was exceeded."
       ::= { lowpanIfStatsEntry 23 }

   lowpanIfOutMeshNoRoutes OBJECT-TYPE
       SYNTAX      Counter32
       MAX-ACCESS  read-only
       STATUS      current
       DESCRIPTION
           "The number of 6LoWPAN datagrams to be sent on this
            interface with a MESH header that were dropped
            because there was no forwarding information available."
       ::= { lowpanIfStatsEntry 24 }

   lowpanIfOutMeshRequests OBJECT-TYPE
       SYNTAX      Counter32
       MAX-ACCESS  read-only
       STATUS      current
       DESCRIPTION
           "The number of 6LoWPAN datagrams to be sent on this
            interface requiring MESH header encapsulation."
       ::= { lowpanIfStatsEntry 25 }

   lowpanIfOutMeshForwds OBJECT-TYPE
       SYNTAX      Counter32
       MAX-ACCESS  read-only
       STATUS      current
       DESCRIPTION
           "The number of 6LoWPAN datagrams to be sent on this
            interface with a MESH header for which suitable
            forwarding information was available."
       ::= { lowpanIfStatsEntry 26 }
   lowpanIfOutMeshTransmits OBJECT-TYPE
       SYNTAX      Counter32
       MAX-ACCESS  read-only
       STATUS      current
       DESCRIPTION
           "The number of 6LoWPAN datagrams to be sent on this
            interface with a MESH header created."
       ::= { lowpanIfStatsEntry 27 }

   lowpanIfOutDiscards OBJECT-TYPE
       SYNTAX      Counter32
       MAX-ACCESS  read-only
       STATUS      current
       DESCRIPTION
           "The number of IPv6 packets to be sent over this
            interface that were discarded (e.g., for lack of buffer
            space) even though no problem was encountered to
            prevent their transmission to their destination."
       ::= { lowpanIfStatsEntry 28 }

   lowpanIfOutTransmits OBJECT-TYPE
       SYNTAX      Counter32
       MAX-ACCESS  read-only
       STATUS      current
       DESCRIPTION
           "The total number of 6LoWPAN datagrams to be sent on
            this interface that this entity supplied to the lower
            layers for transmission."
       ::= { lowpanIfStatsEntry 29 }

   -- conformance definitions

   lowpanGroups      OBJECT IDENTIFIER ::= { lowpanConformance 1 }
   lowpanCompliances OBJECT IDENTIFIER ::= { lowpanConformance 2 }

   lowpanCompliance MODULE-COMPLIANCE
       STATUS      current
       DESCRIPTION
           "Compliance statement for systems that implement 6LoWPAN."
       MODULE      -- this module
       MANDATORY-GROUPS {
           lowpanStatsGroup
       }
       GROUP       lowpanStatsMeshGroup
       DESCRIPTION
         "This group is mandatory for implementations that process
          or forward 6LoWPAN datagrams with a MESH header."
       GROUP       lowpanIfStatsGroup
       DESCRIPTION
         "This group is mandatory for implementations that expose
          per-interface statistics."
       GROUP       lowpanIfStatsMeshGroup
       DESCRIPTION
         "This group is mandatory for implementations that expose
          per-interface statistics and that process or forward
          6LoWPAN datagrams with a MESH header."
       ::= { lowpanCompliances 1 }

   lowpanStatsGroup OBJECT-GROUP
       OBJECTS {
           lowpanReasmTimeout,
           lowpanInReceives,
           lowpanInHdrErrors,
           lowpanInMeshReceives,
           lowpanInReasmReqds,
           lowpanInReasmFails,
           lowpanInReasmOKs,
           lowpanInCompReqds,
           lowpanInCompFails,
           lowpanInCompOKs,
           lowpanInDiscards,
           lowpanInDelivers,
           lowpanOutRequests,
           lowpanOutCompReqds,
           lowpanOutCompFails,
           lowpanOutCompOKs,
           lowpanOutFragReqds,
           lowpanOutFragFails,
           lowpanOutFragOKs,
           lowpanOutFragCreates,
           lowpanOutDiscards,
           lowpanOutTransmits
       }
       STATUS      current
       DESCRIPTION
           "A collection of objects providing information and
            statistics about the processing of 6LoWPAN datagrams,
            excluding counters covering the processing of datagrams
            with a MESH header."
       ::= { lowpanGroups 1 }

   lowpanStatsMeshGroup OBJECT-GROUP
       OBJECTS {
           lowpanInMeshForwds,
           lowpanInMeshDelivers,
           lowpanOutMeshHopLimitExceeds,
           lowpanOutMeshNoRoutes,
           lowpanOutMeshRequests,
           lowpanOutMeshForwds,
           lowpanOutMeshTransmits
       }
       STATUS      current
       DESCRIPTION
           "A collection of objects providing information and
            statistics about the processing of 6LoWPAN datagrams
            with a MESH header."
       ::= { lowpanGroups 2 }

   lowpanIfStatsGroup OBJECT-GROUP
       OBJECTS {
           lowpanIfReasmTimeout,
           lowpanIfInReceives,
           lowpanIfInHdrErrors,
           lowpanIfInMeshReceives,
           lowpanIfInReasmReqds,
           lowpanIfInReasmFails,
           lowpanIfInReasmOKs,
           lowpanIfInCompReqds,
           lowpanIfInCompFails,
           lowpanIfInCompOKs,
           lowpanIfInDiscards,
           lowpanIfInDelivers,
           lowpanIfOutRequests,
           lowpanIfOutCompReqds,
           lowpanIfOutCompFails,
           lowpanIfOutCompOKs,
           lowpanIfOutFragReqds,
           lowpanIfOutFragFails,
           lowpanIfOutFragOKs,
           lowpanIfOutFragCreates,
           lowpanIfOutDiscards,
           lowpanIfOutTransmits
       }
       STATUS      current
       DESCRIPTION
           "A collection of objects providing per-interface
            information and statistics about the processing
            of 6LoWPAN datagrams, excluding counters covering
            the processing of datagrams with a MESH header."
       ::= { lowpanGroups 3 }
   lowpanIfStatsMeshGroup OBJECT-GROUP
       OBJECTS {
           lowpanIfInMeshForwds,
           lowpanIfInMeshDelivers,
           lowpanIfOutMeshHopLimitExceeds,
           lowpanIfOutMeshNoRoutes,
           lowpanIfOutMeshRequests,
           lowpanIfOutMeshForwds,
           lowpanIfOutMeshTransmits
       }
       STATUS      current
       DESCRIPTION
           "A collection of objects providing per-interface
            information and statistics about the processing
            of 6LoWPAN datagrams with a MESH header."
       ::= { lowpanGroups 4 }

   END
