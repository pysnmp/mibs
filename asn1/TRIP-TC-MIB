TRIP-TC-MIB DEFINITIONS ::= BEGIN

IMPORTS
    MODULE-IDENTITY,
    Unsigned32,
    Integer32,
    mib-2
        FROM SNMPv2-SMI            -- [RFC2578]

    TEXTUAL-CONVENTION
        FROM SNMPv2-TC;            -- [RFC2579]

tripTC MODULE-IDENTITY
    LAST-UPDATED   "200409020000Z" -- Sep 02, 2004
    ORGANIZATION   "IETF IPTel Working Group.
        Mailing list: iptel@lists.bell-labs.com"
    CONTACT-INFO
       "Co-editor  David Zinman
        postal:    265 Ridley Blvd.
                   Toronto ON, M5M 4N8
                   Canada
        email:     dzinman@rogers.com
        phone:     +1 416 433 4298

        Co-editor: David Walker
                   Sedna Wireless Inc.
        postal:    495 March Road, Suite 500
                   Ottawa, ON K2K 3G1
                   Canada
        email:     david.walker@sedna-wireless.com
        phone:     +1 613 878 8142

        Co-editor   Jianping Jiang
                    Syndesis Limited
        postal:     30 Fulton Way
                    Richmond Hill, ON L4B 1J5
                    Canada

        email:      jjiang@syndesis.com
        phone:      +1 905 886-7818 x2515
        "
    DESCRIPTION
        "Initial version of TRIP (Telephony Routing Over IP)
        MIB Textual Conventions module used by other
        TRIP-related MIB Modules.

        Copyright (C) The Internet Society (2004). This version of
        this MIB module is part of RFC 3872, see the RFC itself
        for full legal notices."
    REVISION      "200409020000Z" -- Sep 02, 2004
    DESCRIPTION
        "The initial version, Published as RFC 3872."
    ::= { mib-2 115 }

--
-- Textual Conventions
--

TripItad ::= TEXTUAL-CONVENTION
    STATUS current
    DESCRIPTION
       "The values for identifying the IP Telephony
       Administrative Domain (ITAD)."
    SYNTAX Unsigned32 (0..4294967295)

TripId ::= TEXTUAL-CONVENTION
    STATUS current
    DESCRIPTION
       "The TRIP Identifier uniquely identifies a LS within its
       ITAD. It is a 4 octet unsigned integer that may, but not
       necessarily, represent the IPv4 address of a Location
       Server.  Where bytes 1-4 of the Unsigned32 represent
       1-4 bytes of the IPv4 address in network-byte order. For
       an IPv6 network, TripId will not represent the IPv6
       address."
    SYNTAX Unsigned32 (0..4294967295)

TripAddressFamily ::= TEXTUAL-CONVENTION
    STATUS current
    DESCRIPTION
        "A type of address for a TRIP route. Address families
        defined within this MIB module are:

        Code              Address Family
        1                 Decimal Routing Numbers
        2                 PentaDecimal Routing Numbers
        3                 E.164 Numbers
        255               An other type of address family"

    SYNTAX INTEGER
        { decimal(1), pentadecimal(2), e164(3), other(255) }
TripAppProtocol ::= TEXTUAL-CONVENTION
    STATUS current
    DESCRIPTION
        "The application protocol used for communication with TRIP
        Location Servers. Protocols defined in this MIB Module
        are:

        Code              Protocol
        1                 SIP
        2                 H.323-H.225.0-Q.931
        3                 H.323-H.225.0-RAS
        4                 H.323-H.225.0-Annex-G
        255               An other type of application protocol"

    SYNTAX INTEGER
        { sip(1), q931(2), ras(3), annexG(4), other(255) }

TripCommunityId ::= TEXTUAL-CONVENTION
    STATUS current
    DESCRIPTION
       "The range of legal values for a TRIP Community
       Identifier."
    SYNTAX Unsigned32 (0..4294967295)

TripProtocolVersion ::= TEXTUAL-CONVENTION
    STATUS current
    DESCRIPTION
       "The version number of the TRIP protocol."
    SYNTAX Integer32 (1..255)

TripSendReceiveMode ::= TEXTUAL-CONVENTION
    STATUS current
    DESCRIPTION
       "The operational mode of the TRIP application. Possible
       values are:
          1 - Send Receive mode
          2 - Send only mode
          3 - Receive Only mode"
    SYNTAX INTEGER { sendReceive(1), sendOnly(2), receiveOnly(3) }

END
