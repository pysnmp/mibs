TIMETRA-SDP-MIB DEFINITIONS ::= BEGIN

IMPORTS
    InterfaceIndexOrZero
                                                         FROM IF-MIB
    InetAddress, InetAddressType
                                                         FROM INET-ADDRESS-MIB
    MODULE-COMPLIANCE, NOTIFICATION-GROUP,
    OBJECT-GROUP
                                                         FROM SNMPv2-CONF
    Counter32, Counter64, Gauge32,
    Integer32, IpAddress, MODULE-IDENTITY,
    NOTIFICATION-TYPE, OBJECT-TYPE,
    Unsigned32
                                                         FROM SNMPv2-SMI
    DisplayString, MacAddress, RowStatus,
    TimeStamp, TruthValue
                                                         FROM SNMPv2-TC
    tmnxCardSlotNum, tmnxChassisIndex,
    tmnxMDASlotNum
                                                         FROM TIMETRA-CHASSIS-MIB
    TConfigOrVsdFilterID, TFilterID
                                                         FROM TIMETRA-FILTER-MIB
    timetraSRMIBModules
                                                         FROM TIMETRA-GLOBAL-MIB
    BridgeId, ConfigStatus, L2ptProtocols,
    LspIdList, MvplsPruneState,
    PWTemplateId, SdpBindBandwidth,
    SdpBindVcType, SdpId, ServObjDesc,
    ServObjName, StpExceptionCondition,
    StpPortRole, StpProtocol, TStpPortState,
    TdmOptionsCasTrunkFraming,
    TdmOptionsSigPkts, TlsBpduTranslation,
    TlsLimitMacMove, TlsLimitMacMoveLevel,
    TmnxSiteId, VpnId, custId,
    protectedMacForNotify,
    svcDhcpClientLease, svcDhcpCoAError,
    svcDhcpLseStateNewChAddr,
    svcDhcpLseStateNewCiAddr,
    svcDhcpLseStateOldChAddr,
    svcDhcpLseStateOldCiAddr,
    svcDhcpLseStatePopulateError,
    svcDhcpPacketProblem, svcDhcpProxyError,
    svcDhcpSubAuthError, svcId,
    svcTlsMacMoveMaxRate,
    svcTlsStpDesignatedRoot, svcVpnId,
    tlsDhcpPacketProblem, tlsFdbType,
    tmnxCustomerBridgeId,
    tmnxCustomerRootBridgeId,
    tmnxOldSdpBindTlsStpPortState,
    tmnxOtherBridgeId, tmnxServConformance,
    tmnxServNotifications, tmnxServObjs,
    tmnxSvcObjs, tstpTraps
                                                         FROM TIMETRA-SERV-MIB
    AluNgeKeygroupIdOrZero, SdpBindId,
    ServiceAdminStatus, TCpmProtPolicyID,
    TFCSet, TItemDescription,
    TLNamedItemOrEmpty, TNamedItem,
    TNamedItemOrEmpty,
    TPolicyStatementNameOrEmpty,
    TQosQGrpInstanceIDorZero,
    TSdpEgressPolicyID, TSdpIngressPolicyID,
    TmnxActionType, TmnxAdminState,
    TmnxAdminStateTruthValue, TmnxBfdEncap,
    TmnxBsxAarpIdOrZero,
    TmnxBsxAarpServiceRefType,
    TmnxBsxTransPrefPolicyIdOrZero,
    TmnxBsxTransitIpPolicyIdOrZero,
    TmnxCreateOrigin, TmnxCustId,
    TmnxEnabledDisabled,
    TmnxEnabledDisabledAdminState,
    TmnxEvpnMHEthSegStatus, TmnxISID,
    TmnxIgmpVersion, TmnxIsidMFibStatus,
    TmnxMplsTpGlobalID, TmnxMplsTpNodeID,
    TmnxOperState, TmnxPortID,
    TmnxPwGlobalId, TmnxServId,
    TmnxSpokeSdpIdOrZero,
    TmnxVPNRouteDistinguisher,
    TmnxVRtrMplsLspID,
    TmnxVRtrMplsLspIDNoZero, TmnxVcId,
    TmnxVcIdOrNone
                                                         FROM TIMETRA-TC-MIB
    ;

timetraServicesSdpMIBModule      MODULE-IDENTITY
    LAST-UPDATED "201605140000Z"
    ORGANIZATION "Nokia"
    CONTACT-INFO
        "Nokia SROS Support
         Web: http://www.nokia.com"
    DESCRIPTION
        "This document is the SNMP MIB module to manage and provision the
         various services of the Nokia SROS system.

         Copyright 2003-2018 Nokia. All rights reserved. Reproduction of this
         document is authorized on the condition that the foregoing copyright
         notice is included.

         This SNMP MIB module (Specification) embodies Nokia's
         proprietary intellectual property.  Nokia retains
         all title and ownership in the Specification, including any
         revisions.

         Nokia grants all interested parties a non-exclusive license to use and
         distribute an unmodified copy of this Specification in connection with
         management of Nokia products, and without fee, provided this copyright
         notice and license appear on all copies.

         This Specification is supplied 'as is', and Nokia makes no warranty,
         either express or implied, as to the use, operation, condition, or
         performance of the Specification."

    REVISION    "201605140000Z"
    DESCRIPTION
        "Rev 15.0              14 May 2016 00:00
         15.0 release of the TIMETRA-SDP-MIB."

    REVISION    "201602010000Z"
    DESCRIPTION
        "Rev 14.0               1 Feb 2016 00:00
         14.0 release of the TIMETRA-SDP-MIB."

    REVISION    "201501010000Z"
    DESCRIPTION
        "Rev 13.0               1 Jan 2015 00:00
         13.0 release of the TIMETRA-SDP-MIB."

    REVISION    "201401010000Z"
    DESCRIPTION
        "Rev 12.0               1 Jan 2014 00:00
         12.0 release of the TIMETRA-SDP-MIB."

    REVISION    "201102010000Z"
    DESCRIPTION
        "Rev 9.0                1 Feb 2011 00:00
         9.0 release of the TIMETRA-SDP-MIB."

    REVISION    "200902280000Z"
    DESCRIPTION
        "Rev 7.0                28 Feb 2009 00:00
         7.0 release of the TIMETRA-SDP-MIB."

    REVISION    "200807010000Z"
    DESCRIPTION
        "Rev 6.1                01 Jul 2008 00:00
         6.1 release of the TIMETRA-SDP-MIB."

    REVISION    "200710010000Z"
    DESCRIPTION
        "Rev 1.0                01 Oct 2007 00:00
         1.0 release of the TIMETRA-SDP-MIB from TIMETRA-SERV-MIB."

    ::= { timetraSRMIBModules 56 }

tmnxSdpObjs                      OBJECT IDENTIFIER ::= { tmnxServObjs 4 }

sdpNumEntries                    OBJECT-TYPE
    SYNTAX      Integer32
    MAX-ACCESS  read-only
    STATUS      current
    DESCRIPTION
        "The current number of SDPs configured in this device."
    ::= { tmnxSdpObjs 1 }

sdpNextFreeId                    OBJECT-TYPE
    SYNTAX      SdpId
    MAX-ACCESS  read-only
    STATUS      current
    DESCRIPTION
        "The next available value for sdpId."
    ::= { tmnxSdpObjs 2 }

sdpInfoTable                     OBJECT-TYPE
    SYNTAX      SEQUENCE OF SdpInfoEntry
    MAX-ACCESS  not-accessible
    STATUS      current
    DESCRIPTION
        "A table that contains SDP information."
    ::= { tmnxSdpObjs 3 }

sdpInfoEntry                     OBJECT-TYPE
    SYNTAX      SdpInfoEntry
    MAX-ACCESS  not-accessible
    STATUS      current
    DESCRIPTION
        "Information about a specific SDP."
    INDEX       { sdpId }
    ::= { sdpInfoTable 1 }

SdpInfoEntry                     ::= SEQUENCE
{
    sdpId                            SdpId,
    sdpRowStatus                     RowStatus,
    sdpDelivery                      INTEGER,
    sdpFarEndIpAddress               IpAddress,
    sdpLspList                       LspIdList,
    sdpDescription                   ServObjDesc,
    sdpLabelSignaling                INTEGER,
    sdpAdminStatus                   ServiceAdminStatus,
    sdpOperStatus                    INTEGER,
    sdpAdminPathMtu                  Integer32,
    sdpOperPathMtu                   Integer32,
    sdpKeepAliveAdminStatus          TmnxEnabledDisabledAdminState,
    sdpKeepAliveOperStatus           INTEGER,
    sdpKeepAliveHelloTime            Integer32,
    sdpKeepAliveMaxDropCount         Integer32,
    sdpKeepAliveHoldDownTime         Integer32,
    sdpLastMgmtChange                TimeStamp,
    sdpKeepAliveHelloMessageLength   Integer32,
    sdpKeepAliveNumHelloRequestMessages Unsigned32,
    sdpKeepAliveNumHelloResponseMessages Unsigned32,
    sdpKeepAliveNumLateHelloResponseMessages Unsigned32,
    sdpKeepAliveHelloRequestTimeout  Integer32,
    sdpLdpEnabled                    TruthValue,
    sdpVlanVcEtype                   Unsigned32,
    sdpAdvertisedVllMtuOverride      TruthValue,
    sdpOperFlags                     BITS,
    sdpLastStatusChange              TimeStamp,
    sdpMvplsMgmtService              TmnxServId,
    sdpMvplsMgmtSdpBndId             SdpBindId,
    sdpCollectAcctStats              TruthValue,
    sdpAccountingPolicyId            Unsigned32,
    sdpClassFwdingEnabled            TmnxAdminStateTruthValue,
    sdpClassFwdingDefaultLsp         TmnxVRtrMplsLspID,
    sdpClassFwdingMcLsp              TmnxVRtrMplsLspID,
    sdpMetric                        Unsigned32,
    sdpAutoSdp                       TruthValue,
    sdpSnmpAllowed                   TruthValue,
    sdpPBBEtype                      Unsigned32,
    sdpBandwidthBookingFactor        Unsigned32,
    sdpOperBandwidth                 Unsigned32,
    sdpAvailableBandwidth            Unsigned32,
    sdpMaxBookableBandwidth          Unsigned32,
    sdpBookedBandwidth               Unsigned32,
    sdpCreationOrigin                TmnxCreateOrigin,
    sdpEnforceDiffServLspFc          TruthValue,
    sdpMixedLspModeEnabled           TruthValue,
    sdpLspRevertTime                 Integer32,
    sdpLspRevertTimeCountDown        Integer32,
    sdpLdpLspId                      Unsigned32,
    sdpLdpActive                     TruthValue,
    sdpNetDomainName                 TNamedItemOrEmpty,
    sdpEgressIfsNetDomainConsistent  INTEGER,
    sdpBgpTunnelEnabled              TruthValue,
    sdpBgpTunnelLspId                Unsigned32,
    sdpTunnelFarEndIpAddress         IpAddress,
    sdpActiveLspType                 INTEGER,
    sdpBindingPort                   TmnxPortID,
    sdpFarEndNodeId                  TmnxMplsTpNodeID,
    sdpFarEndGlobalId                TmnxMplsTpGlobalID,
    sdpFarEndInetAddressType         InetAddressType,
    sdpFarEndInetAddress             InetAddress,
    sdpLocalEndInetAddressType       InetAddressType,
    sdpLocalEndInetAddress           InetAddress,
    sdpSourceBMacLSB                 Unsigned32,
    sdpControlPWVCId                 TmnxVcIdOrNone,
    sdpControlPWIsActive             TruthValue,
    sdpTunnelFarEndInetAddressType   InetAddressType,
    sdpTunnelFarEndInetAddress       InetAddress,
    sdpGreAllowFragmentation         TruthValue,
    sdpFpeLspId                      Unsigned32,
    sdpWeightedEcmpEnabled           TruthValue,
    sdpOperTunnelFarEndInetAddrType  InetAddressType,
    sdpOperTunnelFarEndInetAddr      InetAddress
}

sdpId                            OBJECT-TYPE
    SYNTAX      SdpId
    MAX-ACCESS  read-only
    STATUS      current
    DESCRIPTION
        "SDP identifier."
    ::= { sdpInfoEntry 1 }

sdpRowStatus                     OBJECT-TYPE
    SYNTAX      RowStatus
    MAX-ACCESS  read-create
    STATUS      current
    DESCRIPTION
        "This object specifies the status of this row. The only values
         supported during a set operation are 'createAndGo' and 'destroy'. To
         delete an entry from this table, the corresponding SDP must be
         administratively down, not bound to any service, and not in use as a
         mirror destination."
    ::= { sdpInfoEntry 2 }

sdpDelivery                      OBJECT-TYPE
    SYNTAX      INTEGER {
        gre           (1),
        mpls          (2),
        l2tpv3        (4),
        greethbridged (5)
    }
    MAX-ACCESS  read-create
    STATUS      current
    DESCRIPTION
        "This object specifies the type of delivery used by this SDP. The value
         of this object must be specified when the row is created and cannot be
         changed while the row status is 'active'."
    ::= { sdpInfoEntry 3 }

sdpFarEndIpAddress               OBJECT-TYPE
    SYNTAX      IpAddress
    MAX-ACCESS  read-create
    STATUS      obsolete
    DESCRIPTION
        "This object specifies the IP address of the remote end of the GRE or
         MPLS tunnel defined by this SDP. If sdpTunnelFarEndIpAddress is not
         set, then sdpFarEndIpAddress also specifies the remote end of the TLDP
         session.

         The value of this object must be set to a non-default value when the
         sdpDelivery is set to 'gre' or 'mpls' for the row to become 'active',
         and can only be changed while the admin status of the SDP is 'down'.

         The sdpFarEndIpAddress is obsoleted and replaced with
         sdpFarEndInetAddressType and sdpFarEndInetAddress objects."
    DEFVAL      { 0 }
    ::= { sdpInfoEntry 4 }

sdpLspList                       OBJECT-TYPE
    SYNTAX      LspIdList
    MAX-ACCESS  read-create
    STATUS      obsolete
    DESCRIPTION
        "When the SDP delivery specified by sdpDelivery is 'mpls', this object
         specifies the list of LSPs used to reach the far-end ESR device.

         All the LSPs in this list must terminate at the IP address specified
         by sdpFarEndIpAddress or sdpFarEndNodeId (for sdpDelivery of 'mpls').
         This object is otherwise insignificant and should contain a value of
         0.

         When this list has more than one element, the Nokia SROS router will
         use all of the LSPs for load balancing purposes. Each LSP ID in the
         list corresponds to the vRtrMplsLspIndex of the given MPLS LSP."
    ::= { sdpInfoEntry 5 }

sdpDescription                   OBJECT-TYPE
    SYNTAX      ServObjDesc
    MAX-ACCESS  read-create
    STATUS      current
    DESCRIPTION
        "Generic information about this SDP."
    DEFVAL      { "" }
    ::= { sdpInfoEntry 6 }

sdpLabelSignaling                OBJECT-TYPE
    SYNTAX      INTEGER {
        none (1),
        tldp (2),
        bgp  (3)
    }
    MAX-ACCESS  read-create
    STATUS      current
    DESCRIPTION
        "This object specifies the signaling protocol used to obtain the
         ingress and egress labels used in frames transmitted and received on
         this SDP. When the value of this object is 'none' then the labels are
         manually assigned at the time the SDP is bound to a service. The value
         of this object can only be changed while the admin status of the SDP
         is 'down'.

         An 'inconsistentValue' error is returned if this object is not set to
         'none' when sdpDelivery is set to 'mpls'.

         An 'inconsistentValue' error is returned if this object is not set to
         'none' when sdpDelivery is set to 'l2tpv3'.

         Default value of this object is set to 'none' when sdpDelivery is set
         to 'l2tpv3' otherwise default value for this object is set to 'tldp'."
    ::= { sdpInfoEntry 7 }

sdpAdminStatus                   OBJECT-TYPE
    SYNTAX      ServiceAdminStatus
    MAX-ACCESS  read-create
    STATUS      current
    DESCRIPTION
        "The desired state of this SDP."
    DEFVAL      { down }
    ::= { sdpInfoEntry 8 }

sdpOperStatus                    OBJECT-TYPE
    SYNTAX      INTEGER {
        up                     (1),
        notAlive               (2),
        notReady               (3),
        invalidEgressInterface (4),
        transportTunnelDown    (5),
        down                   (6)
    }
    MAX-ACCESS  read-only
    STATUS      current
    DESCRIPTION
        "The operating state of this SDP. The value 'notAlive' is valid only
         when keep-alive is enabled, and it means that the keep-alive operating
         status is not alive. The value 'notReady' is valid only when this SDP
         uses a label signaling protocol (e.g. TLDP) and it means that the
         signaling session with the far-end peer has not been established. The
         value 'invalidEgressInterface' indicates that the IOMs have detected
         that the egress interface towards the far-end device is not a network
         port."
    ::= { sdpInfoEntry 9 }

sdpAdminPathMtu                  OBJECT-TYPE
    SYNTAX      Integer32 (0 | 576..9782)
    MAX-ACCESS  read-create
    STATUS      current
    DESCRIPTION
        "This object specifies the desired largest service frame size (in
         octets) that can be transmitted through this SDP to the far-end ESR,
         without requiring the packet to be fragmented. The default value of
         zero indicates that the path MTU should be computed dynamically from
         the corresponding MTU of the tunnel."
    DEFVAL      { 0 }
    ::= { sdpInfoEntry 10 }

sdpOperPathMtu                   OBJECT-TYPE
    SYNTAX      Integer32
    MAX-ACCESS  read-only
    STATUS      current
    DESCRIPTION
        "This object indicates the actual largest service frame size (in
         octets) that can be transmitted through this SDP to the far-end ESR,
         without requiring the packet to be fragmented. In order to be able to
         bind this SDP to a given service, the value of this object minus the
         control word size (if applicable) must be equal to or larger than the
         MTU of the service, as defined by its svcMtu."
    ::= { sdpInfoEntry 11 }

sdpKeepAliveAdminStatus          OBJECT-TYPE
    SYNTAX      TmnxEnabledDisabledAdminState
    MAX-ACCESS  read-create
    STATUS      current
    DESCRIPTION
        "This object is used to enable or disable the keep-alive protocol used
         to determine the operating status of this SDP."
    DEFVAL      { disabled }
    ::= { sdpInfoEntry 12 }

sdpKeepAliveOperStatus           OBJECT-TYPE
    SYNTAX      INTEGER {
        alive            (1),
        noResponse       (2),
        senderIdInvalid  (3),
        responderIdError (4),
        disabled         (5)
    }
    MAX-ACCESS  read-only
    STATUS      current
    DESCRIPTION
        "The current status of the keep-alive protocol. The value 'alive'
         indicates that the far-end ESR is replying the SDP Echo Requests
         messages sent by this device indicating no error condition. The value
         'noResponse' indicates that the number of consecutive SDP Echo Request
         messages unacknowledged by the far-end ESR exceeded the limit defined
         by sdpKeepAliveMaxDropCount. The values 'senderIdInvalid' and
         'responderIdError' are two error conditions detected by the far-end
         ESR. The value 'disabled' indicates that the keep-alive protocol is
         not enabled."
    ::= { sdpInfoEntry 13 }

sdpKeepAliveHelloTime            OBJECT-TYPE
    SYNTAX      Integer32 (1..3600)
    UNITS       "seconds"
    MAX-ACCESS  read-create
    STATUS      current
    DESCRIPTION
        "This object specifies how often the SDP Echo Request messages are
         transmitted on this SDP."
    DEFVAL      { 10 }
    ::= { sdpInfoEntry 14 }

sdpKeepAliveMaxDropCount         OBJECT-TYPE
    SYNTAX      Integer32 (1..5)
    MAX-ACCESS  read-create
    STATUS      current
    DESCRIPTION
        "This object specifies the maximum number of consecutive SDP Echo
         Request messages that can be unacknowledged before the keep-alive
         protocol reports a fault."
    DEFVAL      { 3 }
    ::= { sdpInfoEntry 15 }

sdpKeepAliveHoldDownTime         OBJECT-TYPE
    SYNTAX      Integer32 (0..3600)
    UNITS       "seconds"
    MAX-ACCESS  read-create
    STATUS      current
    DESCRIPTION
        "This object specifies the amount of time to wait before the keep-alive
         operating status is eligible to enter the 'alive' state."
    DEFVAL      { 10 }
    ::= { sdpInfoEntry 16 }

sdpLastMgmtChange                OBJECT-TYPE
    SYNTAX      TimeStamp
    MAX-ACCESS  read-only
    STATUS      current
    DESCRIPTION
        "The value of sysUpTime at the time of the most recent
         management-initiated change to this SDP."
    ::= { sdpInfoEntry 17 }

sdpKeepAliveHelloMessageLength   OBJECT-TYPE
    SYNTAX      Integer32 (0 | 40..9198)
    MAX-ACCESS  read-create
    STATUS      current
    DESCRIPTION
        "This object specifies the length of the SDP Echo Request messages
         transmitted on this SDP. The default value of zero indicates that the
         message length should be equal to the SDP's operating path MTU, as
         specified by sdpOperPathMtu. When the default value is overridden, the
         message length is sdpKeepAliveHelloMessageLength."
    DEFVAL      { 0 }
    ::= { sdpInfoEntry 18 }

sdpKeepAliveNumHelloRequestMessages OBJECT-TYPE
    SYNTAX      Unsigned32
    MAX-ACCESS  read-only
    STATUS      current
    DESCRIPTION
        "The number of SDP Echo Request messages transmitted since the
         keep-alive was administratively enabled or the counter was cleared."
    ::= { sdpInfoEntry 19 }

sdpKeepAliveNumHelloResponseMessages OBJECT-TYPE
    SYNTAX      Unsigned32
    MAX-ACCESS  read-only
    STATUS      current
    DESCRIPTION
        "The number of SDP Echo Response messages received since the keep-alive
         was administratively enabled or the counter was cleared."
    ::= { sdpInfoEntry 20 }

sdpKeepAliveNumLateHelloResponseMessages OBJECT-TYPE
    SYNTAX      Unsigned32
    MAX-ACCESS  read-only
    STATUS      current
    DESCRIPTION
        "The number of SDP Echo Response messages received after the
         corresponding Request timeout timer expired."
    ::= { sdpInfoEntry 21 }

sdpKeepAliveHelloRequestTimeout  OBJECT-TYPE
    SYNTAX      Integer32 (1..10)
    UNITS       "seconds"
    MAX-ACCESS  read-create
    STATUS      current
    DESCRIPTION
        "The number of seconds to wait for an SDP Echo Response message before
         declaring a timeout."
    DEFVAL      { 5 }
    ::= { sdpInfoEntry 22 }

sdpLdpEnabled                    OBJECT-TYPE
    SYNTAX      TruthValue
    MAX-ACCESS  read-create
    STATUS      current
    DESCRIPTION
        "When the value of this object is 'true' the transport LSPs are
         signalled by LDP, as opposed to being provisioned static or
         RSVP-signalled LSPs. This object applies only to MPLS SDPs."
    DEFVAL      { false }
    ::= { sdpInfoEntry 23 }

sdpVlanVcEtype                   OBJECT-TYPE
    SYNTAX      Unsigned32 (1536..65535)
    MAX-ACCESS  read-create
    STATUS      current
    DESCRIPTION
        "This object specifies the Ethertype used in frames sent out this SDP,
         when the VC type is vlan."
    DEFVAL      { '8100'H }
    ::= { sdpInfoEntry 24 }

sdpAdvertisedVllMtuOverride      OBJECT-TYPE
    SYNTAX      TruthValue
    MAX-ACCESS  read-create
    STATUS      current
    DESCRIPTION
        "When the value of this object is 'true' the advertised MTU of a VLL
         spoke SDP bind includes the 14-byte L2 header, so that it is backward
         compatible with pre-2.0 software."
    DEFVAL      { false }
    ::= { sdpInfoEntry 25 }

sdpOperFlags                     OBJECT-TYPE
    SYNTAX      BITS {
        sdpAdminDown            (0),
        signalingSessionDown    (1),
        transportTunnelDown     (2),
        keepaliveFailure        (3),
        invalidEgressInterface  (4),
        noSystemIpAddress       (5),
        transportTunnelUnstable (6),
        notOnBindingPort        (7)
    }
    MAX-ACCESS  read-only
    STATUS      current
    DESCRIPTION
        "This object indicates all the conditions that affect the operating
         status of this SDP."
    ::= { sdpInfoEntry 26 }

sdpLastStatusChange              OBJECT-TYPE
    SYNTAX      TimeStamp
    MAX-ACCESS  read-only
    STATUS      current
    DESCRIPTION
        "The value of sysUpTime at the time of the most recent operating status
         change to this SDP."
    ::= { sdpInfoEntry 27 }

sdpMvplsMgmtService              OBJECT-TYPE
    SYNTAX      TmnxServId
    MAX-ACCESS  read-only
    STATUS      current
    DESCRIPTION
        "The value of sdpMvplsMgmtService indicates the service Id of the
         service where the STP instance is running that is managing this SDP.
         This object is only valid if sdpMvplsMgmtService is different from 0."
    ::= { sdpInfoEntry 28 }

sdpMvplsMgmtSdpBndId             OBJECT-TYPE
    SYNTAX      SdpBindId
    MAX-ACCESS  read-only
    STATUS      current
    DESCRIPTION
        "The value of sdpMvplsMgmtSdpBndId indicates which SDP bind in the
         mVPLS instance specified in sdpMvplsMgmtService is controlling this
         SDP. This object is only valid if sdpMvplsMgmtService is different
         from 0."
    ::= { sdpInfoEntry 29 }

sdpCollectAcctStats              OBJECT-TYPE
    SYNTAX      TruthValue
    MAX-ACCESS  read-create
    STATUS      current
    DESCRIPTION
        "The value of the object sdpCollectAcctStats specifies whether the
         agent collects accounting statistics for this SDP. When the value is
         'true' the agent collects accounting statistics on this SDP."
    DEFVAL      { false }
    ::= { sdpInfoEntry 30 }

sdpAccountingPolicyId            OBJECT-TYPE
    SYNTAX      Unsigned32 (0..99)
    MAX-ACCESS  read-create
    STATUS      current
    DESCRIPTION
        "The value of sdpAccountingPolicyId specifies the policy to use to
         collect accounting statistics on this SDP. The value zero indicates
         that the agent should use the default accounting policy, if one
         exists."
    DEFVAL      { 0 }
    ::= { sdpInfoEntry 31 }

sdpClassFwdingEnabled            OBJECT-TYPE
    SYNTAX      TmnxAdminStateTruthValue
    MAX-ACCESS  read-create
    STATUS      current
    DESCRIPTION
        "The value of sdpClassFwdingEnabled specifies the admin state of
         class-based forwarding on this SDP. When the value is 'true',
         class-based forwarding is enabled."
    DEFVAL      { false }
    ::= { sdpInfoEntry 32 }

sdpClassFwdingDefaultLsp         OBJECT-TYPE
    SYNTAX      TmnxVRtrMplsLspID
    MAX-ACCESS  read-create
    STATUS      current
    DESCRIPTION
        "The value of sdpClassFwdingDefaultLsp specifies the LSP ID that is
         used as a default when class-based forwarding is enabled on this SDP.
         This object must be set when enabling class-based forwarding."
    DEFVAL      { 0 }
    ::= { sdpInfoEntry 33 }

sdpClassFwdingMcLsp              OBJECT-TYPE
    SYNTAX      TmnxVRtrMplsLspID
    MAX-ACCESS  read-create
    STATUS      current
    DESCRIPTION
        "The value of sdpClassFwdingMcLsp specifies the LSP ID that all
         multicast traffic will be forwarded on when class-based forwarding is
         enabled on this SDP. When this object has its default value, multicast
         traffic will be forwarded on an LSP according to its forwarding class
         mapping."
    DEFVAL      { 0 }
    ::= { sdpInfoEntry 34 }

sdpMetric                        OBJECT-TYPE
    SYNTAX      Unsigned32 (0..65535)
    MAX-ACCESS  read-create
    STATUS      current
    DESCRIPTION
        "The value of sdpMetric specifies the metric to be used within the
         Tunnel Table Manager for decision making purposes. When multiple SDPs
         going to the same destination exist, this value is used as a
         tiebreaker by Tunnel Table Manager users like MP-BGP to select route
         with lower value."
    DEFVAL      { 0 }
    ::= { sdpInfoEntry 35 }

sdpAutoSdp                       OBJECT-TYPE
    SYNTAX      TruthValue
    MAX-ACCESS  read-only
    STATUS      current
    DESCRIPTION
        "The value of sdpAutoSdp indicates whether this is an Auto generated
         SDP from RADIUS discovery or BGP auto-discovery."
    ::= { sdpInfoEntry 36 }

sdpSnmpAllowed                   OBJECT-TYPE
    SYNTAX      TruthValue
    MAX-ACCESS  read-only
    STATUS      obsolete
    DESCRIPTION
        "The value of sdpSnmpAllowed indicates if SNMP sets are allowed on this
         SDP."
    ::= { sdpInfoEntry 37 }

sdpPBBEtype                      OBJECT-TYPE
    SYNTAX      Unsigned32 (1536..65535)
    MAX-ACCESS  read-create
    STATUS      current
    DESCRIPTION
        "This object specifies the Ethertype used in frames sent out on this
         SDP when sdpBindVcType is 'vlan' for Provider Backbone Bridging
         frames."
    DEFVAL      { '88E7'H }
    ::= { sdpInfoEntry 38 }

sdpBandwidthBookingFactor        OBJECT-TYPE
    SYNTAX      Unsigned32 (0..1000)
    MAX-ACCESS  read-create
    STATUS      current
    DESCRIPTION
        "sdpBandwidthBookingFactor is used to calculate the max
         SDP available bandwidth.  The value of
         sdpBandwidthBookingFactor specifies the percentage of the
         SDP max available bandwidth for VLL call admission. When
         the value of sdpBandwidthBookingFactor is set to zero (0),
         no new VLL spoke-sdp bindings with non-zero bandwidth are
         permitted with this SDP.  Overbooking, >100% is allowed."
    DEFVAL      { 100 }
    ::= { sdpInfoEntry 39 }

sdpOperBandwidth                 OBJECT-TYPE
    SYNTAX      Unsigned32
    UNITS       "kilobps"
    MAX-ACCESS  read-only
    STATUS      current
    DESCRIPTION
        "The value of sdpOperBandwidth indicates the operational Bandwidth in
         kilobits per seconds (Kbps) available for this SDP. The value
         sdpOperBandwidth is determined by the sum of the bandwidth of all the
         RSVP LSPs used by the SDP."
    ::= { sdpInfoEntry 40 }

sdpAvailableBandwidth            OBJECT-TYPE
    SYNTAX      Unsigned32
    UNITS       "kilobps"
    MAX-ACCESS  read-only
    STATUS      current
    DESCRIPTION
        "The value of sdpAvailableBandwidth indicates the Bandwidth that is
         still free for booking by the SDP bindings on the SDP."
    ::= { sdpInfoEntry 41 }

sdpMaxBookableBandwidth          OBJECT-TYPE
    SYNTAX      Unsigned32
    UNITS       "kilobps"
    MAX-ACCESS  accessible-for-notify
    STATUS      current
    DESCRIPTION
        "The value of sdpMaxBookableBandwidth indicates the max Bandwidth that
         the SDP has for booking by the SDP bindings. The value of
         sdpMaxBookableBandwidth is calculated as follow:

         sdpMaxBookableBandwidth = sdpOperBandwidth *
                                   sdpBandwidthBookingFactor"
    ::= { sdpInfoEntry 42 }

sdpBookedBandwidth               OBJECT-TYPE
    SYNTAX      Unsigned32
    UNITS       "kilobps"
    MAX-ACCESS  accessible-for-notify
    STATUS      current
    DESCRIPTION
        "The value of sdpBookedBandwidth indicates the SDP Bandwidth that has
         been booked by the SDP bindings."
    ::= { sdpInfoEntry 43 }

sdpCreationOrigin                OBJECT-TYPE
    SYNTAX      TmnxCreateOrigin
    MAX-ACCESS  read-only
    STATUS      current
    DESCRIPTION
        "The value of sdpCreationOrigin indicates the protocol or mechanism
         which created this SDP."
    ::= { sdpInfoEntry 44 }

sdpEnforceDiffServLspFc          OBJECT-TYPE
    SYNTAX      TruthValue
    MAX-ACCESS  read-create
    STATUS      current
    DESCRIPTION
        "The value of sdpEnforceDiffServLspFc specifies whether service manager
         must validate with RSVP the support of the FC by the LSP.

         By default, the SDP uses the direct configuration without validation
         with RSVP. "
    DEFVAL      { false }
    ::= { sdpInfoEntry 45 }

sdpMixedLspModeEnabled           OBJECT-TYPE
    SYNTAX      TruthValue
    MAX-ACCESS  read-create
    STATUS      current
    DESCRIPTION
        "The value of sdpMixedLspModeEnabled specifies whether
         mixed mode LSPs is enabled on this SDP.  Setting the
         value to 'true' allows LDP to be enabled and LSPs to
         be configured at the same time on this SDP."
    DEFVAL      { false }
    ::= { sdpInfoEntry 46 }

sdpLspRevertTime                 OBJECT-TYPE
    SYNTAX      Integer32 (-1 | 0..600)
    UNITS       "seconds"
    MAX-ACCESS  read-create
    STATUS      current
    DESCRIPTION
        "The value of sdpLspRevertTime specifies the time to wait before
         reverting back from LDP to the configured LSPs, after having failed
         over to LDP.

         When the value is -1, the sdp will never revert back."
    DEFVAL      { 0 }
    ::= { sdpInfoEntry 47 }

sdpLspRevertTimeCountDown        OBJECT-TYPE
    SYNTAX      Integer32 (-1 | 0..600)
    UNITS       "seconds"
    MAX-ACCESS  read-only
    STATUS      current
    DESCRIPTION
        "The value of sdpLspRevertTimeCountDown indicated the timer countdown
         before reverting back from LDP on this SDP. The timer countdown begins
         after the first configured LSP becomes active.

         The value of -1 indicates when the revert time countdown is not
         applicable."
    ::= { sdpInfoEntry 48 }

sdpLdpLspId                      OBJECT-TYPE
    SYNTAX      Unsigned32
    MAX-ACCESS  read-only
    STATUS      current
    DESCRIPTION
        "The value of sdpLdpLspId indicates the Id for the LDP LSP if
         sdpLdpEnabled is set to 'true' and there is a valid LDP route to the
         sdpFarEndIpAddress or sdpFarEndNodeId."
    ::= { sdpInfoEntry 49 }

sdpLdpActive                     OBJECT-TYPE
    SYNTAX      TruthValue
    MAX-ACCESS  read-only
    STATUS      obsolete
    DESCRIPTION
        "The value of sdpLdpActive indicates whether LDP is active for the
         current SDP."
    ::= { sdpInfoEntry 50 }

sdpNetDomainName                 OBJECT-TYPE
    SYNTAX      TNamedItemOrEmpty
    MAX-ACCESS  read-create
    STATUS      current
    DESCRIPTION
        "The value of sdpNetDomainName specifies the network-domain name this
         SDP is associated with. The network-domain defines the list of network
         interfaces this SDP can send traffic on.

         The default value of this object is the 'default' network-domain."
    DEFVAL      { "default" }
    ::= { sdpInfoEntry 51 }

sdpEgressIfsNetDomainConsistent  OBJECT-TYPE
    SYNTAX      INTEGER {
        notApplicable (1),
        consistent    (2),
        inconsistent  (3)
    }
    MAX-ACCESS  read-only
    STATUS      current
    DESCRIPTION
        "The value of sdpEgressIfsNetDomainConsistent indicates whether all the
         egress network interfaces that can carry traffic on this SDP are
         associated with the network-domain configured on this SDP.

         A value of 'notApplicable' indicates that there is no egress network
         interface that can carry traffic on this SDP.

         A value of 'consistent' indicates that the network-domains for all the
         egress network interfaces that can carry traffic on this SDP are
         consistent.

         A value of 'inconsistent' indicates that the network-domain for one or
         more egress network interfaces that can carry traffic on this SDP are
         inconsistent."
    ::= { sdpInfoEntry 52 }

sdpBgpTunnelEnabled              OBJECT-TYPE
    SYNTAX      TruthValue
    MAX-ACCESS  read-create
    STATUS      current
    DESCRIPTION
        "The value of sdpBgpTunnelEnabled specifies whether the transport
         tunnel is BGP as opposed to LDP or RSVP signalled LSPs.

         This value cannot be set to 'true' if sdpLdpEnabled is 'true' or if
         there is at least one RSVP or static LSP provisioned.

         This object applies to MPLS SDPs."
    DEFVAL      { false }
    ::= { sdpInfoEntry 53 }

sdpBgpTunnelLspId                OBJECT-TYPE
    SYNTAX      Unsigned32
    MAX-ACCESS  read-only
    STATUS      current
    DESCRIPTION
        "The value of sdpBgpTunnelLspId indicates the Id for the BGP Tunnel LSP
         if sdpBgpTunnelEnabled is set to 'true' and there is a valid LDP route
         to the sdpFarEndIpAddress."
    ::= { sdpInfoEntry 54 }

sdpTunnelFarEndIpAddress         OBJECT-TYPE
    SYNTAX      IpAddress
    MAX-ACCESS  read-create
    STATUS      obsolete
    DESCRIPTION
        "The value of sdpTunnelFarEndIpAddress specifies the IP address of the
         remote end of the transport tunnel for this SDP.

         The value can only be changed while the admin status of the SDP is
         'down'.

         The sdpTunnelFarEndIpAddress is obsoleted and replaced with
         sdpTunnelFarEndInetAddressType and sdpTunnelFarEndInetAddress objects."
    ::= { sdpInfoEntry 55 }

sdpActiveLspType                 OBJECT-TYPE
    SYNTAX      INTEGER {
        not-applicable (0),
        rsvp           (1),
        ldp            (2),
        bgp            (3),
        none           (4),
        mplsTp         (5),
        srIsis         (6),
        srOspf         (7),
        srTeLsp        (8),
        fpe            (9)
    }
    MAX-ACCESS  read-only
    STATUS      current
    DESCRIPTION
        "The value of sdpActiveLspType indicates the type of LSP that is
         currently active on this SDP.

         For sdpDelivery 'gre', the value is always 'not-applicable'.

         For sdpDelivery 'mpls', the values can be 'rsvp', 'ldp', 'mplsTp',
         'srIsis', 'srOspf', 'srTeLsp', 'fpe', 'bgp' or 'none'."
    ::= { sdpInfoEntry 56 }

sdpBindingPort                   OBJECT-TYPE
    SYNTAX      TmnxPortID
    MAX-ACCESS  read-create
    STATUS      current
    DESCRIPTION
        "The value of sdpBindingPort specifies the port id for the binding on
         this SDP.

         The value of sdpPwPortOperStatus will be set to 'down' of all the
         related SDP pseudo-wire ports, if the SDP resolves to another port
         than the one specified here.

         An 'inconsistentValue' error is returned when this object is set to a
         non-default value when sdpDelivery is set to 'gre'."
    DEFVAL      { '1e000000'H }
    ::= { sdpInfoEntry 57 }

sdpFarEndNodeId                  OBJECT-TYPE
    SYNTAX      TmnxMplsTpNodeID
    MAX-ACCESS  read-create
    STATUS      current
    DESCRIPTION
        "The value of sdpFarEndNodeId specifies the node identifier of the
         far-end for this sdp.

         The value of this object must be set to a non-default value when the
         sdpDelivery is set to 'mpls' for the row to become 'active', and can
         only be changed while the admin status of the SDP is 'down'."
    DEFVAL      { 0 }
    ::= { sdpInfoEntry 58 }

sdpFarEndGlobalId                OBJECT-TYPE
    SYNTAX      TmnxMplsTpGlobalID
    MAX-ACCESS  read-create
    STATUS      current
    DESCRIPTION
        "The value of sdpFarEndGlobalId specifies the global identifier of the
         far-end for this sdp."
    DEFVAL      { 0 }
    ::= { sdpInfoEntry 59 }

sdpFarEndInetAddressType         OBJECT-TYPE
    SYNTAX      InetAddressType
    MAX-ACCESS  read-create
    STATUS      current
    DESCRIPTION
        "The value of the object sdpFarEndInetAddressType specifies the address
         type of sdpFarEndInetAddress."
    DEFVAL      { unknown }
    ::= { sdpInfoEntry 60 }

sdpFarEndInetAddress             OBJECT-TYPE
    SYNTAX      InetAddress (SIZE (0|4|16))
    MAX-ACCESS  read-create
    STATUS      current
    DESCRIPTION
        "The value of sdpFarEndInetAddress object specifies the IP address of
         the remote end of the tunnel defined by this SDP."
    DEFVAL      { ''H }
    ::= { sdpInfoEntry 61 }

sdpLocalEndInetAddressType       OBJECT-TYPE
    SYNTAX      InetAddressType
    MAX-ACCESS  read-create
    STATUS      current
    DESCRIPTION
        "The value of the object sdpLocalEndInetAddressType specifies the
         address type of sdpLocalEndInetAddress."
    DEFVAL      { unknown }
    ::= { sdpInfoEntry 62 }

sdpLocalEndInetAddress           OBJECT-TYPE
    SYNTAX      InetAddress (SIZE (0|4|16))
    MAX-ACCESS  read-create
    STATUS      current
    DESCRIPTION
        "The value of sdpLocalEndInetAddress object specifies the IP address of
         the local end of the tunnel defined by this SDP.

         An 'inconsistentValue' error is returned when sdpLocalEndInetAddress
         is set to non-default and sdpDelivery is not set to 'l2tpv3'."
    DEFVAL      { ''H }
    ::= { sdpInfoEntry 63 }

sdpSourceBMacLSB                 OBJECT-TYPE
    SYNTAX      Unsigned32 (0 | 1..65535)
    MAX-ACCESS  read-create
    STATUS      current
    DESCRIPTION
        "The value of sdpSourceBMacLSB specifies the 16 least significant bits
         (lsb) which when combined with the 32 most significant bits of the PBB
         source-bmac specified by svcPbbSrcBVplsMacAddr, forms the virtual
         backbone MAC associated with this SDP.

         The virtual backbone MAC is used as the source backbone MAC for
         traffic received on a PBB EPIPE spoke-SDP with the value of
         sdpBindUseSdpBMac set to 'true (1)' (i.e. redundant pseudo-wire) and
         forwarded into the B-VPLS domain.

         An 'inconsistentValue' error is returned if the value of
         sdpSourceBMacLSB is set to non-default value when the value of
         sdpControlPWVCId is set to default value."
    DEFVAL      { 0 }
    ::= { sdpInfoEntry 64 }

sdpControlPWVCId                 OBJECT-TYPE
    SYNTAX      TmnxVcIdOrNone
    MAX-ACCESS  read-create
    STATUS      current
    DESCRIPTION
        "The value of sdpControlPWVCId specifies the spoke-SDP VC identifier to
         be used as a control pseudo-wire to determine whether Shortest Path
         Bridging Module (SPBM) advertises the virtual backbone MAC.

         An 'inconsistentValue' error is returned if the value of
         sdpControlPWVCId is set to non-default value when the value of
         sdpSourceBMacLSB is set to default value."
    DEFVAL      { 0 }
    ::= { sdpInfoEntry 65 }

sdpControlPWIsActive             OBJECT-TYPE
    SYNTAX      TruthValue
    MAX-ACCESS  read-only
    STATUS      current
    DESCRIPTION
        "The value of sdpControlPWIsActive indicates whether control
         pseudo-wire is considered active on the Backbone Edge Bridge (BEB)."
    ::= { sdpInfoEntry 66 }

sdpTunnelFarEndInetAddressType   OBJECT-TYPE
    SYNTAX      InetAddressType
    MAX-ACCESS  read-create
    STATUS      current
    DESCRIPTION
        "The value of sdpTunnelFarEndInetAddressType specifies the address type
         of sdpTunnelFarEndInetAddress."
    DEFVAL      { unknown }
    ::= { sdpInfoEntry 67 }

sdpTunnelFarEndInetAddress       OBJECT-TYPE
    SYNTAX      InetAddress (SIZE (0|4|16))
    MAX-ACCESS  read-create
    STATUS      current
    DESCRIPTION
        "The value of sdpTunnelFarEndInetAddress specifies the IP address of
         the remote end of the transport tunnel for this SDP.

         This address must be different from sdpFarEndInetAddress.

         The value can only be changed while the admin status of the SDP is
         'down'."
    DEFVAL      { ''H }
    ::= { sdpInfoEntry 68 }

sdpGreAllowFragmentation         OBJECT-TYPE
    SYNTAX      TruthValue
    MAX-ACCESS  read-create
    STATUS      current
    DESCRIPTION
        "The value of sdpGreAllowFragmentation specifies whether to allow GRE
         encapsulated packets to be sent without setting the DF bit for this
         SDP.

         This object is valid only when sdpDelivery is set to 'gre'."
    DEFVAL      { false }
    ::= { sdpInfoEntry 69 }

sdpFpeLspId                      OBJECT-TYPE
    SYNTAX      Unsigned32
    MAX-ACCESS  read-only
    STATUS      current
    DESCRIPTION
        "The value of sdpFpeLspId indicates the identifier for the
         forward-path-extension LSP when the SDP is created using 'fpe'."
    ::= { sdpInfoEntry 70 }

sdpWeightedEcmpEnabled           OBJECT-TYPE
    SYNTAX      TruthValue
    MAX-ACCESS  read-create
    STATUS      current
    DESCRIPTION
        "The value of sdpWeightedEcmpEnabled specifies the packets forwarded to
         a set of ECMP tunnel next-hops which will be sprayed proportionally to
         the load balancing weights configured for each LSP."
    DEFVAL      { false }
    ::= { sdpInfoEntry 71 }

sdpOperTunnelFarEndInetAddrType  OBJECT-TYPE
    SYNTAX      InetAddressType
    MAX-ACCESS  read-only
    STATUS      current
    DESCRIPTION
        "The value of sdpOperTunnelFarEndInetAddrType indicates the address
         type of sdpOperTunnelFarEndInetAddr."
    ::= { sdpInfoEntry 72 }

sdpOperTunnelFarEndInetAddr      OBJECT-TYPE
    SYNTAX      InetAddress (SIZE (0|4|16))
    MAX-ACCESS  read-only
    STATUS      current
    DESCRIPTION
        "The value of sdpOperTunnelFarEndInetAddr indicates the operational IP
         address of the remote end of the transport tunnel for this SDP.

         If sdpTunnelFarEndInetAddress is not set, it will take the value from
         sdpFarEndInetAddress."
    ::= { sdpInfoEntry 73 }

sdpBindTable                     OBJECT-TYPE
    SYNTAX      SEQUENCE OF SdpBindEntry
    MAX-ACCESS  not-accessible
    STATUS      current
    DESCRIPTION
        "A table that contains SDP binding information."
    ::= { tmnxSdpObjs 4 }

sdpBindEntry                     OBJECT-TYPE
    SYNTAX      SdpBindEntry
    MAX-ACCESS  not-accessible
    STATUS      current
    DESCRIPTION
        "Information about a specific SDP binding."
    INDEX       {
        svcId,
        sdpBindId
    }
    ::= { sdpBindTable 1 }

SdpBindEntry                     ::= SEQUENCE
{
    sdpBindId                        SdpBindId,
    sdpBindRowStatus                 RowStatus,
    sdpBindAdminIngressLabel         Unsigned32,
    sdpBindAdminEgressLabel          Unsigned32,
    sdpBindOperIngressLabel          Unsigned32,
    sdpBindOperEgressLabel           Unsigned32,
    sdpBindAdminStatus               ServiceAdminStatus,
    sdpBindOperStatus                INTEGER,
    sdpBindLastMgmtChange            TimeStamp,
    sdpBindType                      INTEGER,
    sdpBindIngressMacFilterId        TConfigOrVsdFilterID,
    sdpBindIngressIpFilterId         TConfigOrVsdFilterID,
    sdpBindEgressMacFilterId         TFilterID,
    sdpBindEgressIpFilterId          TFilterID,
    sdpBindVpnId                     VpnId,
    sdpBindCustId                    TmnxCustId,
    sdpBindVcType                    SdpBindVcType,
    sdpBindVlanVcTag                 Unsigned32,
    sdpBindSplitHorizonGrp           ServObjName,
    sdpBindOperFlags                 BITS,
    sdpBindLastStatusChange          TimeStamp,
    sdpBindIesIfIndex                InterfaceIndexOrZero,
    sdpBindMacPinning                TmnxEnabledDisabled,
    sdpBindIngressIpv6FilterId       TConfigOrVsdFilterID,
    sdpBindEgressIpv6FilterId        TFilterID,
    sdpBindCollectAcctStats          TruthValue,
    sdpBindAccountingPolicyId        Unsigned32,
    sdpBindPwPeerStatusBits          BITS,
    sdpBindPeerVccvCvBits            BITS,
    sdpBindPeerVccvCcBits            BITS,
    sdpBindControlWordBit            TruthValue,
    sdpBindOperControlWord           TruthValue,
    sdpBindEndPoint                  ServObjName,
    sdpBindEndPointPrecedence        Unsigned32,
    sdpBindIsICB                     TruthValue,
    sdpBindPwFaultInetAddressType    InetAddressType,
    sdpBindPwFaultInetAddress        InetAddress,
    sdpBindClassFwdingOperState      TmnxOperState,
    sdpBindForceVlanVcForwarding     TruthValue,
    sdpBindAdminBandwidth            SdpBindBandwidth,
    sdpBindOperBandwidth             SdpBindBandwidth,
    sdpBindCreationOrigin            TmnxCreateOrigin,
    sdpBindDescription               TItemDescription,
    sdpBindSiteName                  TNamedItemOrEmpty,
    sdpBindHashLabel                 TruthValue,
    sdpBindIsaAaApplicationProfile   ServObjName,
    sdpBindStandbySigSlave           TruthValue,
    sdpBindHashLabelSignalCapability TruthValue,
    sdpBindIngressFlowspec           TruthValue,
    sdpBindCpmProtPolicyId           TCpmProtPolicyID,
    sdpBindCpmProtMonitorMac         TruthValue,
    sdpBindCpmProtEthCfmMonitorFlags BITS,
    sdpBindTransitIpPolicyId         TmnxBsxTransitIpPolicyIdOrZero,
    sdpBindPwStatusSignaling         TruthValue,
    sdpBindOperGrp                   TNamedItemOrEmpty,
    sdpBindMonitorOperGrp            TNamedItemOrEmpty,
    sdpBindOperHashLabel             TruthValue,
    sdpBindTransitPrefixPolicyId     TmnxBsxTransPrefPolicyIdOrZero,
    sdpBindAarpId                    TmnxBsxAarpIdOrZero,
    sdpBindIngressQoSNetworkPlcyId   TSdpIngressPolicyID,
    sdpBindEgressQoSNetworkPlcyId    TSdpEgressPolicyID,
    sdpBindIngressQoSFpRedirectQGrp  TNamedItemOrEmpty,
    sdpBindEgressQoSPortRedirectQGrp TNamedItemOrEmpty,
    sdpBindIngressQoSInstanceId      TQosQGrpInstanceIDorZero,
    sdpBindEgressQoSInstanceId       TQosQGrpInstanceIDorZero,
    sdpBindAarpServRefType           TmnxBsxAarpServiceRefType,
    sdpBindPwLocalStatusBits         BITS,
    sdpBindBlockOnPeerFault          TruthValue,
    sdpBindIngressIPv6Flowspec       TruthValue,
    sdpBindMirrorRemoteSource        TruthValue,
    sdpBindEtreeRootLeafTag          TruthValue,
    sdpBindCpmProtMonitorIP          TruthValue,
    sdpBindUseSdpBMac                TruthValue,
    sdpBindEtreeLeafAc               TruthValue,
    sdpBindBfdTemplateName           TNamedItemOrEmpty,
    sdpBindBfdEnable                 TruthValue,
    sdpBindBfdEncap                  TmnxBfdEncap,
    sdpBindForceQinqVcForwarding     TruthValue,
    sdpBindIngressVlanTranslation    INTEGER,
    sdpBindIngressVlanTranslationId  Integer32,
    sdpBindMinReqdSdpOperMtu         Integer32,
    sdpBindForceQinqVcFwding         INTEGER,
    sdpBindMulticastSource           TruthValue
}

sdpBindId                        OBJECT-TYPE
    SYNTAX      SdpBindId
    MAX-ACCESS  read-only
    STATUS      current
    DESCRIPTION
        "SDP Binding identifier."
    ::= { sdpBindEntry 1 }

sdpBindRowStatus                 OBJECT-TYPE
    SYNTAX      RowStatus
    MAX-ACCESS  read-create
    STATUS      current
    DESCRIPTION
        "This object specifies the status of this row. The only values
         supported during a set operation are 'createAndGo' and 'destroy'."
    ::= { sdpBindEntry 2 }

sdpBindAdminIngressLabel         OBJECT-TYPE
    SYNTAX      Unsigned32 (0 | 1..1048575)
    MAX-ACCESS  read-create
    STATUS      current
    DESCRIPTION
        "The static MPLS VC label used by the far-end device to send packets to
         this device in this service via this SDP.

         Normal range of (2048..18431) is used unless changed by the user."
    DEFVAL      { 0 }
    ::= { sdpBindEntry 3 }

sdpBindAdminEgressLabel          OBJECT-TYPE
    SYNTAX      Unsigned32 (0 | 16..1048575)
    MAX-ACCESS  read-create
    STATUS      current
    DESCRIPTION
        "The static MPLS VC label used by this device to send packets to the
         far-end device in this service via this SDP."
    DEFVAL      { 0 }
    ::= { sdpBindEntry 4 }

sdpBindOperIngressLabel          OBJECT-TYPE
    SYNTAX      Unsigned32 (0 | 1..1048575)
    MAX-ACCESS  read-only
    STATUS      current
    DESCRIPTION
        "The MPLS label used by the far-end device to send packets to this
         device in this service via this SDP. This label is either
         sdpBindAdminIngressLabel, if not null, or the one obtained via the
         SDP's signaling protocol."
    DEFVAL      { 0 }
    ::= { sdpBindEntry 5 }

sdpBindOperEgressLabel           OBJECT-TYPE
    SYNTAX      Unsigned32 (0 | 1..1048575)
    MAX-ACCESS  read-only
    STATUS      current
    DESCRIPTION
        "The MPLS label used by this device to send packets to the far-end
         device in this service via this SDP. This label is either
         sdpBindAdminEgressLabel, if not null, or the one obtained via the
         SDP's signaling protocol."
    DEFVAL      { 0 }
    ::= { sdpBindEntry 6 }

sdpBindAdminStatus               OBJECT-TYPE
    SYNTAX      ServiceAdminStatus
    MAX-ACCESS  read-create
    STATUS      current
    DESCRIPTION
        "The desired state of this Service-SDP binding."
    DEFVAL      { up }
    ::= { sdpBindEntry 7 }

sdpBindOperStatus                OBJECT-TYPE
    SYNTAX      INTEGER {
        up                 (1),
        noEgressLabel      (2),
        noIngressLabel     (3),
        noLabels           (4),
        down               (5),
        svcMtuMismatch     (6),
        sdpPathMtuTooSmall (7),
        sdpNotReady        (8),
        sdpDown            (9),
        sapDown            (10)
    }
    MAX-ACCESS  read-only
    STATUS      current
    DESCRIPTION
        "The value of sdpBindOperStatus indicates the operating status of
         this Service-SDP binding.
            'up'               The Service-SDP binding is operational.

            'noEgressLabel'    The ingress label is available but the
                               egress one is missing.

            'noIngressLabel'   The egress label is available but the
                               ingress one is not.

            'noLabels'         Both the ingress and the egress labels
                               are missing.

            'down'             The binding is administratively down.

            'svcMtuMismatch'   Both labels are available, but a service
                               MTU mismatch was detected between the local
                               and the far-end devices.

            'sdpPathMtuTooSmall' The operating path MTU of the corresponding
                                 SDP minus the size of the SDP Bind control
                                 word (if applicable) is smaller than the
                                 service MTU.

            'sdpNotReady'      The SDP's signaling session is down.

            'sdpDown'          The SDP is not operationally up.

            'sapDown'          The SAP associated with the service is down."
    ::= { sdpBindEntry 8 }

sdpBindLastMgmtChange            OBJECT-TYPE
    SYNTAX      TimeStamp
    MAX-ACCESS  read-only
    STATUS      current
    DESCRIPTION
        "The value of sysUpTime at the time of the most recent
         management-initiated change to this Service-SDP binding."
    ::= { sdpBindEntry 9 }

sdpBindType                      OBJECT-TYPE
    SYNTAX      INTEGER {
        spoke (1),
        mesh  (2)
    }
    MAX-ACCESS  read-create
    STATUS      current
    DESCRIPTION
        "This object specifies whether this Service SDP
         binding is a spoke or a mesh.  The value of this
         object must be specified when the row is created
         and cannot be changed while the row status is
         'active'."
    DEFVAL      { mesh }
    ::= { sdpBindEntry 10 }

sdpBindIngressMacFilterId        OBJECT-TYPE
    SYNTAX      TConfigOrVsdFilterID
    MAX-ACCESS  read-create
    STATUS      current
    DESCRIPTION
        "The row index in the tMacFilterTable corresponding to this ingress
         filter, or zero if no filter is specified."
    DEFVAL      { 0 }
    ::= { sdpBindEntry 11 }

sdpBindIngressIpFilterId         OBJECT-TYPE
    SYNTAX      TConfigOrVsdFilterID
    MAX-ACCESS  read-create
    STATUS      current
    DESCRIPTION
        "The row index in the tIPFilterTable corresponding to this ingress
         filter, or zero if no filter is specified."
    DEFVAL      { 0 }
    ::= { sdpBindEntry 12 }

sdpBindEgressMacFilterId         OBJECT-TYPE
    SYNTAX      TFilterID
    MAX-ACCESS  read-create
    STATUS      current
    DESCRIPTION
        "The row index in the tMacFilterTable corresponding to this egress
         filter, or zero if no filter is specified."
    DEFVAL      { 0 }
    ::= { sdpBindEntry 13 }

sdpBindEgressIpFilterId          OBJECT-TYPE
    SYNTAX      TFilterID
    MAX-ACCESS  read-create
    STATUS      current
    DESCRIPTION
        "The row index in the tIPFilterTable corresponding to this egress
         filter, or zero if no filter is specified."
    DEFVAL      { 0 }
    ::= { sdpBindEntry 14 }

sdpBindVpnId                     OBJECT-TYPE
    SYNTAX      VpnId
    MAX-ACCESS  read-only
    STATUS      current
    DESCRIPTION
        "The VPN ID of the associated service."
    ::= { sdpBindEntry 15 }

sdpBindCustId                    OBJECT-TYPE
    SYNTAX      TmnxCustId
    MAX-ACCESS  read-only
    STATUS      current
    DESCRIPTION
        "The Customer ID of the associated service."
    ::= { sdpBindEntry 16 }

sdpBindVcType                    OBJECT-TYPE
    SYNTAX      SdpBindVcType
    MAX-ACCESS  read-create
    STATUS      current
    DESCRIPTION
        "The value of sdpBindVcType is an enumerated integer that specifies the
         type of virtual circuit (VC) associated with the SDP binding.

         The value 'vpls' is no longer supported."
    ::= { sdpBindEntry 17 }

sdpBindVlanVcTag                 OBJECT-TYPE
    SYNTAX      Unsigned32 (0..4095)
    MAX-ACCESS  read-create
    STATUS      current
    DESCRIPTION
        ""
    DEFVAL      { '0fff'H }
    ::= { sdpBindEntry 18 }

sdpBindSplitHorizonGrp           OBJECT-TYPE
    SYNTAX      ServObjName
    MAX-ACCESS  read-create
    STATUS      current
    DESCRIPTION
        "This value of the object sdpBindSplitHorizonGrp specifies the name of
         the split-horizon group where the spoke SDP Bind belongs to. This
         object can be set only at the time the row is created and is mutually
         exclusive with sdpBindMulticastSource. Per default a spoke SDP Bind
         does not belong to any split-horizon group. The name specified must
         correspond to an existing split-horizon group in the TLS service where
         this spoke SDP Bind is defined."
    DEFVAL      { "" }
    ::= { sdpBindEntry 19 }

sdpBindOperFlags                 OBJECT-TYPE
    SYNTAX      BITS {
        sdpBindAdminDown        (0),
        svcAdminDown            (1),
        stitchingSvcTxDown      (2),
        sdpOperDown             (3),
        sdpPathMtuTooSmall      (4),
        noIngressVcLabel        (5),
        noEgressVcLabel         (6),
        svcMtuMismatch          (7),
        vcTypeMismatch          (8),
        relearnLimitExceeded    (9),
        iesIfAdminDown          (10),
        releasedIngressVcLabel  (11),
        labelsExhausted         (12),
        svcParamMismatch        (13),
        insufficientBandwidth   (14),
        pwPeerFaultStatusBits   (15),
        meshSdpDown             (16),
        notManagedByMcRing      (17),
        outOfResource           (18),
        mhStandby               (19),
        oamDownMepFault         (20),
        oamUpMepFault           (21),
        standbySigSlaveTxDown   (22),
        operGrpDown             (23),
        withdrawnIngressVcLabel (24),
        vplsPmsiDown            (25),
        recProtSrcMac           (26),
        peerFaultStatusTxDown   (27),
        evpnRouteConflict       (28),
        adminLocked             (29),
        evpnP2mpConflict        (30),
        labelStackLimitExceeded (31)
    }
    MAX-ACCESS  read-only
    STATUS      current
    DESCRIPTION
        "This object indicates all the conditions that affect the operating
         status of this SDP Bind.

         The bit values are as follows:

         sdpBindAdminDown        (0)  - SDP Bind is admin down.
         svcAdminDown            (1)  - Service is admin down.
         stitchingSvcTxDown      (2)  - PW-PORT FPE stitching svc
                                     transmit is down.
         sdpOperDown             (3)  - SDP is oper down.
         sdpPathMtuTooSmall      (4)  - SDP's path MTU minus SDP Bind control
                                     word size is less than Service MTU.
         noIngressVcLabel        (5)  - No ingress VC label.
         noEgressVcLabel         (6)  - No egress VC label.
         svcMtuMismatch          (7)  - Service MTU mismatch with the
                                     remote PE.
         vcTypeMismatch          (8)  - VC type mismatch with the remote PE.
         relearnLimitExceeded    (9)  - MAC relearn limit was exceeded
                                     (TLS only).
         iesIfAdminDown         (10)  - IP interface is admin down
                                     (IES and VPRN only).
         releasedIngressVcLabel (11)  - Peer released our ingress VC label.
         labelsExhausted        (12)  - Label Manager has ran out of labels.
         svcParamMismatch       (13)  - Service-specific parameter mismatch.
         insufficientBandwidth  (14)  - Insufficient bandwidth to allocate
                                     to SDP binding.
         pwPeerFaultStatusBits  (15)  - Received PW fault status bits from
                                     peer.
         meshSdpDown            (16)  - Mesh SDP Down.
         notManagedByMcRing     (17)  - Not managed by mc-ring.
         outOfResource          (18)  - Such as memory.
         mhStandby              (19)  - Standby due to BGP.
                                     multi-home protocol.
         oamDownMepFault        (20)  - ETH-CFM down MEP fault detected.
         oamUpMepFault          (21)  - ETH-CFM up MEP fault detected.
         standbySigSlaveTxDown  (22)  - Transmit is down for
                                     standby-sig-spoke.
         operGrpDown            (23)  - Operational group is down.
         withdrawnIngressVcLabel(24)  - Withdrawn due to incompatibility.
         vplsPmsiDown           (25)  - provider-tunnel down.
         recProtSrcMac          (26)  - Received a packet with a
                                     protected source MAC.
         peerFaultStatusTxDown  (27)  - Transmit is down because
                                     block-on-peer-fault is
                                     enabled and received PW
                                     faults status from peer.
         evpnRouteConflict      (28)  - EVPN has route to.
         adminLocked            (29)  - SDP Bind is admin-locked.
         evpnP2mpConfict        (30)  - Conflict with evpn p2mp.
         labelStackLimitExceeded(31)  - label stack overhead exceeding the
                                     egress IOM limitation."
    ::= { sdpBindEntry 20 }

sdpBindLastStatusChange          OBJECT-TYPE
    SYNTAX      TimeStamp
    MAX-ACCESS  read-only
    STATUS      current
    DESCRIPTION
        "The value of the object sdpBindLastStatusChange indicates the value of
         sysUpTime at the time of the most recent operating status change to
         this SDP Bind."
    ::= { sdpBindEntry 21 }

sdpBindIesIfIndex                OBJECT-TYPE
    SYNTAX      InterfaceIndexOrZero
    MAX-ACCESS  read-create
    STATUS      current
    DESCRIPTION
        "When this SDP Bind is defined on an IES service and the value of
         sdpBindType is 'spoke', this object specifies the index of the
         associated IES interface. The value of this object can be set only
         when the row is created and cannot be changed while the row status is
         'active'. This object is otherwise not significant and should have the
         value zero."
    ::= { sdpBindEntry 22 }

sdpBindMacPinning                OBJECT-TYPE
    SYNTAX      TmnxEnabledDisabled
    MAX-ACCESS  read-create
    STATUS      current
    DESCRIPTION
        "The value of the object sdpBindMacPinning specifies whether or not MAC
         address pinning is active on this SDP bind (mesh or spoke). Setting
         the value to enable disables relearning of MAC addresses on other SAPs
         or SDPs within the same VPLS; the MAC address will hence remain
         attached to the SDP Bind for the duration of its age-timer. This
         object has effect only for MAC addresses learned via the normal MAC
         learning process, and not for entries learned via DHCP. The value will
         be set by default to disabled. However for a spoke SDP that belongs to
         a residential SHG, the value is set to enabled by the system, and
         cannot be altered by the operator. This object applies to spoke-SDP
         associated with the service with svcType set to 'tls'."
    ::= { sdpBindEntry 23 }

sdpBindIngressIpv6FilterId       OBJECT-TYPE
    SYNTAX      TConfigOrVsdFilterID
    MAX-ACCESS  read-create
    STATUS      current
    DESCRIPTION
        "The value of the object sdpBindIngressIpv6FilterId specifies the row
         index in the tIPv6FilterTable corresponding to this ingress ipv6
         filter, or zero if no ipv6 filter is specified."
    DEFVAL      { 0 }
    ::= { sdpBindEntry 24 }

sdpBindEgressIpv6FilterId        OBJECT-TYPE
    SYNTAX      TFilterID
    MAX-ACCESS  read-create
    STATUS      current
    DESCRIPTION
        "The value of the object sdpBindEgressIpv6FilterId specifies the row
         index in the tIPv6FilterTable corresponding to this egress ipv6
         filter, or zero if no ipv6 filter is specified."
    DEFVAL      { 0 }
    ::= { sdpBindEntry 25 }

sdpBindCollectAcctStats          OBJECT-TYPE
    SYNTAX      TruthValue
    MAX-ACCESS  read-create
    STATUS      current
    DESCRIPTION
        "The value of the object sdpBindCollectAcctStats specifies whether the
         agent collects accounting statistics for this SDP bind. When the value
         is 'true' the agent collects accounting statistics on this SDP bind."
    DEFVAL      { false }
    ::= { sdpBindEntry 26 }

sdpBindAccountingPolicyId        OBJECT-TYPE
    SYNTAX      Unsigned32 (0..99)
    MAX-ACCESS  read-create
    STATUS      current
    DESCRIPTION
        "The value of sdpBindAccountingPolicyId specifies the policy to use to
         collect accounting statistics on this SDP bind. The value zero
         indicates that the agent should use the default accounting policy, if
         one exists."
    DEFVAL      { 0 }
    ::= { sdpBindEntry 27 }

sdpBindPwPeerStatusBits          OBJECT-TYPE
    SYNTAX      BITS {
        pwNotForwarding (0),
        lacIngressFault (1),
        lacEgresssFault (2),
        psnIngressFault (3),
        psnEgressFault  (4),
        pwFwdingStandby (5)
    }
    MAX-ACCESS  read-only
    STATUS      current
    DESCRIPTION
        "sdpBindPwPeerStatusBits indicates the bits set by the LDP
         peer when there is a fault on its side of the pseudowire.
         LAC failures occur on the SAP that has been configured on
         the PIPE service, PSN bits are set by SDP-binding failures
         on the PIPE service.  The pwNotForwarding bit is set when
         none of the above failures apply, such as an MTU mismatch
         failure.  This value is only applicable if the peer is
         using the pseudowire status signalling method to indicate
         faults."
    ::= { sdpBindEntry 28 }

sdpBindPeerVccvCvBits            OBJECT-TYPE
    SYNTAX      BITS {
        icmpPing                       (0),
        lspPing                        (1),
        bfdFaultDetection              (2),
        bfdFaultDetectionAndSignalling (3)
    }
    MAX-ACCESS  read-only
    STATUS      current
    DESCRIPTION
        "sdpBindPeerVccvCvBits indicates the CV type bits set by the
         LDP peer if it supports VCCV (Virtual Circuit Connection
         Verification) on a pseudowire.  If the peer does not send
         VCCV information, or does not support it, the bits will
         be set to 0."
    ::= { sdpBindEntry 29 }

sdpBindPeerVccvCcBits            OBJECT-TYPE
    SYNTAX      BITS {
        pwe3ControlWord          (0),
        mplsRouterAlertLabel     (1),
        mplsPwDemultiplexorLabel (2)
    }
    MAX-ACCESS  read-only
    STATUS      current
    DESCRIPTION
        "sdpBindPeerVccvCcBits indicates the CC type bits set by the
         LDP peer if it supports VCCV (Virtual Circuit Connection
         Verification) on a pseudowire.  If the peer does not send
         VCCV information, or does not support it, the bits will
         all be 0."
    ::= { sdpBindEntry 30 }

sdpBindControlWordBit            OBJECT-TYPE
    SYNTAX      TruthValue
    MAX-ACCESS  read-create
    STATUS      current
    DESCRIPTION
        "sdpBindControlWordBit specifies whether the use of the 'ControlWord'
         is preferred or not. The value of sdpBindControlWordBit is exchanged
         with LDP peer during pseudowire negotiation time. The default value is
         determined by sdpBindVcType. sdpBindVcType of atmSdu and frDlci must
         have default value of 'true'. Other values of sdpBindVcType must have
         default value of 'false'."
    ::= { sdpBindEntry 31 }

sdpBindOperControlWord           OBJECT-TYPE
    SYNTAX      TruthValue
    MAX-ACCESS  read-only
    STATUS      current
    DESCRIPTION
        "sdpBindOperControlWord indicates whether the 'ControlWord'
         is used or not. The value of sdpBindOperControlWord is
         negotiated with the LDP peer.  When both the local and the
         peer prefer the use of the 'ControlWord', sdpBindOperControlWord
         has the value of 'true'."
    ::= { sdpBindEntry 32 }

sdpBindEndPoint                  OBJECT-TYPE
    SYNTAX      ServObjName
    MAX-ACCESS  read-create
    STATUS      current
    DESCRIPTION
        "sdpBindEndPoint specifies the service endpoint to which this SDP bind
         is attached. The svcId of the SDP bind MUST match the svcId of the
         service endpoint."
    DEFVAL      { "" }
    ::= { sdpBindEntry 33 }

sdpBindEndPointPrecedence        OBJECT-TYPE
    SYNTAX      Unsigned32 (0..4)
    MAX-ACCESS  read-create
    STATUS      current
    DESCRIPTION
        "sdpBindEndPointPrecedence specifies the precedence of this SDP bind
         when there are multiple SDP binds attached to one service endpoint.
         The value 0 can only be assigned to one SDP bind, making it the
         primary SDP bind. When an SDP bind goes down, the next highest
         precedence SDP bind begins forwarding traffic."
    DEFVAL      { 4 }
    ::= { sdpBindEntry 34 }

sdpBindIsICB                     OBJECT-TYPE
    SYNTAX      TruthValue
    MAX-ACCESS  read-create
    STATUS      current
    DESCRIPTION
        "sdpBindIsICB specifies whether this sdpBind is an inter-chassis backup
         SDP bind."
    DEFVAL      { false }
    ::= { sdpBindEntry 35 }

sdpBindPwFaultInetAddressType    OBJECT-TYPE
    SYNTAX      InetAddressType
    MAX-ACCESS  read-only
    STATUS      current
    DESCRIPTION
        "The value of the object sdpBindPwFaultInetAddressType indicates the
         address type of sdpBindPwFaultInetAddress."
    ::= { sdpBindEntry 36 }

sdpBindPwFaultInetAddress        OBJECT-TYPE
    SYNTAX      InetAddress (SIZE (0|4|16))
    MAX-ACCESS  read-only
    STATUS      current
    DESCRIPTION
        "The value of sdpBindPwFaultInetAddress indicates the IP
         address that was included in the pseudowire status
         message sent by the LDP peer.  This value is only
         applicable if the peer is using the pseudowire status
         signalling method to indicate faults."
    ::= { sdpBindEntry 37 }

sdpBindClassFwdingOperState      OBJECT-TYPE
    SYNTAX      TmnxOperState
    MAX-ACCESS  read-only
    STATUS      current
    DESCRIPTION
        "The value of sdpBindClassFwdingOperState indicates the operational
         state of forwarding class based forwarding on this sdpBind.

         When the SDP this sdpBind is bound to has sdpClassFwdingEnabled set to
         'false', the value of sdpBindClassFwdingOperState is 'outOfService'.

         When the SDP this sdpBind is bound to has sdpClassFwdingEnabled set to
         'true' and the svcType of the service this sdpBind is defined on is
         'tls', 'vprn', or 'ies', the value of sdpBindClassFwdingOperState is
         'inService'. If the service has svcVcSwitching set to 'true', the
         value of sdpBindClassFwdingOperState is 'inService'

         When the SDP this sdpBind is bound to has sdpClassFwdingEnabled set to
         'true' and the svcType of the service this sdpBind is defined on is
         'epipe', 'apipe', 'fpipe', or 'ipipe' with no SAP defined on the
         service, the value of sdpBindClassFwdingOperState is 'unknown'. If the
         service has a SAP with a NULL sapIngressSharedQueuePolicy, the value
         of sdpBindClassFwdingOperState is 'outOfService'. If the service has a
         SAP with a non-NULL sapIngressSharedQueuePolicy, the value of
         sdpBindClassFwdingOperState is 'inService'."
    ::= { sdpBindEntry 38 }

sdpBindForceVlanVcForwarding     OBJECT-TYPE
    SYNTAX      TruthValue
    MAX-ACCESS  read-create
    STATUS      current
    DESCRIPTION
        "The value of sdpBindForceVlanVcForwarding specifies whether or not
         vc-vlan-type forwarding is forced in the datapath for the sdp which
         have sdpBindVcType set to 'ether'.  When set to 'true'
         vc-vlan-type forwarding is forced.

         An 'inconsistentValue' error is returned when an attempt is made to
         set the value of sdpBindForceVlanVcForwarding to 'true' and
         sdpBindVcType is not set to 'ether'."
    DEFVAL      { false }
    ::= { sdpBindEntry 39 }

sdpBindAdminBandwidth            OBJECT-TYPE
    SYNTAX      SdpBindBandwidth
    UNITS       "kilobps"
    MAX-ACCESS  read-create
    STATUS      current
    DESCRIPTION
        "The value of the object sdpBindAdminBandwidth specifies the bandwidth
         that needs to be reserved for this SDP binding in kilobits per second.
         The SdpBindBandwidth object only applies to the SDP bindings under the
         epipe(1), apipe(7), fpipe(8), ipipe(9) and cpipe(10) services."
    DEFVAL      { 0 }
    ::= { sdpBindEntry 40 }

sdpBindOperBandwidth             OBJECT-TYPE
    SYNTAX      SdpBindBandwidth
    UNITS       "kilobps"
    MAX-ACCESS  read-only
    STATUS      current
    DESCRIPTION
        "The value of the object sdpBindOperBandwidth indicates the bandwidth
         that has been reserved for this SDP binding in kilobits per second.
         The value 0 indicates that SDP doesn't have bandwidth to satisfy the
         bandwidth requirement of this SDP binding. The sdpBindOperBandwidth
         object only applies to the SDP bindings under the epipe(1), apipe(7),
         fpipe(8), ipipe(9) and cpipe(10) services."
    ::= { sdpBindEntry 41 }

sdpBindCreationOrigin            OBJECT-TYPE
    SYNTAX      TmnxCreateOrigin
    MAX-ACCESS  read-only
    STATUS      current
    DESCRIPTION
        "The value of sdpBindCreationOrigin indicates the protocol or mechanism
         which created this SDP binding."
    ::= { sdpBindEntry 42 }

sdpBindDescription               OBJECT-TYPE
    SYNTAX      TItemDescription
    MAX-ACCESS  read-create
    STATUS      current
    DESCRIPTION
        "The value of sdpBindDescription specifies a user-provided description
         for the SDP Bind."
    DEFVAL      { "" }
    ::= { sdpBindEntry 43 }

sdpBindSiteName                  OBJECT-TYPE
    SYNTAX      TNamedItemOrEmpty
    MAX-ACCESS  read-only
    STATUS      current
    DESCRIPTION
        "The value of sdpBindSiteName indicates the site-name associated with
         this SDP Bind."
    ::= { sdpBindEntry 44 }

sdpBindHashLabel                 OBJECT-TYPE
    SYNTAX      TruthValue
    MAX-ACCESS  read-create
    STATUS      current
    DESCRIPTION
        "The value of sdpBindHashLabel specifies whether the use of hash label
         is enabled or not on this SDP Bind."
    DEFVAL      { false }
    ::= { sdpBindEntry 45 }

sdpBindIsaAaApplicationProfile   OBJECT-TYPE
    SYNTAX      ServObjName
    MAX-ACCESS  read-create
    STATUS      current
    DESCRIPTION
        "The value of sdpBindIsaAaApplicationProfile specifies the ISA-AA
         application profile for this sdp. The specified application profile
         needs to exist in the TIMETRA-BSX-NG-MIB::tmnxBsxAppProfTable."
    DEFVAL      { "" }
    ::= { sdpBindEntry 46 }

sdpBindStandbySigSlave           OBJECT-TYPE
    SYNTAX      TruthValue
    MAX-ACCESS  read-create
    STATUS      current
    DESCRIPTION
        "The value of sdpBindStandbySigSlave specifies whether transmission of
         the spoke will be blocked when the spoke receives standby status
         notification from its peer."
    DEFVAL      { false }
    ::= { sdpBindEntry 47 }

sdpBindHashLabelSignalCapability OBJECT-TYPE
    SYNTAX      TruthValue
    MAX-ACCESS  read-create
    STATUS      current
    DESCRIPTION
        "The value of sdpBindHashLabelSignalCapability specifies whether to
         signal the hash label capability to the remote PE.

         The default value is 'false' and cannot be changed unless
         sdpBindHashLabel is set to 'true'."
    DEFVAL      { false }
    ::= { sdpBindEntry 48 }

sdpBindIngressFlowspec           OBJECT-TYPE
    SYNTAX      TruthValue
    MAX-ACCESS  read-create
    STATUS      obsolete
    DESCRIPTION
        "The value of sdpBindIngressFlowspec specifies whether ingress IPv4
         Flowspec is enabled for this sdp."
    DEFVAL      { false }
    ::= { sdpBindEntry 49 }

sdpBindCpmProtPolicyId           OBJECT-TYPE
    SYNTAX      TCpmProtPolicyID
    MAX-ACCESS  read-create
    STATUS      current
    DESCRIPTION
        "The value of sdpBindCpmProtPolicyId specifies the CPM protection
         policy for this SDP binding.

         Zero specifies that no CPM protection policy is associated with this
         SDP binding.  A non-zero value must be the index of an active
         tmnxCpmProtPolTable row.

         If the SDP binding can support Eth-CFM MEPs or MIPs, the default CPM
         protection policy is 255 (which is the default CPU protection policy
         for a network interface).  Zero is not supported in this case.

         If the SDP binding cannot support Eth-CFM MEPs or MIPs, the default CPM
         protection policy is zero.  Changing the CPM protection policy value
         is not supported in this case."
    DEFVAL      { 255 }
    ::= { sdpBindEntry 50 }

sdpBindCpmProtMonitorMac         OBJECT-TYPE
    SYNTAX      TruthValue
    MAX-ACCESS  read-create
    STATUS      current
    DESCRIPTION
        "The value of sdpBindCpmProtMonitorMac specifies whether the
         tmnxCpmProtPolPerSrcRateLimit of the CPM protection policy (as
         specified by sdpBindCpmProtPolicyId) must be applied.

         If the value of sdpBindCpmProtMonitorMac is 'true', the per-source
         rate limit must be applied.

         If the value of sdpBindCpmProtPolicyId is zero, the value of
         sdpBindCpmProtMonitorMac is irrelevant and will be ignored.

         At most one of sdpBindCpmProtMonitorMac and the
         sdpBindCpmProtEthCfmMonitorFlags option 'ethCfmMonitor(0)' can be
         enabled for this SDP binding."
    DEFVAL      { false }
    ::= { sdpBindEntry 51 }

sdpBindCpmProtEthCfmMonitorFlags OBJECT-TYPE
    SYNTAX      BITS {
        ethCfmMonitor                    (0),
        ethCfmMonitorAggregate           (1),
        ethCfmMonitorCommittedAccessRate (2)
    }
    MAX-ACCESS  read-create
    STATUS      current
    DESCRIPTION
        "The value of sdpBindCpmProtEthCfmMonitorFlags specifies whether or not
         to apply rate limiting (using the tmnxCpmProtEthCfmPolTable
         configuration) to Ethernet Connectivity Fault Management (Eth-CFM)
         packets served by the SDP binding.  Two associated options are also
         specified.

         Five combinations of flag values are supported, as shown in the
         following table.

         Flag                                    Value (0=Disabled, 1=Enabled)
         -------------------------------------   -----------------------------
         'ethCfmMonitor(0)'                      0   0   0   0   1   1   1   1
         'ethCfmMonitorAggregate(1)'             0   0   1   1   0   0   1   1
         'ethCfmMonitorCommittedAccessRate(2)'   0   1   0   1   0   1   0   1
         -------------------------------------   -----------------------------
         Supported Combination?                  Y   N   N   N   Y   Y   Y   Y

         If 'ethCfmMonitor(0)' is disabled, Eth-CFM rate limiting is disabled
         on this SDP binding.

         If 'ethCfmMonitor(0)' is enabled, Eth-CFM rate limiting is enabled on
         this SDP binding.  Excess packets are discarded.  The configured
         information used to perform the Eth-CFM rate limiting (e.g. the rate
         limit(s)) resides in the tmnxCpmProtEthCfmPolTable row(s) indexed by
         the SDP binding's sdpBindCpmProtPolicyId.

         At most one of the following options can be enabled on this SAP:
           1.  sdpBindCpmProtMonitorMac,
           2.  The sdpBindCpmProtEthCfmMonitorFlags option 'ethCfmMonitor(0)',
           3.  sdpBindCpmProtMonitorIP.

         The flags 'ethCfmMonitorAggregate(1)' and
         'ethCfmMonitorCommittedAccessRate(2)' adjust the behavior of Eth-CFM
         rate limiting.  Therefore, they are only significant if Eth-CFM rate
         limiting is enabled (i.e. when 'ethCfmMonitor(0)' is enabled).  The
         remainder of this DESCRIPTION assumes 'ethCfmMonitor(0)' is enabled.

         If 'ethCfmMonitorAggregate(1)' is disabled, the applicable Eth-CFM
         packet rate limit (tmnxCpmProtEthCfmPolRateLimit) applies per peer
         (i.e. on a source MAC address basis).  For example, if the SDP
         binding's rate limit for all Eth-CFM packets is 100 packets/sec, and
         two peers are served by the SDP binding, then 100 Eth-CFM packets/sec
         from each peer is within the limit.

         If 'ethCfmMonitorAggregate(1)' is enabled, the applicable Eth-CFM
         packet rate limit (tmnxCpmProtEthCfmPolRateLimit) applies to the
         aggregated traffic flow.  For example, if the SDP binding's rate limit
         for all Eth-CFM packets is 100 packets/sec, and two peers are served by
         this SDP binding, then the combined rate of the two peers cannot exceed
         100 packets/sec.

         'ethCfmMonitorCommittedAccessRate(2)' controls the interaction
         between two features:  Eth-CFM rate limiting, and overall rate limiting
         (as configured using tmnxCpmProtPolOverallRateLimit).

         If 'ethCfmMonitorCommittedAccessRate(2)' is disabled, an Eth-CFM
         packet is subjected to two rate limits, in the following order.
         a) The applicable tmnxCpmProtEthCfmPolRateLimit is applied, as
            described above.  If the packet exceeds the limit, it is discarded.
            Otherwise...
         b) The SDP binding's tmnxCpmProtPolOverallRateLimit (which is applied
            to Eth-CFM packets, and the other rate limited packet types) is
            applied.

         If 'ethCfmMonitorCommittedAccessRate(2)' is enabled, an Eth-CFM packet
         is subjected to one rate limit:  the applicable
         tmnxCpmProtEthCfmPolRateLimit, as described above.  Eth-CFM packets
         are neither counted nor discarded when performing the
         tmnxCpmProtPolOverallRateLimit rate limiting."
    DEFVAL      { {} }
    ::= { sdpBindEntry 52 }

sdpBindTransitIpPolicyId         OBJECT-TYPE
    SYNTAX      TmnxBsxTransitIpPolicyIdOrZero
    MAX-ACCESS  read-create
    STATUS      current
    DESCRIPTION
        "The value of sdpBindTransitIpPolicyId specifies the transit IP policy
         to be associated with this SDP binding. The value must either be '0'
         indicating an invalid transit IP policy or the specified transit IP
         policy needs to exist in the
         TIMETRA-BSX-NG-MIB::tmnxBsxTransitIpPolicyTable.

         At most one of sdpBindTransitIpPolicyId and
         sdpBindTransitPrefixPolicyId can be non-zero."
    DEFVAL      { 0 }
    ::= { sdpBindEntry 53 }

sdpBindPwStatusSignaling         OBJECT-TYPE
    SYNTAX      TruthValue
    MAX-ACCESS  read-create
    STATUS      current
    DESCRIPTION
        "The value of sdpBindPwStatusSignaling specified whether this SDP
         binding supports pseudowire status signaling.

         Default value depends on the type of service:
         - For VPLS services it is 'true' and configurable.
         - For EPIPE services it is 'true' and configurable.
         - For all other VLL services it is 'true' but not configurable.
         - For Mirror services it is 'true' but not configurable.
         - For IES/VPRN services it is 'true' but not configurable.
         - For all other services it is 'false' and not configurable.

         An 'inconsistentValue' error is returned when an attempt is made to
         change this value for a SDP binding that is not configurable."
    ::= { sdpBindEntry 54 }

sdpBindOperGrp                   OBJECT-TYPE
    SYNTAX      TNamedItemOrEmpty
    MAX-ACCESS  read-create
    STATUS      current
    DESCRIPTION
        "The value of the sdpBindOperGrp specifies the Operational-Group
         identifier associated with this SDP Bind.

         An 'inconsistentValue' error is returned when both sdpBindOperGrp and
         sdpBindMonitorOperGrp are set together and at least one of them to a
         non-default value."
    DEFVAL      { "" }
    ::= { sdpBindEntry 55 }

sdpBindMonitorOperGrp            OBJECT-TYPE
    SYNTAX      TNamedItemOrEmpty
    MAX-ACCESS  read-create
    STATUS      current
    DESCRIPTION
        "The value of the sdpBindMonitorOperGrp specifies the Operational-Group
         identifier which will affect the state of this SDP Bind.

         An 'inconsistentValue' error is returned when both sdpBindOperGrp and
         sdpBindMonitorOperGrp are set together and at least one of them to a
         non-default value."
    DEFVAL      { "" }
    ::= { sdpBindEntry 56 }

sdpBindOperHashLabel             OBJECT-TYPE
    SYNTAX      TruthValue
    MAX-ACCESS  read-only
    STATUS      current
    DESCRIPTION
        "The value of sdpBindOperHashLabel indicates the negotiated value of
         hash label that is used on this SDP binding.

         If the value of sdpBindHashLabel is set to 'true' but the value of
         sdpBindHashLabelSignalCapability is set to 'false' then
         sdpBindOperHashLabel will be 'true'.

         If the value of sdpBindHashLabelSignalCapability set to 'true' then
         the value of sdpBindOperHashLabel is 'true' if peer capability is
         'true' and the 7xxx SR router hardware supports this capability.

         If the service has svcVcSwitching set to 'true', the value of
         sdpBindOperHashLabel will be 'true' if peer capability is 'true' and
         the 7xxx SR router hardware supports this capability."
    ::= { sdpBindEntry 57 }

sdpBindTransitPrefixPolicyId     OBJECT-TYPE
    SYNTAX      TmnxBsxTransPrefPolicyIdOrZero
    MAX-ACCESS  read-create
    STATUS      current
    DESCRIPTION
        "The value of sdpBindTransitPrefixPolicyId specifies the transit prefix
         policy to be associated with this SDP binding. The value must either
         be '0' indicating an invalid transit prefix policy or the specified
         transit prefix policy needs to exist in the
         TIMETRA-BSX-NG-MIB::tmnxBsxTransPrefPolicyTable.

         At most one of sdpBindTransitIpPolicyId and
         sdpBindTransitPrefixPolicyId can be non-zero."
    DEFVAL      { 0 }
    ::= { sdpBindEntry 58 }

sdpBindAarpId                    OBJECT-TYPE
    SYNTAX      TmnxBsxAarpIdOrZero
    MAX-ACCESS  read-create
    STATUS      current
    DESCRIPTION
        "The value of sdpBindAarpId specifies the AA Redundancy Protocol (AARP)
         instance associated with this SDP binding. If set to 0, no AARP
         instance is associated with this SDP binding."
    DEFVAL      { 0 }
    ::= { sdpBindEntry 59 }

sdpBindIngressQoSNetworkPlcyId   OBJECT-TYPE
    SYNTAX      TSdpIngressPolicyID
    MAX-ACCESS  read-create
    STATUS      current
    DESCRIPTION
        "The value of the sdpBindIngressQoSNetworkPlcyId specifies the ingress
         QoS network policy applied to this SDP binding."
    DEFVAL      { 0 }
    ::= { sdpBindEntry 60 }

sdpBindEgressQoSNetworkPlcyId    OBJECT-TYPE
    SYNTAX      TSdpEgressPolicyID
    MAX-ACCESS  read-create
    STATUS      current
    DESCRIPTION
        "The value of the sdpBindEgressQoSNetworkPlcyId specifies the egress
         QoS network policy applied to this SDP binding."
    DEFVAL      { 0 }
    ::= { sdpBindEntry 61 }

sdpBindIngressQoSFpRedirectQGrp  OBJECT-TYPE
    SYNTAX      TNamedItemOrEmpty
    MAX-ACCESS  read-create
    STATUS      current
    DESCRIPTION
        "The value of sdpBindIngressQoSFpRedirectQGrp specifies the
         forwarding-plane queue group Policy for this SDP binding.

         This object must be set along with sdpBindIngressQoSNetworkPlcyId
         object."
    DEFVAL      { "" }
    ::= { sdpBindEntry 62 }

sdpBindEgressQoSPortRedirectQGrp OBJECT-TYPE
    SYNTAX      TNamedItemOrEmpty
    MAX-ACCESS  read-create
    STATUS      current
    DESCRIPTION
        "The value of sdpBindEgressQoSPortRedirectQGrp specifies the
         forwarding-plane queue group Policy for this SDP binding.

         This object must be set along with sdpBindEgressQoSNetworkPlcyId
         object."
    DEFVAL      { "" }
    ::= { sdpBindEntry 63 }

sdpBindIngressQoSInstanceId      OBJECT-TYPE
    SYNTAX      TQosQGrpInstanceIDorZero
    MAX-ACCESS  read-create
    STATUS      current
    DESCRIPTION
        "The value of sdpBindIngressQoSInstanceId specifies the instance of the
         forwarding-plane ingress Queue Group for this SDP binding."
    DEFVAL      { 0 }
    ::= { sdpBindEntry 64 }

sdpBindEgressQoSInstanceId       OBJECT-TYPE
    SYNTAX      TQosQGrpInstanceIDorZero
    MAX-ACCESS  read-create
    STATUS      current
    DESCRIPTION
        "The value of sdpBindEgressQoSInstanceId specifies the instance of the
         forwarding-plane egress Queue Group for this SDP binding."
    DEFVAL      { 0 }
    ::= { sdpBindEntry 65 }

sdpBindAarpServRefType           OBJECT-TYPE
    SYNTAX      TmnxBsxAarpServiceRefType
    MAX-ACCESS  read-create
    STATUS      current
    DESCRIPTION
        "The value of sdpBindAarpServRefType specifies the role of the Spoke
         SDP referenced by the Redundancy Protocol (AARP) instance identified
         by sdpBindAarpId. If sdpBindAarpId is the invalid AARP instance '0',
         then the service reference type is 'none(0)'."
    DEFVAL      { none }
    ::= { sdpBindEntry 66 }

sdpBindPwLocalStatusBits         OBJECT-TYPE
    SYNTAX      BITS {
        pwNotForwarding (0),
        lacIngressFault (1),
        lacEgresssFault (2),
        psnIngressFault (3),
        psnEgressFault  (4),
        pwFwdingStandby (5)
    }
    MAX-ACCESS  read-only
    STATUS      current
    DESCRIPTION
        "sdpBindPwLocalStatusBits indicates the bits set locally
         when there is a fault.
         LAC failures occur on the SAP that has been configured on
         the PIPE service, PSN bits are set by SDP-binding failures
         on the PIPE service.  The pwNotForwarding bit is set when
         none of the above failures apply, such as an MTU mismatch
         failure.  This value is sent to the peer via pseudowire
         status signalling method to indicate faults only if
         sdpBindPwStatusSignaling is set to true."
    ::= { sdpBindEntry 67 }

sdpBindBlockOnPeerFault          OBJECT-TYPE
    SYNTAX      TruthValue
    MAX-ACCESS  read-create
    STATUS      current
    DESCRIPTION
        "The sdpBindBlockOnPeerFault specifies whether to block the user
         traffic on this SDP bind when peer pw status has fault bits set."
    DEFVAL      { false }
    ::= { sdpBindEntry 68 }

sdpBindIngressIPv6Flowspec       OBJECT-TYPE
    SYNTAX      TruthValue
    MAX-ACCESS  read-create
    STATUS      obsolete
    DESCRIPTION
        "The value of sdpBindIngressIPv6Flowspec specifies whether ingress IPv6
         Flowspec is enabled for this sdp."
    DEFVAL      { false }
    ::= { sdpBindEntry 69 }

sdpBindMirrorRemoteSource        OBJECT-TYPE
    SYNTAX      TruthValue
    MAX-ACCESS  read-create
    STATUS      current
    DESCRIPTION
        "The value of sdpBindMirrorRemoteSource specifies whether this SDP bind
         is part of remote source of the mirror service."
    DEFVAL      { false }
    ::= { sdpBindEntry 70 }

sdpBindEtreeRootLeafTag          OBJECT-TYPE
    SYNTAX      TruthValue
    MAX-ACCESS  read-create
    STATUS      current
    DESCRIPTION
        "The value of sdpBindEtreeRootLeafTag specifies whether or not this SDP
         binding is etree tagging in this service.

         An 'inconsistentValue' error is returned if the value of this object
         is set to 'true' when TIMETRA-SERV-MIB::svcType for the service is not
         set to 'tls'.

         An 'inconsistentValue' error is returned if the value of this object
         is set to 'true' when TIMETRA-SERV-MIB::svcTlsModeEtree for the
         service is set to 'false'.

         An 'inconsistentValue' error is returned if sdpBindEtreeRootLeafTag is
         set to a non-default value and sdpBindEtreeLeafAc is also set to a
         non-default value for the same SDP instance.

         The value of this object can be set only during the creation of the
         SDP instance. An 'inconsistentValue' error is returned if
         sdpBindEtreeRootLeafTag is Set to a different value after the SDP
         instance has been created."
    DEFVAL      { false }
    ::= { sdpBindEntry 72 }

sdpBindCpmProtMonitorIP          OBJECT-TYPE
    SYNTAX      TruthValue
    MAX-ACCESS  read-create
    STATUS      current
    DESCRIPTION
        "The value of sdpBindCpmProtMonitorIP specifies whether or not to apply
         the tmnxCpmProtPolPerSrcRateLimit of this SDP binding's CPM Protection
         policy to IPv4 DHCP packets served by the SDP binding, on a per source
         IP address basis.

         For example, suppose sdpBindCpmProtMonitorIP is 'true', and this SDP
         binding's sdpBindCpmProtPolicyId points to a policy table row with
         tmnxCpmProtPolPerSrcRateLimit set to 100 packets/second. Suppose two
         source IP addresses (e.g. 138.120.141.173 and 138.120.141.174) each
         send 150 DHCP packets/second to this SAP. Approx. 50 DHCP
         packets/second from each source will be discarded.

         If the value of sdpBindCpmProtPolicyId is equal to zero, the value of
         sdpBindCpmProtMonitorIP is irrelevant and will be ignored.

         At most one of the following options can be enabled on this SDP
         binding:
           1.  sdpBindCpmProtMonitorMac,
           2.  The sdpBindCpmProtEthCfmMonitorFlags option 'ethCfmMonitor(0)',
           3.  sdpBindCpmProtMonitorIP."
    DEFVAL      { false }
    ::= { sdpBindEntry 73 }

sdpBindUseSdpBMac                OBJECT-TYPE
    SYNTAX      TruthValue
    MAX-ACCESS  read-create
    STATUS      current
    DESCRIPTION
        "The value of sdpBindUseSdpBMac specifies whether this spoke-SDP is
         expected to be part of a redundant pseudo-wire within a PBB epipe
         service.

         Setting the value of sdpBindUseSdpBMac to 'true (1)' will cause
         traffic forwarded from this spoke-SDP into the B-VPLS domain to use a
         virtual backbone MAC as its source MAC address when the value of both
         sdpSourceBMacLSB and sdpControlPWVCId is set to non-default values."
    DEFVAL      { false }
    ::= { sdpBindEntry 74 }

sdpBindEtreeLeafAc               OBJECT-TYPE
    SYNTAX      TruthValue
    MAX-ACCESS  read-create
    STATUS      current
    DESCRIPTION
        "The value of sdpBindEtreeLeafAc specifies whether or not this SDP
         binding is an etree leaf access circuit of the service.

         An 'inconsistentValue' error is returned if the value of this object
         is set to 'true' when TIMETRA-SERV-MIB::svcType for the service is not
         set to 'tls'.

         An 'inconsistentValue' error is returned if the value of this object
         is set to 'true' when TIMETRA-SERV-MIB::svcTlsModeEtree for the
         service is set to 'false'.

         An 'inconsistentValue' error is returned if sdpBindEtreeLeafAc is set
         to a non-default value and sdpBindEtreeRootLeafTag is also set to a
         non-default value for the same SDP instance.

         The value of this object can be set only during the creation of the
         SDP instance. An 'inconsistentValue' error is returned if
         sdpBindEtreeLeafAc is Set to a different value after the SDP instance
         has been created."
    DEFVAL      { false }
    ::= { sdpBindEntry 75 }

sdpBindBfdTemplateName           OBJECT-TYPE
    SYNTAX      TNamedItemOrEmpty
    MAX-ACCESS  read-create
    STATUS      current
    DESCRIPTION
        "The value of sdpBindBfdTemplateName specifies BFD template associated
         with this SDP binding."
    DEFVAL      { ''H }
    ::= { sdpBindEntry 76 }

sdpBindBfdEnable                 OBJECT-TYPE
    SYNTAX      TruthValue
    MAX-ACCESS  read-create
    STATUS      current
    DESCRIPTION
        "The value of sdpBindBfdEnable specifies whether BFD is enabled on this
         SDP binding."
    DEFVAL      { false }
    ::= { sdpBindEntry 77 }

sdpBindBfdEncap                  OBJECT-TYPE
    SYNTAX      TmnxBfdEncap
    MAX-ACCESS  read-create
    STATUS      current
    DESCRIPTION
        "The value of sdpBindBfdEncap specifies the BFD encapsulation used on
         this SDP binding."
    DEFVAL      { ipv4 }
    ::= { sdpBindEntry 78 }

sdpBindForceQinqVcForwarding     OBJECT-TYPE
    SYNTAX      TruthValue
    MAX-ACCESS  read-create
    STATUS      obsolete
    DESCRIPTION
        "The value of sdpBindForceQinqVcForwarding specifies whether or not the
         datapath should forcefully insert two VLAN tags when sdpBindVcType is
         either set to 'ether' or 'vlan'.

         An 'inconsistentValue' error is returned when an attempt is made to
         set the value of sdpBindForceQinqVcForwarding to 'true' and
         sdpBindVcType is not set to either 'ether' or 'vlan'."
    DEFVAL      { false }
    ::= { sdpBindEntry 79 }

sdpBindIngressVlanTranslation    OBJECT-TYPE
    SYNTAX      INTEGER {
        none      (1),
        vlanId    (2),
        copyOuter (3)
    }
    MAX-ACCESS  read-create
    STATUS      obsolete
    DESCRIPTION
        "The value of sdpBindIngressVlanTranslation specifies the desired
         Ingress Vlan Translation.

         A value of 'vlanId' specifies that the value of
         sdpBindIngressVlanTranslationId is to be used to overwrite the
         preserved VLAN id in the packet.

         A value of 'copyOuter' specifies that the outer VLAN id should be used
         to overwrite the preserved VLAN id in the packet.

         An 'inconsistentValue' error is returned when an attempt is made to
         set the value of sdpBindIngressVlanTranslation to 'vlanId' and
         sdpBindIngressVlanTranslationId is set to '-1'."
    DEFVAL      { none }
    ::= { sdpBindEntry 80 }

sdpBindIngressVlanTranslationId  OBJECT-TYPE
    SYNTAX      Integer32 (-1 | 0..4094)
    MAX-ACCESS  read-create
    STATUS      obsolete
    DESCRIPTION
        "The value of sdpBindIngressVlanTranslationId specifies the VLAN id to
         be used to overwrite the preserved VLAN id in the packet.

         An 'inconsistentValue' error is returned when an attempt is made to
         set the value of sdpBindIngressVlanTranslationId to other than '-1'
         and sdpBindIngressVlanTranslation is not set to 'vlanId'."
    DEFVAL      { -1 }
    ::= { sdpBindEntry 81 }

sdpBindMinReqdSdpOperMtu         OBJECT-TYPE
    SYNTAX      Integer32
    MAX-ACCESS  read-only
    STATUS      current
    DESCRIPTION
        "The value of sdpBindMinReqdSdpOperMtu indicates the minimum required
         SDP MTU size used with this SDP binding."
    ::= { sdpBindEntry 82 }

sdpBindForceQinqVcFwding         OBJECT-TYPE
    SYNTAX      INTEGER {
        none     (0),
        ctagctag (1),
        stagctag (2)
    }
    MAX-ACCESS  read-create
    STATUS      current
    DESCRIPTION
        "The value of sdpBindForceQinqVcFwding specifies whether or not the
         datapath should forcefully insert two VLAN tags which are copied from
         the qinq service-delimiting vlan values.

         The sdpBindVcType should be either set to 'ether' or 'vlan'."
    DEFVAL      { none }
    ::= { sdpBindEntry 83 }

sdpBindMulticastSource           OBJECT-TYPE
    SYNTAX      TruthValue
    MAX-ACCESS  read-create
    STATUS      current
    DESCRIPTION
        "The value of sdpBindMulticastSource specifies whether or not the
         multicast source is enabled on the SDP. This object can only be set at
         the time the row is created and is mutually exclusive with
         sdpBindSplitHorizonGrp."
    DEFVAL      { false }
    ::= { sdpBindEntry 84 }

sdpBindBaseStatsTable            OBJECT-TYPE
    SYNTAX      SEQUENCE OF SdpBindBaseStatsEntry
    MAX-ACCESS  not-accessible
    STATUS      current
    DESCRIPTION
        "A table that contains basic SDP Binding statistics."
    ::= { tmnxSdpObjs 5 }

sdpBindBaseStatsEntry            OBJECT-TYPE
    SYNTAX      SdpBindBaseStatsEntry
    MAX-ACCESS  not-accessible
    STATUS      current
    DESCRIPTION
        "Basic statistics about a specific SDP Binding."
    INDEX       {
        svcId,
        sdpBindId
    }
    ::= { sdpBindBaseStatsTable 1 }

SdpBindBaseStatsEntry            ::= SEQUENCE
{
    sdpBindBaseStatsIngressForwardedPackets Counter64,
    sdpBindBaseStatsIngressDroppedPackets Counter64,
    sdpBindBaseStatsEgressForwardedPackets Counter64,
    sdpBindBaseStatsEgressForwardedOctets Counter64,
    sdpBindBaseStatsCustId           TmnxCustId,
    sdpBindBaseStatsIngFwdOctets     Counter64,
    sdpBindBaseStatsIngDropOctets    Counter64
}

sdpBindBaseStatsIngressForwardedPackets OBJECT-TYPE
    SYNTAX      Counter64
    MAX-ACCESS  read-only
    STATUS      current
    DESCRIPTION
        ""
    ::= { sdpBindBaseStatsEntry 1 }

sdpBindBaseStatsIngressDroppedPackets OBJECT-TYPE
    SYNTAX      Counter64
    MAX-ACCESS  read-only
    STATUS      current
    DESCRIPTION
        ""
    ::= { sdpBindBaseStatsEntry 2 }

sdpBindBaseStatsEgressForwardedPackets OBJECT-TYPE
    SYNTAX      Counter64
    MAX-ACCESS  read-only
    STATUS      current
    DESCRIPTION
        ""
    ::= { sdpBindBaseStatsEntry 3 }

sdpBindBaseStatsEgressForwardedOctets OBJECT-TYPE
    SYNTAX      Counter64
    MAX-ACCESS  read-only
    STATUS      current
    DESCRIPTION
        ""
    ::= { sdpBindBaseStatsEntry 4 }

sdpBindBaseStatsCustId           OBJECT-TYPE
    SYNTAX      TmnxCustId
    MAX-ACCESS  read-only
    STATUS      current
    DESCRIPTION
        "The Customer ID of the associated service."
    ::= { sdpBindBaseStatsEntry 5 }

sdpBindBaseStatsIngFwdOctets     OBJECT-TYPE
    SYNTAX      Counter64
    MAX-ACCESS  read-only
    STATUS      current
    DESCRIPTION
        ""
    ::= { sdpBindBaseStatsEntry 6 }

sdpBindBaseStatsIngDropOctets    OBJECT-TYPE
    SYNTAX      Counter64
    MAX-ACCESS  read-only
    STATUS      current
    DESCRIPTION
        ""
    ::= { sdpBindBaseStatsEntry 7 }

sdpBindTlsTable                  OBJECT-TYPE
    SYNTAX      SEQUENCE OF SdpBindTlsEntry
    MAX-ACCESS  not-accessible
    STATUS      current
    DESCRIPTION
        "A table that contains TLS spoke SDP Bind information."
    ::= { tmnxSdpObjs 6 }

sdpBindTlsEntry                  OBJECT-TYPE
    SYNTAX      SdpBindTlsEntry
    MAX-ACCESS  not-accessible
    STATUS      current
    DESCRIPTION
        "TLS specific information about an SDP Bind."
    INDEX       {
        svcId,
        sdpBindId
    }
    ::= { sdpBindTlsTable 1 }

SdpBindTlsEntry                  ::= SEQUENCE
{
    sdpBindTlsStpAdminStatus         TmnxEnabledDisabledAdminState,
    sdpBindTlsStpPriority            Integer32,
    sdpBindTlsStpPortNum             Integer32,
    sdpBindTlsStpPathCost            Integer32,
    sdpBindTlsStpRapidStart          TmnxEnabledDisabled,
    sdpBindTlsStpBpduEncap           INTEGER,
    sdpBindTlsStpPortState           TStpPortState,
    sdpBindTlsStpDesignatedBridge    BridgeId,
    sdpBindTlsStpDesignatedPort      Integer32,
    sdpBindTlsStpForwardTransitions  Gauge32,
    sdpBindTlsStpInConfigBpdus       Gauge32,
    sdpBindTlsStpInTcnBpdus          Gauge32,
    sdpBindTlsStpInBadBpdus          Gauge32,
    sdpBindTlsStpOutConfigBpdus      Gauge32,
    sdpBindTlsStpOutTcnBpdus         Gauge32,
    sdpBindTlsStpOperBpduEncap       INTEGER,
    sdpBindTlsStpVpnId               VpnId,
    sdpBindTlsStpCustId              TmnxCustId,
    sdpBindTlsMacAddressLimit        Integer32,
    sdpBindTlsNumMacAddresses        Integer32,
    sdpBindTlsNumStaticMacAddresses  Integer32,
    sdpBindTlsMacLearning            TmnxEnabledDisabled,
    sdpBindTlsMacAgeing              TmnxEnabledDisabled,
    sdpBindTlsStpOperEdge            TruthValue,
    sdpBindTlsStpAdminPointToPoint   INTEGER,
    sdpBindTlsStpPortRole            StpPortRole,
    sdpBindTlsStpAutoEdge            TmnxEnabledDisabled,
    sdpBindTlsStpOperProtocol        StpProtocol,
    sdpBindTlsStpInRstBpdus          Gauge32,
    sdpBindTlsStpOutRstBpdus         Gauge32,
    sdpBindTlsLimitMacMove           TlsLimitMacMove,
    sdpBindTlsDiscardUnknownSource   TmnxEnabledDisabled,
    sdpBindTlsMvplsPruneState        MvplsPruneState,
    sdpBindTlsMvplsMgmtService       TmnxServId,
    sdpBindTlsMvplsMgmtSdpBndId      SdpBindId,
    sdpBindTlsStpException           StpExceptionCondition,
    sdpBindTlsL2ptTermination        TmnxEnabledDisabled,
    sdpBindTlsBpduTranslation        TlsBpduTranslation,
    sdpBindTlsStpRootGuard           TruthValue,
    sdpBindTlsStpInMstBpdus          Gauge32,
    sdpBindTlsStpOutMstBpdus         Gauge32,
    sdpBindTlsStpRxdDesigBridge      BridgeId,
    sdpBindTlsMacMoveNextUpTime      Unsigned32,
    sdpBindTlsMacMoveRateExcdLeft    Unsigned32,
    sdpBindTlsLimitMacMoveLevel      TlsLimitMacMoveLevel,
    sdpBindTlsBpduTransOper          INTEGER,
    sdpBindTlsL2ptProtocols          L2ptProtocols,
    sdpBindTlsIgnoreStandbySig       TruthValue,
    sdpBindTlsBlockOnMeshFail        TruthValue,
    sdpBindTlsInTcBitBpdus           Counter32,
    sdpBindTlsOutTcBitBpdus          Counter32,
    sdpBindTlsRestProtSrcMac         TruthValue,
    sdpBindTlsRestProtSrcMacAction   INTEGER,
    sdpBindTlsAutoLearnMacProtect    TruthValue,
    sdpBindDisableSendBvplsEvpnFlush TruthValue,
    sdpBindTlsRestProtSrcMacOper     TruthValue,
    sdpBindTlsRestProtSrcMacOperAct  INTEGER
}

sdpBindTlsStpAdminStatus         OBJECT-TYPE
    SYNTAX      TmnxEnabledDisabledAdminState
    MAX-ACCESS  read-write
    STATUS      current
    DESCRIPTION
        "The value of the object sdpBindTlsStpAdminStatus specifies whether
         this SDP Bind participates in the TLS's Spanning Tree Protocol."
    DEFVAL      { enabled }
    ::= { sdpBindTlsEntry 1 }

sdpBindTlsStpPriority            OBJECT-TYPE
    SYNTAX      Integer32 (0..255)
    MAX-ACCESS  read-write
    STATUS      current
    DESCRIPTION
        "The value of the object sdpBindTlsStpPriority specifies the value of
         the port priority field which is contained in the most significant 4
         bits of the 16-bit Port ID associated with this SDP Bind. As only the
         most significant 4 bits of the value are used, the actual value of
         this object is limited to multiples of 16: e.g. the agent rounds down
         the value to one of: 0, 16, 32, .. , 224, 240."
    DEFVAL      { 128 }
    ::= { sdpBindTlsEntry 2 }

sdpBindTlsStpPortNum             OBJECT-TYPE
    SYNTAX      Integer32 (0..4094)
    MAX-ACCESS  read-write
    STATUS      current
    DESCRIPTION
        "The value of the object sdpBindTlsStpPortNum specifies the value of
         the port number field which is contained in the least significant 12
         bits of the 16-bit Port ID associated with this SDP Bind. Values in
         the range 2048..4094 are automatically assigned by the agent when the
         SDP Bind is created or when the value of this object is set to zero
         via management. Values in the range 1..2047 can be set via management,
         to allow this object to have a deterministic value across system
         reboots."
    ::= { sdpBindTlsEntry 3 }

sdpBindTlsStpPathCost            OBJECT-TYPE
    SYNTAX      Integer32 (1..200000000)
    MAX-ACCESS  read-write
    STATUS      current
    DESCRIPTION
        "The value of the object sdpBindTlsStpPathCost specifies the
         contribution of this port to the path cost of paths towards the
         spanning tree root which include this port."
    DEFVAL      { 10 }
    ::= { sdpBindTlsEntry 4 }

sdpBindTlsStpRapidStart          OBJECT-TYPE
    SYNTAX      TmnxEnabledDisabled
    MAX-ACCESS  read-write
    STATUS      current
    DESCRIPTION
        "The value of the object sdpBindTlsStpRapidStart specifies whether
         Rapid Start is enabled on this SDP Bind. When the value is 'enabled'
         the Spanning Tree Protocol state transitions on this SDP Bind are
         driven by the value of the 'HelloTime', instead of the value of
         'ForwardDelay', thus allowing a faster transition into the forwarding
         state."
    DEFVAL      { disabled }
    ::= { sdpBindTlsEntry 5 }

sdpBindTlsStpBpduEncap           OBJECT-TYPE
    SYNTAX      INTEGER {
        dynamic (1),
        dot1d   (2),
        pvst    (3)
    }
    MAX-ACCESS  read-write
    STATUS      current
    DESCRIPTION
        "The value of the object sdpBindTlsStpBpduEncap specifies the type of
         encapsulation used on BPDUs sent out and received on this SDP Bind."
    DEFVAL      { dynamic }
    ::= { sdpBindTlsEntry 6 }

sdpBindTlsStpPortState           OBJECT-TYPE
    SYNTAX      TStpPortState
    MAX-ACCESS  read-only
    STATUS      current
    DESCRIPTION
        "The value of the object sdpBindTlsStpPortState indicates the port's
         current state as defined by application of the Spanning Tree Protocol.
         This state controls what action a port takes on reception of a frame.
         If the bridge has detected a port that is malfunctioning it will place
         that port into the 'broken' state. All possible states are: learning,
         forwarding, broken, and discarding."
    ::= { sdpBindTlsEntry 7 }

sdpBindTlsStpDesignatedBridge    OBJECT-TYPE
    SYNTAX      BridgeId
    MAX-ACCESS  read-only
    STATUS      current
    DESCRIPTION
        "The value of the object sdpBindTlsStpDesignatedBridge indicates the
         Bridge Identifier of the bridge which this port considers to be the
         Designated Bridge for this port's segment."
    ::= { sdpBindTlsEntry 8 }

sdpBindTlsStpDesignatedPort      OBJECT-TYPE
    SYNTAX      Integer32
    MAX-ACCESS  read-only
    STATUS      current
    DESCRIPTION
        "The value of the object sdpBindTlsStpDesignatedPort indicates the Port
         Identifier of the port on the Designated Bridge for this port's
         segment."
    ::= { sdpBindTlsEntry 9 }

sdpBindTlsStpForwardTransitions  OBJECT-TYPE
    SYNTAX      Gauge32
    MAX-ACCESS  read-only
    STATUS      current
    DESCRIPTION
        "The value of the object sdpBindTlsStpForwardTransitions indicates the
         number of times this port has transitioned from the Learning state to
         the Forwarding state."
    ::= { sdpBindTlsEntry 10 }

sdpBindTlsStpInConfigBpdus       OBJECT-TYPE
    SYNTAX      Gauge32
    MAX-ACCESS  read-only
    STATUS      current
    DESCRIPTION
        "The value of the object sdpBindTlsStpInConfigBpdus indicates the
         number of Configuration BPDUs received on this SDP Bind."
    ::= { sdpBindTlsEntry 11 }

sdpBindTlsStpInTcnBpdus          OBJECT-TYPE
    SYNTAX      Gauge32
    MAX-ACCESS  read-only
    STATUS      current
    DESCRIPTION
        "The value of the object sdpBindTlsStpInTcnBpdus indicates the number
         of Topology Change Notification BPDUs received on this SDP Bind."
    ::= { sdpBindTlsEntry 12 }

sdpBindTlsStpInBadBpdus          OBJECT-TYPE
    SYNTAX      Gauge32
    MAX-ACCESS  read-only
    STATUS      current
    DESCRIPTION
        "The value of the object sdpBindTlsStpInBadBpdus indicates the number
         of bad BPDUs received on this SDP Bind."
    ::= { sdpBindTlsEntry 13 }

sdpBindTlsStpOutConfigBpdus      OBJECT-TYPE
    SYNTAX      Gauge32
    MAX-ACCESS  read-only
    STATUS      current
    DESCRIPTION
        "The value of the object sdpBindTlsStpOutConfigBpdus indicates the
         number of Configuration BPDUs sent out this SDP Bind."
    ::= { sdpBindTlsEntry 14 }

sdpBindTlsStpOutTcnBpdus         OBJECT-TYPE
    SYNTAX      Gauge32
    MAX-ACCESS  read-only
    STATUS      current
    DESCRIPTION
        "The value of the object sdpBindTlsStpOutTcnBpdus indicates the number
         of Topology Change Notification BPDUs sent out this SDP Bind."
    ::= { sdpBindTlsEntry 15 }

sdpBindTlsStpOperBpduEncap       OBJECT-TYPE
    SYNTAX      INTEGER {
        dot1d (2),
        pvst  (3)
    }
    MAX-ACCESS  read-only
    STATUS      current
    DESCRIPTION
        "The value of the object sdpBindTlsStpOperBpduEncap indicates the
         operating encapsulation type used on BPDUs sent out and received on
         this SDP Bind."
    ::= { sdpBindTlsEntry 16 }

sdpBindTlsStpVpnId               OBJECT-TYPE
    SYNTAX      VpnId
    MAX-ACCESS  read-only
    STATUS      current
    DESCRIPTION
        "The value of the object sdpBindTlsStpVpnId indicates the VPN ID of the
         associated service."
    ::= { sdpBindTlsEntry 17 }

sdpBindTlsStpCustId              OBJECT-TYPE
    SYNTAX      TmnxCustId
    MAX-ACCESS  read-only
    STATUS      current
    DESCRIPTION
        "The value of the object sdpBindTlsStpCustId indicates the Customer ID
         of the associated service."
    ::= { sdpBindTlsEntry 18 }

sdpBindTlsMacAddressLimit        OBJECT-TYPE
    SYNTAX      Integer32 (0..511999)
    MAX-ACCESS  read-write
    STATUS      current
    DESCRIPTION
        "The value of the object sdpBindTlsMacAddressLimit
         specifies the maximum number of learned and static entries
         allowed in the FDB for this  SDP  Bind.  The value 0
         means: no limit for this SDP Bind. The command is valid
         only for spoke SDPs.

         The maximum value of sdpBindTlsMacAddressLimit depends on the
         platform/chassis mode."
    DEFVAL      { 0 }
    ::= { sdpBindTlsEntry 19 }

sdpBindTlsNumMacAddresses        OBJECT-TYPE
    SYNTAX      Integer32
    MAX-ACCESS  read-only
    STATUS      current
    DESCRIPTION
        "The value of the object sdpBindTlsNumMacAddresses
         indicates the number of MAC addresses  currently present
         in the FDB that belong to this  SDP  Bind (Both learned
         and static MAC addresses are counted)."
    ::= { sdpBindTlsEntry 20 }

sdpBindTlsNumStaticMacAddresses  OBJECT-TYPE
    SYNTAX      Integer32
    MAX-ACCESS  read-only
    STATUS      current
    DESCRIPTION
        "The value of the object sdpBindTlsNumStaticMacAddresses indicates the
         number of static MAC addresses currently present in the FDB that
         belong to this SDP Bind."
    ::= { sdpBindTlsEntry 21 }

sdpBindTlsMacLearning            OBJECT-TYPE
    SYNTAX      TmnxEnabledDisabled
    MAX-ACCESS  read-write
    STATUS      current
    DESCRIPTION
        "The value of the object sdpBindTlsMacLearning specifies whether the
         MAC learning process is enabled for this SDP Bind. The value is
         ignored if MAC learning is disabled on service level."
    DEFVAL      { enabled }
    ::= { sdpBindTlsEntry 22 }

sdpBindTlsMacAgeing              OBJECT-TYPE
    SYNTAX      TmnxEnabledDisabled
    MAX-ACCESS  read-write
    STATUS      current
    DESCRIPTION
        "The value of the object sdpBindTlsMacAgeing specifies
         whether the MAC aging process  is  enabled  for  this
         SDP Bind. the value is ignored if MAC aging is disabled
         on service level."
    DEFVAL      { enabled }
    ::= { sdpBindTlsEntry 23 }

sdpBindTlsStpOperEdge            OBJECT-TYPE
    SYNTAX      TruthValue
    MAX-ACCESS  read-only
    STATUS      current
    DESCRIPTION
        "The value of the object sdpBindTlsStpOperEdge indicates the
         operational value of the Edge Port parameter. The object is
         initialized to the value of sdpBindTlsStpRapidStart and is set FALSE
         on reception of a BPDU."
    REFERENCE
        "IEEE 802.1t clause 14.8.2, 18.3.4"
    ::= { sdpBindTlsEntry 24 }

sdpBindTlsStpAdminPointToPoint   OBJECT-TYPE
    SYNTAX      INTEGER {
        forceTrue  (0),
        forceFalse (1)
    }
    MAX-ACCESS  read-write
    STATUS      current
    DESCRIPTION
        "The value of the object sdpBindTlsStpAdminPointToPoint specifies the
         administrative point-to-point status of the LAN segment attached to
         this sdp. A value of 'forceTrue' indicates that this port should
         always be treated as if it is connected to a point-to-point link. A
         value of 'forceFalse' indicates that this port should be treated as
         having a shared media connection."
    REFERENCE
        "IEEE 802.1w clause 6.4.3, 6.5, 14.8.2"
    DEFVAL      { forceTrue }
    ::= { sdpBindTlsEntry 25 }

sdpBindTlsStpPortRole            OBJECT-TYPE
    SYNTAX      StpPortRole
    MAX-ACCESS  read-only
    STATUS      current
    DESCRIPTION
        "The value of the object sdpBindTlsStpPortRole indicates the current
         role of the sdp as defined by the Rapid Spanning Tree Protocol."
    ::= { sdpBindTlsEntry 26 }

sdpBindTlsStpAutoEdge            OBJECT-TYPE
    SYNTAX      TmnxEnabledDisabled
    MAX-ACCESS  read-write
    STATUS      current
    DESCRIPTION
        "The value of the object sdpBindTlsStpAutoEdge specifies whether this
         SDP is enabled for auto-edge detection as defined by Rapid Spanning
         Tree Protocol."
    DEFVAL      { enabled }
    ::= { sdpBindTlsEntry 27 }

sdpBindTlsStpOperProtocol        OBJECT-TYPE
    SYNTAX      StpProtocol
    MAX-ACCESS  read-only
    STATUS      current
    DESCRIPTION
        "The value of the object sdpBindTlsStpOperProtocol indicates whether
         stp, rstp or mstp is running on this spoke sdp. If the protocol is not
         enabled on this spoke-sdp the value notApplicable is returned."
    ::= { sdpBindTlsEntry 28 }

sdpBindTlsStpInRstBpdus          OBJECT-TYPE
    SYNTAX      Gauge32
    MAX-ACCESS  read-only
    STATUS      current
    DESCRIPTION
        "The value of the object sdpBindTlsStpInRstBpdus indicates the number
         of Rapid Spanning Tree (Rst) BPDUs received on this SDP."
    ::= { sdpBindTlsEntry 29 }

sdpBindTlsStpOutRstBpdus         OBJECT-TYPE
    SYNTAX      Gauge32
    MAX-ACCESS  read-only
    STATUS      current
    DESCRIPTION
        "The value of the object sdpBindTlsStpOutRstBpdus indicates the number
         of Rapid Spanning Tree (Rstp) BPDUs sent out on this SDP."
    ::= { sdpBindTlsEntry 30 }

sdpBindTlsLimitMacMove           OBJECT-TYPE
    SYNTAX      TlsLimitMacMove
    MAX-ACCESS  read-write
    STATUS      current
    DESCRIPTION
        "When sdpBindTlsLimitMacMove value is set to  blockable
         (1) the agent will monitor the MAC relearn rate on this
         SDP  Bind,  and it will block it when the relearn rate
         specified by svcTlsMacMoveMaxRate is exceeded. When the
         value  is  'nonBlockable' this SDP binding will not be
         blocked,  and  another  blockable  SDP  binding will be
         blocked instead."
    DEFVAL      { blockable }
    ::= { sdpBindTlsEntry 31 }

sdpBindTlsDiscardUnknownSource   OBJECT-TYPE
    SYNTAX      TmnxEnabledDisabled
    MAX-ACCESS  read-write
    STATUS      current
    DESCRIPTION
        "With the object sdpBindTlsMacAddressLimit a limit  can
         be configured for the max number of MAC addresses that
         will  be  learned  on  this  SDP  Bind (only for spoke
         SDPs).  When  this  limit  is  reached,  packets  with
         unknown  source  MAC address are forwarded by default.
         By  setting sdpBindTlsDiscardUnknownSource to enabled,
         packets  with  unknown  source  MAC will be dropped in
         stead."
    DEFVAL      { disabled }
    ::= { sdpBindTlsEntry 32 }

sdpBindTlsMvplsPruneState        OBJECT-TYPE
    SYNTAX      MvplsPruneState
    MAX-ACCESS  read-only
    STATUS      current
    DESCRIPTION
        "The value of the object sdpBindTlsMvplsPruneState indicates the mVPLS
         prune state of the spoke SDP. The object will be set to notApplicable
         if the spoke SDP is not managed by a mVPLS. If the SDP is managed the
         state reflects whether or not it is pruned by the STP instance running
         in the mVPLS instance."
    ::= { sdpBindTlsEntry 33 }

sdpBindTlsMvplsMgmtService       OBJECT-TYPE
    SYNTAX      TmnxServId
    MAX-ACCESS  read-only
    STATUS      current
    DESCRIPTION
        "The value of the object sdpBindTlsMvplsMgmtService indicates the
         service Id of the service where the STP instance is running that is
         managing this spoke SDP. This object is only valid if
         sdpBindTlsMvplsPruneState is different from notApplicable."
    ::= { sdpBindTlsEntry 34 }

sdpBindTlsMvplsMgmtSdpBndId      OBJECT-TYPE
    SYNTAX      SdpBindId
    MAX-ACCESS  read-only
    STATUS      current
    DESCRIPTION
        "The value of the object sdpBindTlsMvplsMgmtSdpBndId indicates the SDP
         bind id in the mVPLS instance specified in sdpBindTlsMvplsMgmtService
         that is controlling this SDP. This object is only valid if
         sdpBindTlsMvplsPruneState is different from notApplicable."
    ::= { sdpBindTlsEntry 35 }

sdpBindTlsStpException           OBJECT-TYPE
    SYNTAX      StpExceptionCondition
    MAX-ACCESS  read-only
    STATUS      current
    DESCRIPTION
        "The value of the object sdpBindTlsStpException indicates whether an
         STP exception condition is present on this Spoke Sdp.
         - none : no exception condition found.
         - oneWayCommuniation : The neighbor RSTP peer on this link
                                is not able to detect our presence.
         - downstreamLoopDetected :A loop is detected on this link."
    ::= { sdpBindTlsEntry 36 }

sdpBindTlsL2ptTermination        OBJECT-TYPE
    SYNTAX      TmnxEnabledDisabled
    MAX-ACCESS  read-write
    STATUS      current
    DESCRIPTION
        "The value of the object sdpBindTlsL2ptTermination specifies whether
         received L2 Protocol Tunnel PDUs are terminated on this port or sdp"
    DEFVAL      { disabled }
    ::= { sdpBindTlsEntry 37 }

sdpBindTlsBpduTranslation        OBJECT-TYPE
    SYNTAX      TlsBpduTranslation
    MAX-ACCESS  read-write
    STATUS      current
    DESCRIPTION
        "The value of the object sdpBindTlsBpduTranslation specifies whether
         received L2 Protocol Tunnel PDUs are translated before being sent out
         on this port or sap"
    DEFVAL      { disabled }
    ::= { sdpBindTlsEntry 38 }

sdpBindTlsStpRootGuard           OBJECT-TYPE
    SYNTAX      TruthValue
    MAX-ACCESS  read-write
    STATUS      current
    DESCRIPTION
        "The value of the object sdpBindTlsStpRootGuard specifies whether this
         port is allowed to become STP root port. It corresponds to the
         parameter 'restrictedRole' in 802.1Q. If set, it can cause lack of
         spanning tree connectivity."
    DEFVAL      { false }
    ::= { sdpBindTlsEntry 39 }

sdpBindTlsStpInMstBpdus          OBJECT-TYPE
    SYNTAX      Gauge32
    MAX-ACCESS  read-only
    STATUS      current
    DESCRIPTION
        "The value of the object sdpBindTlsStpInMstBpdus indicates the number
         of Multiple Spanning Tree (Mst) BPDUs received on this SDP."
    ::= { sdpBindTlsEntry 40 }

sdpBindTlsStpOutMstBpdus         OBJECT-TYPE
    SYNTAX      Gauge32
    MAX-ACCESS  read-only
    STATUS      current
    DESCRIPTION
        "The value of the object sdpBindTlsStpOutMstBpdus indicates the number
         of Multiple Spanning Tree (Mst) BPDUs sent out on this SDP."
    ::= { sdpBindTlsEntry 41 }

sdpBindTlsStpRxdDesigBridge      OBJECT-TYPE
    SYNTAX      BridgeId
    MAX-ACCESS  read-only
    STATUS      current
    DESCRIPTION
        "The value of the object sdpBindTlsStpRxdDesigBridge
         indicates  the designated Bridge Identifier in the last
         BPDU which was received on this SDP."
    ::= { sdpBindTlsEntry 42 }

sdpBindTlsMacMoveNextUpTime      OBJECT-TYPE
    SYNTAX      Unsigned32
    UNITS       "seconds"
    MAX-ACCESS  read-only
    STATUS      current
    DESCRIPTION
        "The value of the object sdpBindTlsMacMoveNextUpTime counts down the
         time in seconds until a SDP bind that has been brought down due to
         exceeding the TLS svcTlsMacMoveMaxRate, sdpBindOperFlags
         'relearnLimitExceeded', is automatically brought up again.

         When this value is 0xffff, the SDP bind will never be automatically
         brought up.

         When sdpBindOperStatus is 'up', this object counts down the time in
         seconds until the value of sdpBindTlsMacMoveRateExcdLeft is reset."
    ::= { sdpBindTlsEntry 43 }

sdpBindTlsMacMoveRateExcdLeft    OBJECT-TYPE
    SYNTAX      Unsigned32
    MAX-ACCESS  read-only
    STATUS      current
    DESCRIPTION
        "The value of the object sdpBindTlsMacMoveRateExcdLeft counts down the
         number of times this SDP bind can exceed the TLS svcTlsMacMoveMaxRate
         and still be automatically brought up."
    ::= { sdpBindTlsEntry 44 }

sdpBindTlsLimitMacMoveLevel      OBJECT-TYPE
    SYNTAX      TlsLimitMacMoveLevel
    MAX-ACCESS  read-write
    STATUS      current
    DESCRIPTION
        "The value of the object sdpBindTlsLimitMacMoveLevel specifies the
         hierarchy in which spoke-SDPs are blocked when a MAC-move limit is
         exceeded. When a MAC is moving among multiple SAPs or spoke-SDPs, the
         SAP bind or spoke-SDP bind with the lower level is blocked first.
         (tertiary is the lowest)"
    DEFVAL      { tertiary }
    ::= { sdpBindTlsEntry 45 }

sdpBindTlsBpduTransOper          OBJECT-TYPE
    SYNTAX      INTEGER {
        undefined (1),
        disabled  (2),
        pvst      (3),
        stp       (4),
        pvst-rw   (5)
    }
    MAX-ACCESS  read-only
    STATUS      current
    DESCRIPTION
        "The value of the object sdpBindTlsBpduTransOper indicates the
         operational BPDU encapsulation used for BPDU translated frames."
    ::= { sdpBindTlsEntry 46 }

sdpBindTlsL2ptProtocols          OBJECT-TYPE
    SYNTAX      L2ptProtocols
    MAX-ACCESS  read-write
    STATUS      current
    DESCRIPTION
        "The value of the object sdpBindTlsL2ptProtocols specifies which L2
         Protocol Tunnel PDUs are terminated on this port or sdp"
    DEFVAL      { {stp} }
    ::= { sdpBindTlsEntry 47 }

sdpBindTlsIgnoreStandbySig       OBJECT-TYPE
    SYNTAX      TruthValue
    MAX-ACCESS  read-write
    STATUS      current
    DESCRIPTION
        "The value of sdpBindTlsIgnoreStandbySig specifies whether the local
         internal tasks will take into account the 'pseudo-wire forwarding
         standby' bit received from the LDP peer which is normally ignored.

         When set to 'true', this bit is not considered in the internal tasks.

         A similar object svcEndPointIgnoreStandbySig is present at
         the endpoint level.  If this spoke-SDP is part of that
         explicit endpoint, this object will be set to the value of
         svcEndPointIgnoreStandbySig and its value will not allowed
         to be changed.

         This spoke-SDP can be made part of an explicit endpoint only if the
         setting of this object is not conflicting with the setting of
         svcEndPointIgnoreStandbySig object."
    DEFVAL      { false }
    ::= { sdpBindTlsEntry 48 }

sdpBindTlsBlockOnMeshFail        OBJECT-TYPE
    SYNTAX      TruthValue
    MAX-ACCESS  read-write
    STATUS      current
    DESCRIPTION
        "The value of sdpBindTlsBlockOnMeshFail specifies that the operational
         status of this spoke SDP will consider operational status of
         associated mesh SDPs in this service.

         If there are no mesh SDPs in the service, value of this object is
         ignored.

         When this object is set to 'true', then the operational
         status of this spoke SDP will be 'down' until the
            operational status of at least one mesh SDP in this service
         is 'up'.

         When set to 'false', the operational status of this spoke SDP does not
         consider the operational status of any mesh SDPs in the service."
    DEFVAL      { false }
    ::= { sdpBindTlsEntry 49 }

sdpBindTlsInTcBitBpdus           OBJECT-TYPE
    SYNTAX      Counter32
    MAX-ACCESS  read-only
    STATUS      current
    DESCRIPTION
        "The value of the object sdpBindTlsInTcBitBpdus indicates the number
         BPDUs received on this SDP Bind with the Topology Change bit set."
    ::= { sdpBindTlsEntry 50 }

sdpBindTlsOutTcBitBpdus          OBJECT-TYPE
    SYNTAX      Counter32
    MAX-ACCESS  read-only
    STATUS      current
    DESCRIPTION
        "The value of the object sdpBindTlsOutTcBitBpdus indicates the number
         BPDUs sent out this SDP Bind with the Topology Change bit set."
    ::= { sdpBindTlsEntry 51 }

sdpBindTlsRestProtSrcMac         OBJECT-TYPE
    SYNTAX      TruthValue
    MAX-ACCESS  read-write
    STATUS      current
    DESCRIPTION
        "The value of the object sdpBindTlsRestProtSrcMac specifies how the
         agent will handle relearn requests for protected MAC addresses. When
         the value of this object is 'true' requests to relearn a protected MAC
         address will be ignored.

         In addition, if the value of sdpBindTlsRestProtSrcMacAction is
         'disable', then the SDP-BIND where the protected source MAC was seen
         will be brought operationally down."
    DEFVAL      { false }
    ::= { sdpBindTlsEntry 52 }

sdpBindTlsRestProtSrcMacAction   OBJECT-TYPE
    SYNTAX      INTEGER {
        disable      (1),
        alarmOnly    (2),
        discardFrame (3)
    }
    MAX-ACCESS  read-write
    STATUS      current
    DESCRIPTION
        "The value of the object sdpBindTlsRestProtSrcMacAction indicates the
         action to take whenever a relearn request for a protected MAC is
         received on a restricted SAP.

         When the value of this object is 'disable' the SAP will be placed in
         the operational down state, with the operating flag 'recProtSrcMac'
         set.

         When the value of this object is 'alarmOnly', the SDP-BIND
         will be left up and only a notification,
         sdpBindReceivedProtSrcMac,  will be generated.

         When the value of this object is 'discardFrame', the SDP-BIND will
         start discarding the frame in addition to generating
         sdpBindReceivedProtSrcMac notification."
    DEFVAL      { disable }
    ::= { sdpBindTlsEntry 53 }

sdpBindTlsAutoLearnMacProtect    OBJECT-TYPE
    SYNTAX      TruthValue
    MAX-ACCESS  read-write
    STATUS      current
    DESCRIPTION
        "The value of sdpBindTlsAutoLearnMacProtect specifies whether to enable
         automatic population of the MAC protect list with source MAC addresses
         learned on the associated SDP binding."
    DEFVAL      { false }
    ::= { sdpBindTlsEntry 54 }

sdpBindDisableSendBvplsEvpnFlush OBJECT-TYPE
    SYNTAX      TruthValue
    MAX-ACCESS  read-write
    STATUS      current
    DESCRIPTION
        "The value of sdpBindDisableSendBvplsEvpnFlush specifies whether to
         send a isid based cmac flush indication when the sdp-bind goes
         oper-down."
    DEFVAL      { false }
    ::= { sdpBindTlsEntry 55 }

sdpBindTlsRestProtSrcMacOper     OBJECT-TYPE
    SYNTAX      TruthValue
    MAX-ACCESS  read-only
    STATUS      current
    DESCRIPTION
        "The value of the object sdpBindTlsRestProtSrcMacOper indicates the
         operational state of the Restrict Protected Source MAC feature."
    ::= { sdpBindTlsEntry 56 }

sdpBindTlsRestProtSrcMacOperAct  OBJECT-TYPE
    SYNTAX      INTEGER {
        disable      (1),
        alarmOnly    (2),
        discardFrame (3)
    }
    MAX-ACCESS  read-only
    STATUS      current
    DESCRIPTION
        "The value of the object sdpBindTlsRestProtSrcMacOperAct indicates the
         operational state of the Restrict Protected Source MAC action."
    ::= { sdpBindTlsEntry 57 }

sdpBindMeshTlsTable              OBJECT-TYPE
    SYNTAX      SEQUENCE OF SdpBindMeshTlsEntry
    MAX-ACCESS  not-accessible
    STATUS      current
    DESCRIPTION
        "A table that contains TLS Mesh SDP Bind information."
    ::= { tmnxSdpObjs 7 }

sdpBindMeshTlsEntry              OBJECT-TYPE
    SYNTAX      SdpBindMeshTlsEntry
    MAX-ACCESS  not-accessible
    STATUS      current
    DESCRIPTION
        "TLS specific information about an Mesh SDP Bind."
    INDEX       {
        svcId,
        sdpBindId
    }
    ::= { sdpBindMeshTlsTable 1 }

SdpBindMeshTlsEntry              ::= SEQUENCE
{
    sdpBindMeshTlsPortState          TStpPortState,
    sdpBindMeshTlsHoldDownTimer      INTEGER,
    sdpBindMeshTlsTransitionState    INTEGER,
    sdpBindMeshTlsNotInMstRegion     TruthValue,
    sdpBindMeshTlsRestProtSrcMac     TruthValue,
    sdpBindMeshTlsRestProtSrcMacAct  INTEGER,
    sdpBindMeshTlsAutoLearnMacProt   TruthValue,
    sdpBindMeshTlsRPSMacOper         TruthValue,
    sdpBindMeshTlsRPSMacOperAct      INTEGER
}

sdpBindMeshTlsPortState          OBJECT-TYPE
    SYNTAX      TStpPortState
    MAX-ACCESS  read-only
    STATUS      current
    DESCRIPTION
        "This object indicates the actual state of the Mesh SDP. If the sdp is
         operationally down, the port will be in the 'disabled' state. If the
         sdp is operationally up, the state will be 'forwarding' unless the
         hold-down timer is active in which case the state will be
         'discarding'."
    ::= { sdpBindMeshTlsEntry 1 }

sdpBindMeshTlsHoldDownTimer      OBJECT-TYPE
    SYNTAX      INTEGER {
        not-active (1),
        active     (2)
    }
    MAX-ACCESS  read-only
    STATUS      current
    DESCRIPTION
        "When the hold-down timer is active, all traffic coming
         from this mesh sdp will be blocked. This timer will be
         activated for any of the following cases:
         1. when a mesh SDP becomes operational;
         2. when a 'disputed' BPDU is received over this mesh sdp;
            This is typically a symptom of one way communication
            (the peer at the other side of the mesh sdp does not
            receive our BPDUs).
         3. when a MSTP BPDU from outside the region is received
            over this mesh SDP."
    ::= { sdpBindMeshTlsEntry 2 }

sdpBindMeshTlsTransitionState    OBJECT-TYPE
    SYNTAX      INTEGER {
        not-applicable        (1),
        waiting-for-agreement (2),
        agreement-received    (3)
    }
    MAX-ACCESS  read-only
    STATUS      current
    DESCRIPTION
        "This object indicates whether we already received an agreement from
         the peer connected via this mesh sdp. RSTP expects an agreement from
         every peer after sending a proposal over the VCP when it wants to
         transition the latter to the forwarding state. This object is only
         relevant when the role of the VCP is 'designated'. Not receiving an
         agreement is typically caused by an improperly configured sdp or by a
         non rstp enabled peer."
    ::= { sdpBindMeshTlsEntry 3 }

sdpBindMeshTlsNotInMstRegion     OBJECT-TYPE
    SYNTAX      TruthValue
    MAX-ACCESS  read-only
    STATUS      current
    DESCRIPTION
        "This object sdpBindMeshTlsNotInMstRegion indicates whether we received
         a BPDU from another MST-region on this mesh SDP.

         If set to 'true' then the object sdpBindMeshTlsHoldDownTimer will have
         the value 'active'.

         It is up to the operator to make sure bridges connected via mesh SDPs
         are in the same MST-region. If not the mesh will NOT become
         operational."
    ::= { sdpBindMeshTlsEntry 4 }

sdpBindMeshTlsRestProtSrcMac     OBJECT-TYPE
    SYNTAX      TruthValue
    MAX-ACCESS  read-write
    STATUS      current
    DESCRIPTION
        "The value of the object sdpBindMeshTlsRestProtSrcMac specifies how the
         agent will handle relearn requests for protected MAC addresses. When
         the value of this object is 'true' requests to relearn a protected MAC
         address will be ignored.

         In addition, if the value of sdpBindMeshTlsRestProtSrcMacAct is
         'disable', then the SDP-BIND where the protected source MAC was seen
         will be brought operationally down."
    DEFVAL      { false }
    ::= { sdpBindMeshTlsEntry 5 }

sdpBindMeshTlsRestProtSrcMacAct  OBJECT-TYPE
    SYNTAX      INTEGER {
        disable      (1),
        alarmOnly    (2),
        discardFrame (3)
    }
    MAX-ACCESS  read-write
    STATUS      current
    DESCRIPTION
        "The value of the object sdpBindMeshTlsRestProtSrcMacAct indicates the
         action to take whenever a relearn request for a protected MAC is
         received on a restricted SAP.

         When the value of this object is 'disable' the SAP will be placed in
         the operational down state, with the operating flag 'recProtSrcMac'
         set.

         When the value of this object is 'alarmOnly', the SDP-BIND
         will be left up and only a notification,
         sdpBindReceivedProtSrcMac,  will be generated.

         When the value of this object is 'discardFrame', the SDP-BIND will
         start discarding the frame in addition to generating
         sdpBindReceivedProtSrcMac notification."
    DEFVAL      { disable }
    ::= { sdpBindMeshTlsEntry 6 }

sdpBindMeshTlsAutoLearnMacProt   OBJECT-TYPE
    SYNTAX      TruthValue
    MAX-ACCESS  read-write
    STATUS      current
    DESCRIPTION
        "The value of sdpBindMeshTlsAutoLearnMacProt specifies whether to
         enable automatic population of the MAC protect list with source MAC
         addresses learned on the associated SDP binding."
    DEFVAL      { false }
    ::= { sdpBindMeshTlsEntry 7 }

sdpBindMeshTlsRPSMacOper         OBJECT-TYPE
    SYNTAX      TruthValue
    MAX-ACCESS  read-only
    STATUS      current
    DESCRIPTION
        "The value of the object sdpBindMeshTlsRPSMacOper indicates the
         operational state of Restrict Protected Source feature."
    ::= { sdpBindMeshTlsEntry 8 }

sdpBindMeshTlsRPSMacOperAct      OBJECT-TYPE
    SYNTAX      INTEGER {
        disable      (1),
        alarmOnly    (2),
        discardFrame (3)
    }
    MAX-ACCESS  read-only
    STATUS      current
    DESCRIPTION
        "The value of the object sdpBindMeshTlsRPSMacOperAct indicates the
         operational state of the Restrict Protected Source MAC action."
    ::= { sdpBindMeshTlsEntry 9 }

sdpBindApipeTable                OBJECT-TYPE
    SYNTAX      SEQUENCE OF SdpBindApipeEntry
    MAX-ACCESS  not-accessible
    STATUS      current
    DESCRIPTION
        "The sdpBindApipeTable has an entry for each apipe sdpBind configured
         on this system."
    ::= { tmnxSdpObjs 8 }

sdpBindApipeEntry                OBJECT-TYPE
    SYNTAX      SdpBindApipeEntry
    MAX-ACCESS  not-accessible
    STATUS      current
    DESCRIPTION
        "Each row entry represents a particular sdpBind related to a particular
         Apipe service entry. Entries are created/deleted by the user."
    INDEX       {
        svcId,
        sdpBindId
    }
    ::= { sdpBindApipeTable 1 }

SdpBindApipeEntry                ::= SEQUENCE
{
    sdpBindApipeAdminConcatCellCount Integer32,
    sdpBindApipeSigConcatCellCount   Integer32,
    sdpBindApipeOperConcatCellCount  Integer32,
    sdpBindApipeConcatMaxDelay       Integer32,
    sdpBindApipeConcatCellClp        TruthValue,
    sdpBindApipeConcatCellAal5Fr     TruthValue
}

sdpBindApipeAdminConcatCellCount OBJECT-TYPE
    SYNTAX      Integer32 (1..128)
    MAX-ACCESS  read-write
    STATUS      current
    DESCRIPTION
        "The value of sdpBindApipeAdminConcatCellCount specifies
         the maximum number of ATM cells to accumulate
         into an MPLS packet.  The remote peer will also signal the
         maximum number of concatenated cells it is willing to
         accept in an MPLS packet.  When the lesser of (the
         configured value and the signaled value) number of cells
         is reached, the MPLS packet is queued for transmission
         onto the pseudowire."
    DEFVAL      { 1 }
    ::= { sdpBindApipeEntry 1 }

sdpBindApipeSigConcatCellCount   OBJECT-TYPE
    SYNTAX      Integer32 (0..128)
    MAX-ACCESS  read-only
    STATUS      current
    DESCRIPTION
        "The value of sdpBindApipeSigConcatCellCount indicates the
         maximum number of concatenated ATM cells the remote peer
         is willing to accept.  If there is no remote peer, or if
         the label mapping has not been received, this object will
         be zero (0)."
    ::= { sdpBindApipeEntry 2 }

sdpBindApipeOperConcatCellCount  OBJECT-TYPE
    SYNTAX      Integer32 (1..128)
    MAX-ACCESS  read-only
    STATUS      current
    DESCRIPTION
        "The value of sdpBindApipeOperConcatCellCount indicates the maximum
         number of concatenated ATM cells that will be sent on this SDP
         binding."
    ::= { sdpBindApipeEntry 3 }

sdpBindApipeConcatMaxDelay       OBJECT-TYPE
    SYNTAX      Integer32 (1..400)
    UNITS       "hundreds of microseconds"
    MAX-ACCESS  read-write
    STATUS      current
    DESCRIPTION
        "The value of sdpBindApipeConcatMaxDelay object specifies
         the maximum amount of time to wait while
         performing ATM cell concatenation into an MPLS packet
         before transmitting the MPLS packet.  This places an upper
         bound on the amount of delay introduced by the
         concatenation process.
         When this amount of time is reached from when the first
         ATM cell for this MPLS packet was received, the MPLS
         packet is queued for transmission onto the pseudowire."
    DEFVAL      { 400 }
    ::= { sdpBindApipeEntry 4 }

sdpBindApipeConcatCellClp        OBJECT-TYPE
    SYNTAX      TruthValue
    MAX-ACCESS  read-write
    STATUS      current
    DESCRIPTION
        "The value of sdpBindApipeConcatCellClp specifies whether a CLP change
         should be used as an indication to complete the cell concatenation
         operation. When the value is 'true', CLP is used to indicate that cell
         concatenation should be completed."
    DEFVAL      { false }
    ::= { sdpBindApipeEntry 5 }

sdpBindApipeConcatCellAal5Fr     OBJECT-TYPE
    SYNTAX      TruthValue
    MAX-ACCESS  read-write
    STATUS      current
    DESCRIPTION
        "The value of sdpBindApipeConcatCellAal5Fr specifies whether the AAL5
         EOP (end of packet) should be used as an indication to complete the
         cell concatenation operation. When the value is 'true', EOP is used to
         indicate that cell concatenation should be completed."
    DEFVAL      { false }
    ::= { sdpBindApipeEntry 6 }

sdpBindDhcpInfoTable             OBJECT-TYPE
    SYNTAX      SEQUENCE OF SdpBindDhcpInfoEntry
    MAX-ACCESS  not-accessible
    STATUS      current
    DESCRIPTION
        "A table that contains DHCP information related to a SDP Bind.

         A row will exist in this table for each spoke or
         mesh SDP in a  Tls Service. Rows are created and deleted
         automatically by the system."
    ::= { tmnxSdpObjs 9 }

sdpBindDhcpInfoEntry             OBJECT-TYPE
    SYNTAX      SdpBindDhcpInfoEntry
    MAX-ACCESS  not-accessible
    STATUS      current
    DESCRIPTION
        "DHCP specific information about an SDP Bind."
    INDEX       {
        svcId,
        sdpBindId
    }
    ::= { sdpBindDhcpInfoTable 1 }

SdpBindDhcpInfoEntry             ::= SEQUENCE
{
    sdpBindDhcpDescription           ServObjDesc,
    sdpBindDhcpSnoop                 TmnxEnabledDisabled
}

sdpBindDhcpDescription           OBJECT-TYPE
    SYNTAX      ServObjDesc
    MAX-ACCESS  read-write
    STATUS      current
    DESCRIPTION
        "The value of the object sdpBindDhcpDescription specifies a user
         provided description for DHCP on this Sdp Bind."
    DEFVAL      { ''H }
    ::= { sdpBindDhcpInfoEntry 1 }

sdpBindDhcpSnoop                 OBJECT-TYPE
    SYNTAX      TmnxEnabledDisabled
    MAX-ACCESS  read-write
    STATUS      current
    DESCRIPTION
        "The value of the object sdpBindDhcpSnoop specifies whether or not DHCP
         snooping is enabled on the Sdp Bind."
    DEFVAL      { disabled }
    ::= { sdpBindDhcpInfoEntry 2 }

sdpBindDhcpStatsTable            OBJECT-TYPE
    SYNTAX      SEQUENCE OF SdpBindDhcpStatsEntry
    MAX-ACCESS  not-accessible
    STATUS      current
    DESCRIPTION
        "sdpBindDhcpStatsTable contains DHCP statistics related
         to  a TLS SDP Bind. A row will exist in this table for
         each  spoke  or  mesh  SDP  in a Tls Service. Rows are
         created and deleted automatically by the system."
    ::= { tmnxSdpObjs 10 }

sdpBindDhcpStatsEntry            OBJECT-TYPE
    SYNTAX      SdpBindDhcpStatsEntry
    MAX-ACCESS  not-accessible
    STATUS      current
    DESCRIPTION
        "DHCP statistics for a TLS spoke SDP or mesh SDP."
    INDEX       {
        svcId,
        sdpBindId
    }
    ::= { sdpBindDhcpStatsTable 1 }

SdpBindDhcpStatsEntry            ::= SEQUENCE
{
    sdpBindDhcpStatsClntSnoopdPckts  Counter32,
    sdpBindDhcpStatsSrvrSnoopdPckts  Counter32,
    sdpBindDhcpStatsClntForwdPckts   Counter32,
    sdpBindDhcpStatsSrvrForwdPckts   Counter32,
    sdpBindDhcpStatsClntDropdPckts   Counter32,
    sdpBindDhcpStatsSrvrDropdPckts   Counter32,
    sdpBindDhcpStatsClntProxRadPckts Counter32,
    sdpBindDhcpStatsClntProxLSPckts  Counter32,
    sdpBindDhcpStatsGenReleasePckts  Counter32,
    sdpBindDhcpStatsGenForceRenPckts Counter32,
    sdpBindDhcpStatsClntProxUDBPckts Counter32,
    sdpBindDhcpStatsClntProxNqPckts  Counter32
}

sdpBindDhcpStatsClntSnoopdPckts  OBJECT-TYPE
    SYNTAX      Counter32
    MAX-ACCESS  read-only
    STATUS      current
    DESCRIPTION
        "The value of the object sdpBindDhcpStatsClntSnoopdPckts
         indicates the number of  DHCP client packets that have
         been snooped on this SDP bind."
    ::= { sdpBindDhcpStatsEntry 1 }

sdpBindDhcpStatsSrvrSnoopdPckts  OBJECT-TYPE
    SYNTAX      Counter32
    MAX-ACCESS  read-only
    STATUS      current
    DESCRIPTION
        "The value of the object sdpBindDhcpStatsSrvrSnoopdPckts
         indicates the number of  DHCP server packets that have
         been snooped on this SDP bind."
    ::= { sdpBindDhcpStatsEntry 2 }

sdpBindDhcpStatsClntForwdPckts   OBJECT-TYPE
    SYNTAX      Counter32
    MAX-ACCESS  read-only
    STATUS      current
    DESCRIPTION
        "The value of the object sdpBindDhcpStatsClntForwdPckts
         indicates the number of  DHCP  client  packets  that have
         been forwarded on this SDP bind."
    ::= { sdpBindDhcpStatsEntry 3 }

sdpBindDhcpStatsSrvrForwdPckts   OBJECT-TYPE
    SYNTAX      Counter32
    MAX-ACCESS  read-only
    STATUS      current
    DESCRIPTION
        "The value of the object sdpBindDhcpStatsSrvrForwdPckts
         indicates the number of  DHCP  server  packets  that have
         been forwarded on this SDP bind."
    ::= { sdpBindDhcpStatsEntry 4 }

sdpBindDhcpStatsClntDropdPckts   OBJECT-TYPE
    SYNTAX      Counter32
    MAX-ACCESS  read-only
    STATUS      current
    DESCRIPTION
        "The value of the object sdpBindDhcpStatsClntDropdPckts
         indicates the number of  DHCP client packets that have
         been dropped on this SDP bind."
    ::= { sdpBindDhcpStatsEntry 5 }

sdpBindDhcpStatsSrvrDropdPckts   OBJECT-TYPE
    SYNTAX      Counter32
    MAX-ACCESS  read-only
    STATUS      current
    DESCRIPTION
        "The value of the object sdpBindDhcpStatsSrvrDropdPckts
         indicates the number of  DHCP server packets that have
         been dropped on this SDP bind."
    ::= { sdpBindDhcpStatsEntry 6 }

sdpBindDhcpStatsClntProxRadPckts OBJECT-TYPE
    SYNTAX      Counter32
    MAX-ACCESS  read-only
    STATUS      current
    DESCRIPTION
        "The value of the object sdpBindDhcpStatsClntProxRadPckts indicates the
         number of DHCP client packets that have been proxied on this SDP bind
         based on data received from a RADIUS server."
    ::= { sdpBindDhcpStatsEntry 7 }

sdpBindDhcpStatsClntProxLSPckts  OBJECT-TYPE
    SYNTAX      Counter32
    MAX-ACCESS  read-only
    STATUS      current
    DESCRIPTION
        "The value of the object sdpBindDhcpStatsClntProxLSPckts indicates the
         number of DHCP client packets that have been proxied on this SDP bind
         based on a lease state. The lease itself can have been obtained from a
         DHCP or RADIUS server. This is the so called lease split
         functionality."
    ::= { sdpBindDhcpStatsEntry 8 }

sdpBindDhcpStatsGenReleasePckts  OBJECT-TYPE
    SYNTAX      Counter32
    MAX-ACCESS  read-only
    STATUS      current
    DESCRIPTION
        "The value of the object sdpBindDhcpStatsGenReleasePckts indicates the
         number of DHCP RELEASE messages spoofed on this SDP bind to the DHCP
         server."
    ::= { sdpBindDhcpStatsEntry 9 }

sdpBindDhcpStatsGenForceRenPckts OBJECT-TYPE
    SYNTAX      Counter32
    MAX-ACCESS  read-only
    STATUS      current
    DESCRIPTION
        "The value of the object sdpBindDhcpStatsGenForceRenPckts indicates the
         number of DHCP FORCERENEW messages spoofed on this SDP bind to the
         DHCP clients."
    ::= { sdpBindDhcpStatsEntry 10 }

sdpBindDhcpStatsClntProxUDBPckts OBJECT-TYPE
    SYNTAX      Counter32
    MAX-ACCESS  read-only
    STATUS      current
    DESCRIPTION
        "The value of the object sdpBindDhcpStatsClntProxUDBPckts indicates the
         number of DHCP client packets that have been proxied on the local user
         database."
    ::= { sdpBindDhcpStatsEntry 11 }

sdpBindDhcpStatsClntProxNqPckts  OBJECT-TYPE
    SYNTAX      Counter32
    MAX-ACCESS  read-only
    STATUS      current
    DESCRIPTION
        "The value of the object sdpBindDhcpStatsClntProxNqPckts indicates the
         number of DHCP client packets that have been proxied on this SDP bind
         based on data received from a Diameter NASREQ server."
    ::= { sdpBindDhcpStatsEntry 12 }

sdpBindIpipeTable                OBJECT-TYPE
    SYNTAX      SEQUENCE OF SdpBindIpipeEntry
    MAX-ACCESS  not-accessible
    STATUS      current
    DESCRIPTION
        "The sdpBindIpipeTable has an entry for each IPIPE sdpBind configured
         on this system."
    ::= { tmnxSdpObjs 11 }

sdpBindIpipeEntry                OBJECT-TYPE
    SYNTAX      SdpBindIpipeEntry
    MAX-ACCESS  not-accessible
    STATUS      current
    DESCRIPTION
        "Each row entry represents a particular sdpBind related to a particular
         IPIPE service entry. Entries are created/deleted by the user."
    INDEX       {
        svcId,
        sdpBindId
    }
    ::= { sdpBindIpipeTable 1 }

SdpBindIpipeEntry                ::= SEQUENCE
{
    sdpBindIpipeCeInetAddressType    InetAddressType,
    sdpBindIpipeCeInetAddress        InetAddress,
    sdpBindIpipePeerCeInetAddrType   InetAddressType,
    sdpBindIpipePeerCeInetAddr       InetAddress,
    sdpBindIpipePeerIpv6Capability   TruthValue,
    sdpBindIpipePeerLLCeInetAddr     InetAddress,
    sdpBindIpipePeerGlobalCeInetAddr InetAddress
}

sdpBindIpipeCeInetAddressType    OBJECT-TYPE
    SYNTAX      InetAddressType
    MAX-ACCESS  read-write
    STATUS      current
    DESCRIPTION
        "The value of the object sdpBindIpipeCeInetAddressType
         specifies the address type of the IP address of the CE
            device reachable through this IPIPE SDP binding.

         This object is only configurable if the value of
         'svcIpipeCeAddressDiscovery' is 'disabled."
    ::= { sdpBindIpipeEntry 1 }

sdpBindIpipeCeInetAddress        OBJECT-TYPE
    SYNTAX      InetAddress (SIZE (0|4))
    MAX-ACCESS  read-write
    STATUS      current
    DESCRIPTION
        "The type of this address is determined by the value of the
         sdpBindIpipeCeInetAddressType object.

         This object specifies the IPv4 address of the CE device reachable
         through this SDP binding.

         This object is only configurable if the value of
         'svcIpipeCeAddressDiscovery' is 'disabled."
    ::= { sdpBindIpipeEntry 2 }

sdpBindIpipePeerCeInetAddrType   OBJECT-TYPE
    SYNTAX      InetAddressType
    MAX-ACCESS  read-only
    STATUS      current
    DESCRIPTION
        "If the value of 'svcIpipeCeAddressDiscovery' is enabled,
         the value of the object sdpBindIpipeCeInetAddressType
         indicates the address type of the IP address of the CE
            device that is learned via LDP on this IPIPE SDP binding."
    ::= { sdpBindIpipeEntry 3 }

sdpBindIpipePeerCeInetAddr       OBJECT-TYPE
    SYNTAX      InetAddress (SIZE (0|4))
    MAX-ACCESS  read-only
    STATUS      current
    DESCRIPTION
        "If the value of 'svcIpipeCeAddressDiscovery' is enabled, the type of
         this address is determined by the value of the
         sdpBindIpipeCeInetAddressType object.

         This object indicates the IPv4 address of the
            CE device that is learned via LDP on this SDP binding."
    ::= { sdpBindIpipeEntry 4 }

sdpBindIpipePeerIpv6Capability   OBJECT-TYPE
    SYNTAX      TruthValue
    MAX-ACCESS  read-only
    STATUS      current
    DESCRIPTION
        "The value of sdpBindIpipePeerIpv6Capability indicates whether the far
         end sent us the IPv6 Stack capability TLV."
    ::= { sdpBindIpipeEntry 5 }

sdpBindIpipePeerLLCeInetAddr     OBJECT-TYPE
    SYNTAX      InetAddress (SIZE (0|16))
    MAX-ACCESS  read-only
    STATUS      current
    DESCRIPTION
        "If the value of svcIpipeIpv6CeAddressDiscovery is
         'enabled (1)', this object indicates the discovered link
            local IPv6 address of the far end CE device that is learned
         via NS/NA messages received on this SDP binding."
    ::= { sdpBindIpipeEntry 6 }

sdpBindIpipePeerGlobalCeInetAddr OBJECT-TYPE
    SYNTAX      InetAddress (SIZE (0|16))
    MAX-ACCESS  read-only
    STATUS      current
    DESCRIPTION
        "If the value of svcIpipeIpv6CeAddressDiscovery is
         'enabled (1)', this object indicates the discovered global
            IPv6 address of the far end CE device that is learned via
         NS/NA messages received on this SDP binding."
    ::= { sdpBindIpipeEntry 7 }

sdpFCMappingTable                OBJECT-TYPE
    SYNTAX      SEQUENCE OF SdpFCMappingEntry
    MAX-ACCESS  not-accessible
    STATUS      current
    DESCRIPTION
        "The sdpFCMappingTable has an entry for each FC mapping on an SDP
         configured on this system."
    ::= { tmnxSdpObjs 12 }

sdpFCMappingEntry                OBJECT-TYPE
    SYNTAX      SdpFCMappingEntry
    MAX-ACCESS  not-accessible
    STATUS      current
    DESCRIPTION
        "Each row entry represents a particular FC to LSP ID mapping on an SDP.
         Entries are created/deleted by the user."
    INDEX       {
        sdpId,
        sdpFCMappingFCName
    }
    ::= { sdpFCMappingTable 1 }

SdpFCMappingEntry                ::= SEQUENCE
{
    sdpFCMappingFCName               TNamedItem,
    sdpFCMappingRowStatus            RowStatus,
    sdpFCMappingLspId                TmnxVRtrMplsLspID
}

sdpFCMappingFCName               OBJECT-TYPE
    SYNTAX      TNamedItem
    MAX-ACCESS  not-accessible
    STATUS      current
    DESCRIPTION
        "The value of sdpFCMappingFCName specifies the forwarding class for
         which this mapping is defined, in the SDP indexed by 'sdpId'."
    ::= { sdpFCMappingEntry 1 }

sdpFCMappingRowStatus            OBJECT-TYPE
    SYNTAX      RowStatus
    MAX-ACCESS  read-create
    STATUS      current
    DESCRIPTION
        "The value of sdpFCMappingRowStatus is used for the creation and
         deletion of forwarding class to LSP mappings."
    ::= { sdpFCMappingEntry 2 }

sdpFCMappingLspId                OBJECT-TYPE
    SYNTAX      TmnxVRtrMplsLspID
    MAX-ACCESS  read-create
    STATUS      current
    DESCRIPTION
        "The value of sdpFCMappingLspId specifies the LSP ID that traffic
         corresponding to the class specified in sdpFCMappingFCName will be
         forwarded on. This object MUST be specified at row creation time."
    ::= { sdpFCMappingEntry 3 }

sdpBindTlsMfibAllowedMdaTable    OBJECT-TYPE
    SYNTAX      SEQUENCE OF SdpBindTlsMfibAllowedMdaEntry
    MAX-ACCESS  not-accessible
    STATUS      current
    DESCRIPTION
        "The sdpBindTlsMfibAllowedMdaTable has an entry for each MFIB allowed
         MDA destination for an SDP Binding configured in the system."
    ::= { tmnxSdpObjs 13 }

sdpBindTlsMfibAllowedMdaEntry    OBJECT-TYPE
    SYNTAX      SdpBindTlsMfibAllowedMdaEntry
    MAX-ACCESS  not-accessible
    STATUS      current
    DESCRIPTION
        "Each row entry represents an MFIB allowed MDA destination for an SDP
         Binding configured in the system. Entries can be created and deleted
         via SNMP SET operations on the object sdpBindTlsMfibMdaRowStatus."
    INDEX       {
        svcId,
        sdpBindId,
        tmnxChassisIndex,
        tmnxCardSlotNum,
        tmnxMDASlotNum
    }
    ::= { sdpBindTlsMfibAllowedMdaTable 1 }

SdpBindTlsMfibAllowedMdaEntry    ::= SEQUENCE
{ sdpBindTlsMfibMdaRowStatus       RowStatus }

sdpBindTlsMfibMdaRowStatus       OBJECT-TYPE
    SYNTAX      RowStatus
    MAX-ACCESS  read-create
    STATUS      current
    DESCRIPTION
        "The value of sdpBindTlsMfibMdaRowStatus controls the creation and
         deletion of rows in this table."
    ::= { sdpBindTlsMfibAllowedMdaEntry 1 }

sdpBindCpipeTable                OBJECT-TYPE
    SYNTAX      SEQUENCE OF SdpBindCpipeEntry
    MAX-ACCESS  not-accessible
    STATUS      current
    DESCRIPTION
        "The sdpBindCpipeTable has an entry for each cpipe sdpBind configured
         on this system."
    ::= { tmnxSdpObjs 15 }

sdpBindCpipeEntry                OBJECT-TYPE
    SYNTAX      SdpBindCpipeEntry
    MAX-ACCESS  not-accessible
    STATUS      current
    DESCRIPTION
        "Each row entry represents a particular sdpBind related to a particular
         Cpipe service entry. Entries are created/deleted by the user."
    INDEX       {
        svcId,
        sdpBindId
    }
    ::= { sdpBindCpipeTable 1 }

SdpBindCpipeEntry                ::= SEQUENCE
{
    sdpBindCpipeLocalPayloadSize     Unsigned32,
    sdpBindCpipePeerPayloadSize      Unsigned32,
    sdpBindCpipeLocalBitrate         Unsigned32,
    sdpBindCpipePeerBitrate          Unsigned32,
    sdpBindCpipeLocalSigPkts         TdmOptionsSigPkts,
    sdpBindCpipePeerSigPkts          TdmOptionsSigPkts,
    sdpBindCpipeLocalCasTrunkFraming TdmOptionsCasTrunkFraming,
    sdpBindCpipePeerCasTrunkFraming  TdmOptionsCasTrunkFraming,
    sdpBindCpipeLocalUseRtpHeader    TruthValue,
    sdpBindCpipePeerUseRtpHeader     TruthValue,
    sdpBindCpipeLocalDifferential    TruthValue,
    sdpBindCpipePeerDifferential     TruthValue,
    sdpBindCpipeLocalTimestampFreq   Unsigned32,
    sdpBindCpipePeerTimestampFreq    Unsigned32
}

sdpBindCpipeLocalPayloadSize     OBJECT-TYPE
    SYNTAX      Unsigned32
    UNITS       "bytes"
    MAX-ACCESS  read-only
    STATUS      current
    DESCRIPTION
        "This object indicates the local payload size (in bytes)."
    ::= { sdpBindCpipeEntry 1 }

sdpBindCpipePeerPayloadSize      OBJECT-TYPE
    SYNTAX      Unsigned32
    UNITS       "bytes"
    MAX-ACCESS  read-only
    STATUS      current
    DESCRIPTION
        "This object indicates the remote payload size (in bytes). If there is
         no remote peer, or if the label mapping has not been received, or if
         this value has not been received from the remote peer then this object
         will be zero (0)."
    ::= { sdpBindCpipeEntry 2 }

sdpBindCpipeLocalBitrate         OBJECT-TYPE
    SYNTAX      Unsigned32
    UNITS       "sixty-four kilobps"
    MAX-ACCESS  read-only
    STATUS      current
    DESCRIPTION
        "This object indicates the local bit-rate in multiples of 64 Kbit/s."
    ::= { sdpBindCpipeEntry 3 }

sdpBindCpipePeerBitrate          OBJECT-TYPE
    SYNTAX      Unsigned32
    UNITS       "sixty-four kilobps"
    MAX-ACCESS  read-only
    STATUS      current
    DESCRIPTION
        "This object indicates the remote bit-rate in multiples of 64 Kbit/s.
         If there is no remote peer, or if the label mapping has not been
         received, or if this value has not been received from the remote peer
         then this object will be zero (0)."
    ::= { sdpBindCpipeEntry 4 }

sdpBindCpipeLocalSigPkts         OBJECT-TYPE
    SYNTAX      TdmOptionsSigPkts
    MAX-ACCESS  read-only
    STATUS      current
    DESCRIPTION
        "This object indicates the local CE application signalling packets
         mode."
    ::= { sdpBindCpipeEntry 5 }

sdpBindCpipePeerSigPkts          OBJECT-TYPE
    SYNTAX      TdmOptionsSigPkts
    MAX-ACCESS  read-only
    STATUS      current
    DESCRIPTION
        "This object indicates the remote CE application signalling packets
         mode. If there is no remote peer, or if the label mapping has not been
         received, or if the remote peer does not support signalling packets
         then this object will be zero (0)."
    ::= { sdpBindCpipeEntry 6 }

sdpBindCpipeLocalCasTrunkFraming OBJECT-TYPE
    SYNTAX      TdmOptionsCasTrunkFraming
    MAX-ACCESS  read-only
    STATUS      current
    DESCRIPTION
        "This object indicates the local CAS trunk framing mode."
    ::= { sdpBindCpipeEntry 7 }

sdpBindCpipePeerCasTrunkFraming  OBJECT-TYPE
    SYNTAX      TdmOptionsCasTrunkFraming
    MAX-ACCESS  read-only
    STATUS      current
    DESCRIPTION
        "This object indicates the remote CAS trunk framing mode. If there is
         no remote peer, or if the label mapping has not been received, or if
         the remote peer does not support CAS trunk framing then this object
         will be zero (0)."
    ::= { sdpBindCpipeEntry 8 }

sdpBindCpipeLocalUseRtpHeader    OBJECT-TYPE
    SYNTAX      TruthValue
    MAX-ACCESS  read-only
    STATUS      current
    DESCRIPTION
        "This object indicates whether a RTP header is used when packets are
         transmitted to the remote peer, and the local peer expects a RTP
         header when packets are received from the remote peer."
    ::= { sdpBindCpipeEntry 9 }

sdpBindCpipePeerUseRtpHeader     OBJECT-TYPE
    SYNTAX      TruthValue
    MAX-ACCESS  read-only
    STATUS      current
    DESCRIPTION
        "This object indicates whether a RTP header is used when packets are
         transmitted by the remote peer, and the remote peer expects a RTP
         header when packets are received from the local peer. If there is no
         remote peer, or if the label mapping has not been received, or if the
         remote peer does not support RTP headers then this object will be
         'false'."
    ::= { sdpBindCpipeEntry 10 }

sdpBindCpipeLocalDifferential    OBJECT-TYPE
    SYNTAX      TruthValue
    MAX-ACCESS  read-only
    STATUS      current
    DESCRIPTION
        "This object indicates whether differential timestamp mode is used in
         the RTP header when packets are transmitted to the remote peer, and
         the local peer expects differential timestamps in the RTP header when
         packets are received from the remote peer."
    ::= { sdpBindCpipeEntry 11 }

sdpBindCpipePeerDifferential     OBJECT-TYPE
    SYNTAX      TruthValue
    MAX-ACCESS  read-only
    STATUS      current
    DESCRIPTION
        "This object indicates whether differential timestamp mode is used in
         the RTP header when packets are transmitted by the remote peer, and
         the remote peer expects differential timestamps in the RTP header when
         packets are received from the local peer. If there is no remote peer,
         or if the label mapping has not been received, or if the remote peer
         does not support differential timestamp mode then this object will be
         'false'."
    ::= { sdpBindCpipeEntry 12 }

sdpBindCpipeLocalTimestampFreq   OBJECT-TYPE
    SYNTAX      Unsigned32
    UNITS       "8 KHz"
    MAX-ACCESS  read-only
    STATUS      current
    DESCRIPTION
        "This object indicates the timestamp frequency used in the RTP header
         when packets are transmitted to the remote peer, and the local peer
         expects same timestamp frequency in the RTP header when packets are
         received from the remote peer.

         This value is in multiples of 8 KHz."
    ::= { sdpBindCpipeEntry 13 }

sdpBindCpipePeerTimestampFreq    OBJECT-TYPE
    SYNTAX      Unsigned32
    UNITS       "8 KHz"
    MAX-ACCESS  read-only
    STATUS      current
    DESCRIPTION
        "This object indicates the timestamp frequency used in the RTP header
         when packets are transmitted by the remote peer, and the remote peer
         expects the same timestamp frequency in the RTP header when packets
         are received from the local peer. If there is no remote peer, or if
         the label mapping has not been received, or if the remote peer does
         not support support RTP headers then this object will be zero (0).

         This value is in multiples of 8 KHz."
    ::= { sdpBindCpipeEntry 14 }

sdpBindTlsL2ptStatsTable         OBJECT-TYPE
    SYNTAX      SEQUENCE OF SdpBindTlsL2ptStatsEntry
    MAX-ACCESS  not-accessible
    STATUS      current
    DESCRIPTION
        "A table that contains TLS spoke SDP Bind
         Layer 2 Protocol Tunneling Statistics.
         This table complements the sdpBindTlsTable. Rows in this
         table  are  created  and  deleted automatically by the
         system."
    ::= { tmnxSdpObjs 16 }

sdpBindTlsL2ptStatsEntry         OBJECT-TYPE
    SYNTAX      SdpBindTlsL2ptStatsEntry
    MAX-ACCESS  not-accessible
    STATUS      current
    DESCRIPTION
        "TLS specific information about an SDP Bind."
    INDEX       {
        svcId,
        sdpBindId
    }
    ::= { sdpBindTlsL2ptStatsTable 1 }

SdpBindTlsL2ptStatsEntry         ::= SEQUENCE
{
    sdpBindTlsL2ptStatsLastClearedTime TimeStamp,
    sdpBindTlsL2ptStatsL2ptEncapStpConfigBpdusRx Counter32,
    sdpBindTlsL2ptStatsL2ptEncapStpConfigBpdusTx Counter32,
    sdpBindTlsL2ptStatsL2ptEncapStpRstBpdusRx Counter32,
    sdpBindTlsL2ptStatsL2ptEncapStpRstBpdusTx Counter32,
    sdpBindTlsL2ptStatsL2ptEncapStpTcnBpdusRx Counter32,
    sdpBindTlsL2ptStatsL2ptEncapStpTcnBpdusTx Counter32,
    sdpBindTlsL2ptStatsL2ptEncapPvstConfigBpdusRx Counter32,
    sdpBindTlsL2ptStatsL2ptEncapPvstConfigBpdusTx Counter32,
    sdpBindTlsL2ptStatsL2ptEncapPvstRstBpdusRx Counter32,
    sdpBindTlsL2ptStatsL2ptEncapPvstRstBpdusTx Counter32,
    sdpBindTlsL2ptStatsL2ptEncapPvstTcnBpdusRx Counter32,
    sdpBindTlsL2ptStatsL2ptEncapPvstTcnBpdusTx Counter32,
    sdpBindTlsL2ptStatsStpConfigBpdusRx Counter32,
    sdpBindTlsL2ptStatsStpConfigBpdusTx Counter32,
    sdpBindTlsL2ptStatsStpRstBpdusRx Counter32,
    sdpBindTlsL2ptStatsStpRstBpdusTx Counter32,
    sdpBindTlsL2ptStatsStpTcnBpdusRx Counter32,
    sdpBindTlsL2ptStatsStpTcnBpdusTx Counter32,
    sdpBindTlsL2ptStatsPvstConfigBpdusRx Counter32,
    sdpBindTlsL2ptStatsPvstConfigBpdusTx Counter32,
    sdpBindTlsL2ptStatsPvstRstBpdusRx Counter32,
    sdpBindTlsL2ptStatsPvstRstBpdusTx Counter32,
    sdpBindTlsL2ptStatsPvstTcnBpdusRx Counter32,
    sdpBindTlsL2ptStatsPvstTcnBpdusTx Counter32,
    sdpBindTlsL2ptStatsOtherBpdusRx  Counter32,
    sdpBindTlsL2ptStatsOtherBpdusTx  Counter32,
    sdpBindTlsL2ptStatsOtherL2ptBpdusRx Counter32,
    sdpBindTlsL2ptStatsOtherL2ptBpdusTx Counter32,
    sdpBindTlsL2ptStatsOtherInvalidBpdusRx Counter32,
    sdpBindTlsL2ptStatsOtherInvalidBpdusTx Counter32,
    sdpBindTlsL2ptStatsL2ptEncapCdpBpdusRx Counter32,
    sdpBindTlsL2ptStatsL2ptEncapCdpBpdusTx Counter32,
    sdpBindTlsL2ptStatsL2ptEncapVtpBpdusRx Counter32,
    sdpBindTlsL2ptStatsL2ptEncapVtpBpdusTx Counter32,
    sdpBindTlsL2ptStatsL2ptEncapDtpBpdusRx Counter32,
    sdpBindTlsL2ptStatsL2ptEncapDtpBpdusTx Counter32,
    sdpBindTlsL2ptStatsL2ptEncapPagpBpdusRx Counter32,
    sdpBindTlsL2ptStatsL2ptEncapPagpBpdusTx Counter32,
    sdpBindTlsL2ptStatsL2ptEncapUdldBpdusRx Counter32,
    sdpBindTlsL2ptStatsL2ptEncapUdldBpdusTx Counter32,
    sdpBindTlsL2ptStatsCdpBpdusRx    Counter32,
    sdpBindTlsL2ptStatsCdpBpdusTx    Counter32,
    sdpBindTlsL2ptStatsVtpBpdusRx    Counter32,
    sdpBindTlsL2ptStatsVtpBpdusTx    Counter32,
    sdpBindTlsL2ptStatsDtpBpdusRx    Counter32,
    sdpBindTlsL2ptStatsDtpBpdusTx    Counter32,
    sdpBindTlsL2ptStatsPagpBpdusRx   Counter32,
    sdpBindTlsL2ptStatsPagpBpdusTx   Counter32,
    sdpBindTlsL2ptStatsUdldBpdusRx   Counter32,
    sdpBindTlsL2ptStatsUdldBpdusTx   Counter32
}

sdpBindTlsL2ptStatsLastClearedTime OBJECT-TYPE
    SYNTAX      TimeStamp
    MAX-ACCESS  read-only
    STATUS      current
    DESCRIPTION
        "The value of sdpBindTlsL2ptStatsLastClearedTime indicates the last
         time that these stats were cleared. The value zero indicates that they
         have not been cleared yet."
    ::= { sdpBindTlsL2ptStatsEntry 1 }

sdpBindTlsL2ptStatsL2ptEncapStpConfigBpdusRx OBJECT-TYPE
    SYNTAX      Counter32
    MAX-ACCESS  read-only
    STATUS      current
    DESCRIPTION
        "The value of sdpBindTlsL2ptStatsL2ptEncapStpConfigBpdusRx indicates
         the number of L2PT encapsulated STP config bpdus received on this
         spoke SDP."
    ::= { sdpBindTlsL2ptStatsEntry 2 }

sdpBindTlsL2ptStatsL2ptEncapStpConfigBpdusTx OBJECT-TYPE
    SYNTAX      Counter32
    MAX-ACCESS  read-only
    STATUS      current
    DESCRIPTION
        "The value of sdpBindTlsL2ptStatsL2ptEncapStpConfigBpdusTx indicates
         the number of L2PT encapsulated STP config bpdus transmitted on this
         spoke SDP."
    ::= { sdpBindTlsL2ptStatsEntry 3 }

sdpBindTlsL2ptStatsL2ptEncapStpRstBpdusRx OBJECT-TYPE
    SYNTAX      Counter32
    MAX-ACCESS  read-only
    STATUS      current
    DESCRIPTION
        "The value of sdpBindTlsL2ptStatsL2ptEncapStpRstBpdusRx indicates the
         number of L2PT encapsulated STP rst bpdus received on this spoke SDP."
    ::= { sdpBindTlsL2ptStatsEntry 4 }

sdpBindTlsL2ptStatsL2ptEncapStpRstBpdusTx OBJECT-TYPE
    SYNTAX      Counter32
    MAX-ACCESS  read-only
    STATUS      current
    DESCRIPTION
        "The value of sdpBindTlsL2ptStatsL2ptEncapStpRstBpdusTx indicates the
         number of L2PT encapsulated STP rst bpdus transmitted on this spoke
         SDP."
    ::= { sdpBindTlsL2ptStatsEntry 5 }

sdpBindTlsL2ptStatsL2ptEncapStpTcnBpdusRx OBJECT-TYPE
    SYNTAX      Counter32
    MAX-ACCESS  read-only
    STATUS      current
    DESCRIPTION
        "The value of sdpBindTlsL2ptStatsL2ptEncapStpTcnBpdusRx indicates the
         number of L2PT encapsulated STP tcn bpdus received on this spoke SDP."
    ::= { sdpBindTlsL2ptStatsEntry 6 }

sdpBindTlsL2ptStatsL2ptEncapStpTcnBpdusTx OBJECT-TYPE
    SYNTAX      Counter32
    MAX-ACCESS  read-only
    STATUS      current
    DESCRIPTION
        "The value of sdpBindTlsL2ptStatsL2ptEncapStpTcnBpdusTx indicates the
         number of L2PT encapsulated STP tcn bpdus transmitted on this spoke
         SDP."
    ::= { sdpBindTlsL2ptStatsEntry 7 }

sdpBindTlsL2ptStatsL2ptEncapPvstConfigBpdusRx OBJECT-TYPE
    SYNTAX      Counter32
    MAX-ACCESS  read-only
    STATUS      current
    DESCRIPTION
        "The value of sdpBindTlsL2ptStatsL2ptEncapPvstConfigBpdusRx indicates
         the number of L2PT encapsulated PVST config bpdus received on this
         spoke SDP."
    ::= { sdpBindTlsL2ptStatsEntry 8 }

sdpBindTlsL2ptStatsL2ptEncapPvstConfigBpdusTx OBJECT-TYPE
    SYNTAX      Counter32
    MAX-ACCESS  read-only
    STATUS      current
    DESCRIPTION
        "The value of sdpBindTlsL2ptStatsL2ptEncapPvstConfigBpdusTx indicates
         the number of L2PT encapsulated PVST config bpdus transmitted on this
         spoke SDP."
    ::= { sdpBindTlsL2ptStatsEntry 9 }

sdpBindTlsL2ptStatsL2ptEncapPvstRstBpdusRx OBJECT-TYPE
    SYNTAX      Counter32
    MAX-ACCESS  read-only
    STATUS      current
    DESCRIPTION
        "The value of sdpBindTlsL2ptStatsL2ptEncapPvstRstBpdusRx indicates the
         number of L2PT encapsulated PVST rst bpdus received on this spoke SDP."
    ::= { sdpBindTlsL2ptStatsEntry 10 }

sdpBindTlsL2ptStatsL2ptEncapPvstRstBpdusTx OBJECT-TYPE
    SYNTAX      Counter32
    MAX-ACCESS  read-only
    STATUS      current
    DESCRIPTION
        "The value of sdpBindTlsL2ptStatsL2ptEncapPvstRstBpdusTx indicates the
         number of L2PT encapsulated PVST rst bpdus transmitted on this spoke
         SDP."
    ::= { sdpBindTlsL2ptStatsEntry 11 }

sdpBindTlsL2ptStatsL2ptEncapPvstTcnBpdusRx OBJECT-TYPE
    SYNTAX      Counter32
    MAX-ACCESS  read-only
    STATUS      current
    DESCRIPTION
        "The value of sdpBindTlsL2ptStatsL2ptEncapPvstTcnBpdusRx indicates the
         number of L2PT encapsulated PVST tcn bpdus received on this spoke SDP."
    ::= { sdpBindTlsL2ptStatsEntry 12 }

sdpBindTlsL2ptStatsL2ptEncapPvstTcnBpdusTx OBJECT-TYPE
    SYNTAX      Counter32
    MAX-ACCESS  read-only
    STATUS      current
    DESCRIPTION
        "The value of sdpBindTlsL2ptStatsL2ptEncapPvstTcnBpdusTx indicates the
         number of L2PT encapsulated PVST tcn bpdus transmitted on this spoke
         SDP."
    ::= { sdpBindTlsL2ptStatsEntry 13 }

sdpBindTlsL2ptStatsStpConfigBpdusRx OBJECT-TYPE
    SYNTAX      Counter32
    MAX-ACCESS  read-only
    STATUS      current
    DESCRIPTION
        "The value of sdpBindTlsL2ptStatsStpConfigBpdusRx indicates the number
         of STP config bpdus received on this spoke SDP."
    ::= { sdpBindTlsL2ptStatsEntry 14 }

sdpBindTlsL2ptStatsStpConfigBpdusTx OBJECT-TYPE
    SYNTAX      Counter32
    MAX-ACCESS  read-only
    STATUS      current
    DESCRIPTION
        "The value of sdpBindTlsL2ptStatsStpConfigBpdusTx indicates the number
         of STP config bpdus transmitted on this spoke SDP."
    ::= { sdpBindTlsL2ptStatsEntry 15 }

sdpBindTlsL2ptStatsStpRstBpdusRx OBJECT-TYPE
    SYNTAX      Counter32
    MAX-ACCESS  read-only
    STATUS      current
    DESCRIPTION
        "The value of sdpBindTlsL2ptStatsStpRstBpdusRx indicates the number of
         STP rst bpdus received on this spoke SDP."
    ::= { sdpBindTlsL2ptStatsEntry 16 }

sdpBindTlsL2ptStatsStpRstBpdusTx OBJECT-TYPE
    SYNTAX      Counter32
    MAX-ACCESS  read-only
    STATUS      current
    DESCRIPTION
        "The value of sdpBindTlsL2ptStatsStpRstBpdusTx indicates the number of
         STP rst bpdus transmitted on this spoke SDP."
    ::= { sdpBindTlsL2ptStatsEntry 17 }

sdpBindTlsL2ptStatsStpTcnBpdusRx OBJECT-TYPE
    SYNTAX      Counter32
    MAX-ACCESS  read-only
    STATUS      current
    DESCRIPTION
        "The value of sdpBindTlsL2ptStatsStpTcnBpdusRx indicates the number of
         STP tcn bpdus received on this spoke SDP."
    ::= { sdpBindTlsL2ptStatsEntry 18 }

sdpBindTlsL2ptStatsStpTcnBpdusTx OBJECT-TYPE
    SYNTAX      Counter32
    MAX-ACCESS  read-only
    STATUS      current
    DESCRIPTION
        "The value of sdpBindTlsL2ptStatsStpTcnBpdusTx indicates the number of
         STP tcn bpdus transmitted on this spoke SDP."
    ::= { sdpBindTlsL2ptStatsEntry 19 }

sdpBindTlsL2ptStatsPvstConfigBpdusRx OBJECT-TYPE
    SYNTAX      Counter32
    MAX-ACCESS  read-only
    STATUS      current
    DESCRIPTION
        "The value of sdpBindTlsL2ptStatsPvstConfigBpdusRx indicates the number
         of PVST config bpdus received on this spoke SDP."
    ::= { sdpBindTlsL2ptStatsEntry 20 }

sdpBindTlsL2ptStatsPvstConfigBpdusTx OBJECT-TYPE
    SYNTAX      Counter32
    MAX-ACCESS  read-only
    STATUS      current
    DESCRIPTION
        "The value of sdpBindTlsL2ptStatsPvstConfigBpdusTx indicates the number
         of PVST config bpdus transmitted on this spoke SDP."
    ::= { sdpBindTlsL2ptStatsEntry 21 }

sdpBindTlsL2ptStatsPvstRstBpdusRx OBJECT-TYPE
    SYNTAX      Counter32
    MAX-ACCESS  read-only
    STATUS      current
    DESCRIPTION
        "The value of sdpBindTlsL2ptStatsPvstRstBpdusRx indicates the number of
         PVST rst bpdus received on this spoke SDP."
    ::= { sdpBindTlsL2ptStatsEntry 22 }

sdpBindTlsL2ptStatsPvstRstBpdusTx OBJECT-TYPE
    SYNTAX      Counter32
    MAX-ACCESS  read-only
    STATUS      current
    DESCRIPTION
        "The value of sdpBindTlsL2ptStatsPvstRstBpdusTx indicates the number of
         PVST rst bpdus transmitted on this spoke SDP."
    ::= { sdpBindTlsL2ptStatsEntry 23 }

sdpBindTlsL2ptStatsPvstTcnBpdusRx OBJECT-TYPE
    SYNTAX      Counter32
    MAX-ACCESS  read-only
    STATUS      current
    DESCRIPTION
        "The value of sdpBindTlsL2ptStatsPvstTcnBpdusRx indicates the number of
         PVST tcn bpdus received on this spoke SDP."
    ::= { sdpBindTlsL2ptStatsEntry 24 }

sdpBindTlsL2ptStatsPvstTcnBpdusTx OBJECT-TYPE
    SYNTAX      Counter32
    MAX-ACCESS  read-only
    STATUS      current
    DESCRIPTION
        "The value of sdpBindTlsL2ptStatsPvstTcnBpdusTx indicates the number of
         PVST tcn bpdus transmitted on this spoke SDP."
    ::= { sdpBindTlsL2ptStatsEntry 25 }

sdpBindTlsL2ptStatsOtherBpdusRx  OBJECT-TYPE
    SYNTAX      Counter32
    MAX-ACCESS  read-only
    STATUS      current
    DESCRIPTION
        "The value of sdpBindTlsL2ptStatsOtherBpdusRx indicates the number of
         other bpdus received on this spoke SDP."
    ::= { sdpBindTlsL2ptStatsEntry 26 }

sdpBindTlsL2ptStatsOtherBpdusTx  OBJECT-TYPE
    SYNTAX      Counter32
    MAX-ACCESS  read-only
    STATUS      current
    DESCRIPTION
        "The value of sdpBindTlsL2ptStatsOtherBpdusTx indicates the number of
         other bpdus transmitted on this spoke SDP."
    ::= { sdpBindTlsL2ptStatsEntry 27 }

sdpBindTlsL2ptStatsOtherL2ptBpdusRx OBJECT-TYPE
    SYNTAX      Counter32
    MAX-ACCESS  read-only
    STATUS      current
    DESCRIPTION
        "The value of sdpBindTlsL2ptStatsOtherL2ptBpdusRx indicates the number
         of other L2PT bpdus received on this spoke SDP."
    ::= { sdpBindTlsL2ptStatsEntry 28 }

sdpBindTlsL2ptStatsOtherL2ptBpdusTx OBJECT-TYPE
    SYNTAX      Counter32
    MAX-ACCESS  read-only
    STATUS      current
    DESCRIPTION
        "The value of sdpBindTlsL2ptStatsOtherL2ptBpdusTx indicates the number
         of other L2PT bpdus transmitted on this spoke SDP."
    ::= { sdpBindTlsL2ptStatsEntry 29 }

sdpBindTlsL2ptStatsOtherInvalidBpdusRx OBJECT-TYPE
    SYNTAX      Counter32
    MAX-ACCESS  read-only
    STATUS      current
    DESCRIPTION
        "The value of sdpBindTlsL2ptStatsOtherInvalidBpdusRx indicates the
         number of other invalid bpdus received on this spoke SDP."
    ::= { sdpBindTlsL2ptStatsEntry 30 }

sdpBindTlsL2ptStatsOtherInvalidBpdusTx OBJECT-TYPE
    SYNTAX      Counter32
    MAX-ACCESS  read-only
    STATUS      current
    DESCRIPTION
        "The value of sdpBindTlsL2ptStatsOtherInvalidBpdusTx indicates the
         number of other invalid bpdus transmitted on this spoke SDP."
    ::= { sdpBindTlsL2ptStatsEntry 31 }

sdpBindTlsL2ptStatsL2ptEncapCdpBpdusRx OBJECT-TYPE
    SYNTAX      Counter32
    MAX-ACCESS  read-only
    STATUS      current
    DESCRIPTION
        "The value of sdpBindTlsL2ptStatsL2ptEncapCdpBpdusRx indicates the
         number of L2PT encapsulated CDP bpdus received on this spoke SDP."
    ::= { sdpBindTlsL2ptStatsEntry 32 }

sdpBindTlsL2ptStatsL2ptEncapCdpBpdusTx OBJECT-TYPE
    SYNTAX      Counter32
    MAX-ACCESS  read-only
    STATUS      current
    DESCRIPTION
        "The value of sdpBindTlsL2ptStatsL2ptEncapCdpBpdusTx indicates the
         number of L2PT encapsulated CDP bpdus transmitted on this spoke SDP."
    ::= { sdpBindTlsL2ptStatsEntry 33 }

sdpBindTlsL2ptStatsL2ptEncapVtpBpdusRx OBJECT-TYPE
    SYNTAX      Counter32
    MAX-ACCESS  read-only
    STATUS      current
    DESCRIPTION
        "The value of sdpBindTlsL2ptStatsL2ptEncapVtpBpdusRx indicates the
         number of L2PT encapsulated VTP bpdus received on this spoke SDP."
    ::= { sdpBindTlsL2ptStatsEntry 34 }

sdpBindTlsL2ptStatsL2ptEncapVtpBpdusTx OBJECT-TYPE
    SYNTAX      Counter32
    MAX-ACCESS  read-only
    STATUS      current
    DESCRIPTION
        "The value of sdpBindTlsL2ptStatsL2ptEncapVtpBpdusTx indicates the
         number of L2PT encapsulated VTP bpdus transmitted on this spoke SDP."
    ::= { sdpBindTlsL2ptStatsEntry 35 }

sdpBindTlsL2ptStatsL2ptEncapDtpBpdusRx OBJECT-TYPE
    SYNTAX      Counter32
    MAX-ACCESS  read-only
    STATUS      current
    DESCRIPTION
        "The value of sdpBindTlsL2ptStatsL2ptEncapDtpBpdusRx indicates the
         number of L2PT encapsulated DTP bpdus received on this spoke SDP."
    ::= { sdpBindTlsL2ptStatsEntry 36 }

sdpBindTlsL2ptStatsL2ptEncapDtpBpdusTx OBJECT-TYPE
    SYNTAX      Counter32
    MAX-ACCESS  read-only
    STATUS      current
    DESCRIPTION
        "The value of sdpBindTlsL2ptStatsL2ptEncapDtpBpdusTx indicates the
         number of L2PT encapsulated DTP bpdus transmitted on this spoke SDP."
    ::= { sdpBindTlsL2ptStatsEntry 37 }

sdpBindTlsL2ptStatsL2ptEncapPagpBpdusRx OBJECT-TYPE
    SYNTAX      Counter32
    MAX-ACCESS  read-only
    STATUS      current
    DESCRIPTION
        "The value of sdpBindTlsL2ptStatsL2ptEncapPagpBpdusRx indicates the
         number of L2PT encapsulated PAGP bpdus received on this spoke SDP."
    ::= { sdpBindTlsL2ptStatsEntry 38 }

sdpBindTlsL2ptStatsL2ptEncapPagpBpdusTx OBJECT-TYPE
    SYNTAX      Counter32
    MAX-ACCESS  read-only
    STATUS      current
    DESCRIPTION
        "The value of sdpBindTlsL2ptStatsL2ptEncapPagpBpdusTx indicates the
         number of L2PT encapsulated PAGP bpdus transmitted on this spoke SDP."
    ::= { sdpBindTlsL2ptStatsEntry 39 }

sdpBindTlsL2ptStatsL2ptEncapUdldBpdusRx OBJECT-TYPE
    SYNTAX      Counter32
    MAX-ACCESS  read-only
    STATUS      current
    DESCRIPTION
        "The value of sdpBindTlsL2ptStatsL2ptEncapUdldBpdusRx indicates the
         number of L2PT encapsulated UDLD bpdus received on this spoke SDP."
    ::= { sdpBindTlsL2ptStatsEntry 40 }

sdpBindTlsL2ptStatsL2ptEncapUdldBpdusTx OBJECT-TYPE
    SYNTAX      Counter32
    MAX-ACCESS  read-only
    STATUS      current
    DESCRIPTION
        "The value of sdpBindTlsL2ptStatsL2ptEncapUdldBpdusTx indicates the
         number of L2PT encapsulated UDLD bpdus transmitted on this spoke SDP."
    ::= { sdpBindTlsL2ptStatsEntry 41 }

sdpBindTlsL2ptStatsCdpBpdusRx    OBJECT-TYPE
    SYNTAX      Counter32
    MAX-ACCESS  read-only
    STATUS      current
    DESCRIPTION
        "The value of sdpBindTlsL2ptStatsCdpBpdusRx indicates the number of CDP
         bpdus received on this spoke SDP."
    ::= { sdpBindTlsL2ptStatsEntry 42 }

sdpBindTlsL2ptStatsCdpBpdusTx    OBJECT-TYPE
    SYNTAX      Counter32
    MAX-ACCESS  read-only
    STATUS      current
    DESCRIPTION
        "The value of sdpBindTlsL2ptStatsCdpBpdusTx indicates the number of CDP
         bpdus transmitted on this spoke SDP."
    ::= { sdpBindTlsL2ptStatsEntry 43 }

sdpBindTlsL2ptStatsVtpBpdusRx    OBJECT-TYPE
    SYNTAX      Counter32
    MAX-ACCESS  read-only
    STATUS      current
    DESCRIPTION
        "The value of sdpBindTlsL2ptStatsVtpBpdusRx indicates the number of VTP
         bpdus received on this spoke SDP."
    ::= { sdpBindTlsL2ptStatsEntry 44 }

sdpBindTlsL2ptStatsVtpBpdusTx    OBJECT-TYPE
    SYNTAX      Counter32
    MAX-ACCESS  read-only
    STATUS      current
    DESCRIPTION
        "The value of sdpBindTlsL2ptStatsVtpBpdusTx indicates the number of VTP
         bpdus transmitted on this spoke SDP."
    ::= { sdpBindTlsL2ptStatsEntry 45 }

sdpBindTlsL2ptStatsDtpBpdusRx    OBJECT-TYPE
    SYNTAX      Counter32
    MAX-ACCESS  read-only
    STATUS      current
    DESCRIPTION
        "The value of sdpBindTlsL2ptStatsDtpBpdusRx indicates the number of DTP
         bpdus received on this spoke SDP."
    ::= { sdpBindTlsL2ptStatsEntry 46 }

sdpBindTlsL2ptStatsDtpBpdusTx    OBJECT-TYPE
    SYNTAX      Counter32
    MAX-ACCESS  read-only
    STATUS      current
    DESCRIPTION
        "The value of sdpBindTlsL2ptStatsDtpBpdusTx indicates the number of DTP
         bpdus transmitted on this spoke SDP."
    ::= { sdpBindTlsL2ptStatsEntry 47 }

sdpBindTlsL2ptStatsPagpBpdusRx   OBJECT-TYPE
    SYNTAX      Counter32
    MAX-ACCESS  read-only
    STATUS      current
    DESCRIPTION
        "The value of sdpBindTlsL2ptStatsPagpBpdusRx indicates the number of
         PAGP bpdus received on this spoke SDP."
    ::= { sdpBindTlsL2ptStatsEntry 48 }

sdpBindTlsL2ptStatsPagpBpdusTx   OBJECT-TYPE
    SYNTAX      Counter32
    MAX-ACCESS  read-only
    STATUS      current
    DESCRIPTION
        "The value of sdpBindTlsL2ptStatsPagpBpdusTx indicates the number of
         PAGP bpdus transmitted on this spoke SDP."
    ::= { sdpBindTlsL2ptStatsEntry 49 }

sdpBindTlsL2ptStatsUdldBpdusRx   OBJECT-TYPE
    SYNTAX      Counter32
    MAX-ACCESS  read-only
    STATUS      current
    DESCRIPTION
        "The value of sdpBindTlsL2ptStatsUdldBpdusRx indicates the number of
         UDLD bpdus received on this spoke SDP."
    ::= { sdpBindTlsL2ptStatsEntry 50 }

sdpBindTlsL2ptStatsUdldBpdusTx   OBJECT-TYPE
    SYNTAX      Counter32
    MAX-ACCESS  read-only
    STATUS      current
    DESCRIPTION
        "The value of sdpBindTlsL2ptStatsUdldBpdusTx indicates the number of
         UDLD bpdus transmitted on this spoke SDP."
    ::= { sdpBindTlsL2ptStatsEntry 51 }

pwTemplateTableLastChanged       OBJECT-TYPE
    SYNTAX      TimeStamp
    MAX-ACCESS  read-only
    STATUS      current
    DESCRIPTION
        "The value of pwTemplateTableLastChanged indicates the sysUpTime at the
         time of the last modification of pwTemplateTable.

         If no changes were made to the entry since the last re-initialization
         of the local network management subsystem, then this object contains a
         zero value."
    ::= { tmnxSdpObjs 17 }

pwTemplateTable                  OBJECT-TYPE
    SYNTAX      SEQUENCE OF PwTemplateEntry
    MAX-ACCESS  not-accessible
    STATUS      current
    DESCRIPTION
        "A table that contains entries for pseudowire (PW) templates specifying
         SDP auto-binding."
    ::= { tmnxSdpObjs 18 }

pwTemplateEntry                  OBJECT-TYPE
    SYNTAX      PwTemplateEntry
    MAX-ACCESS  not-accessible
    STATUS      current
    DESCRIPTION
        "Information about a specific PW template."
    INDEX       { pwTemplateId }
    ::= { pwTemplateTable 1 }

PwTemplateEntry                  ::= SEQUENCE
{
    pwTemplateId                     PWTemplateId,
    pwTemplateRowStatus              RowStatus,
    pwTemplateLastChanged            TimeStamp,
    pwTemplateUseProvisionedSdp      TruthValue,
    pwTemplateVcType                 SdpBindVcType,
    pwTemplateAccountingPolicyId     Unsigned32,
    pwTemplateCollectAcctStats       TruthValue,
    pwTemplateMacLearning            TmnxEnabledDisabled,
    pwTemplateMacAgeing              TmnxEnabledDisabled,
    pwTemplateDiscardUnknownSource   TmnxEnabledDisabled,
    pwTemplateLimitMacMove           TlsLimitMacMove,
    pwTemplateMacPinning             TmnxEnabledDisabled,
    pwTemplateVlanVcTag              Unsigned32,
    pwTemplateMacAddressLimit        Unsigned32,
    pwTemplateShgName                TNamedItemOrEmpty,
    pwTemplateShgDescription         TItemDescription,
    pwTemplateShgRestProtSrcMac      TruthValue,
    pwTemplateShgRestUnprotDstMac    TruthValue,
    pwTemplateEgressMacFilterId      TFilterID,
    pwTemplateEgressIpFilterId       TFilterID,
    pwTemplateEgressIpv6FilterId     TFilterID,
    pwTemplateIngressMacFilterId     TFilterID,
    pwTemplateIngressIpFilterId      TFilterID,
    pwTemplateIngressIpv6FilterId    TFilterID,
    pwTemplateIgmpFastLeave          TmnxEnabledDisabled,
    pwTemplateIgmpImportPlcy         TNamedItemOrEmpty,
    pwTemplateIgmpLastMembIntvl      Unsigned32,
    pwTemplateIgmpMaxNbrGrps         Unsigned32,
    pwTemplateIgmpGenQueryIntvl      Unsigned32,
    pwTemplateIgmpQueryRespIntvl     Unsigned32,
    pwTemplateIgmpRobustCount        Unsigned32,
    pwTemplateIgmpSendQueries        TmnxEnabledDisabled,
    pwTemplateIgmpMcacPolicyName     TPolicyStatementNameOrEmpty,
    pwTemplateIgmpMcacUnconstBW      Integer32,
    pwTemplateIgmpMcacPrRsvMndBW     Integer32,
    pwTemplateIgmpVersion            TmnxIgmpVersion,
    pwTemplateForceVlanVcForwarding  TruthValue,
    pwTemplateHashLabel              TruthValue,
    pwTemplateControlWord            TruthValue,
    pwTemplateHashLabelSignalCap     TruthValue,
    pwTemplateRestProtSrcMac         TruthValue,
    pwTemplateRestProtSrcMacAction   INTEGER,
    pwTemplateAutoLearnMacProtect    TruthValue,
    pwTemplateShgRestProtSrcMacAct   INTEGER,
    pwTemplateShgAutoLearnMacProtect TruthValue,
    pwTemplateIngQoSNetworkPlcyId    TSdpIngressPolicyID,
    pwTemplateEgrQoSNetworkPlcyId    TSdpEgressPolicyID,
    pwTemplateIngQoSFpRedirectQGrp   TNamedItemOrEmpty,
    pwTemplateEgrQoSPortRedirectQGrp TNamedItemOrEmpty,
    pwTemplateIngQoSInstanceId       TQosQGrpInstanceIDorZero,
    pwTemplateEgrQoSInstanceId       TQosQGrpInstanceIDorZero,
    pwTemplateBlockOnPeerFault       TruthValue,
    pwTemplateForceQinqVcForwarding  TruthValue,
    pwTemplatePreferProvSdp          TruthValue,
    pwTemplateEntropyLabel           TruthValue,
    pwTemplateName                   TLNamedItemOrEmpty,
    pwTemplateGreDelivery            TruthValue,
    pwTemplateIngQoSNetworkPlcyName  TLNamedItemOrEmpty,
    pwTemplateEgrQoSNetworkPlcyName  TLNamedItemOrEmpty,
    pwTemplateIngressIpFilterName    TLNamedItemOrEmpty,
    pwTemplateIngressIpv6FilterName  TLNamedItemOrEmpty,
    pwTemplateIngressMacFilterName   TLNamedItemOrEmpty,
    pwTemplateEgressIpFilterName     TLNamedItemOrEmpty,
    pwTemplateEgressIpv6FilterName   TLNamedItemOrEmpty,
    pwTemplateEgressMacFilterName    TLNamedItemOrEmpty,
    pwTemplateForceQinqVcFwding      INTEGER
}

pwTemplateId                     OBJECT-TYPE
    SYNTAX      PWTemplateId
    MAX-ACCESS  not-accessible
    STATUS      current
    DESCRIPTION
        "The PW template identifier."
    ::= { pwTemplateEntry 1 }

pwTemplateRowStatus              OBJECT-TYPE
    SYNTAX      RowStatus
    MAX-ACCESS  read-create
    STATUS      current
    DESCRIPTION
        "The value of pwTemplateRowStatus is used for the creation and deletion
         of PW templates."
    ::= { pwTemplateEntry 2 }

pwTemplateLastChanged            OBJECT-TYPE
    SYNTAX      TimeStamp
    MAX-ACCESS  read-only
    STATUS      current
    DESCRIPTION
        "The value of pwTemplateLastChanged indicates the sysUpTime at the time
         of the last modification of this entry.

         If no changes were made to the entry since the last re-initialization
         of the local network management subsystem, then this object contains a
         zero value."
    ::= { pwTemplateEntry 3 }

pwTemplateUseProvisionedSdp      OBJECT-TYPE
    SYNTAX      TruthValue
    MAX-ACCESS  read-create
    STATUS      current
    DESCRIPTION
        "The value of pwTemplateUseProvisionedSdp specifies whether the to use
         an already provisioned SDP. A value of 'true' specifies that the
         tunnel manager will be consulted for an existing active SDP.
         Otherwise, a value of 'false' specifies that the default SDP template
         will be used to use for instantiation of the SDP."
    DEFVAL      { false }
    ::= { pwTemplateEntry 4 }

pwTemplateVcType                 OBJECT-TYPE
    SYNTAX      SdpBindVcType
    MAX-ACCESS  read-create
    STATUS      current
    DESCRIPTION
        "The value of pwTemplateVcType specifies the type of virtual circuit
         (VC) associated with the SDP Bind."
    DEFVAL      { ether }
    ::= { pwTemplateEntry 5 }

pwTemplateAccountingPolicyId     OBJECT-TYPE
    SYNTAX      Unsigned32 (0..99)
    MAX-ACCESS  read-create
    STATUS      current
    DESCRIPTION
        "The value of pwTemplateAccountingPolicyId specifies the policy to use
         to collect accounting statistics on the SDP Bind. The value zero
         indicates that the agent should use the default accounting policy, if
         one exists."
    DEFVAL      { 0 }
    ::= { pwTemplateEntry 6 }

pwTemplateCollectAcctStats       OBJECT-TYPE
    SYNTAX      TruthValue
    MAX-ACCESS  read-create
    STATUS      current
    DESCRIPTION
        "The value of pwTemplateCollectAcctStats specifies whether the agent
         collects accounting statistics for the SDP Bind. When the value is
         'true' the agent collects accounting statistics on the SDP Bind."
    DEFVAL      { false }
    ::= { pwTemplateEntry 7 }

pwTemplateMacLearning            OBJECT-TYPE
    SYNTAX      TmnxEnabledDisabled
    MAX-ACCESS  read-create
    STATUS      current
    DESCRIPTION
        "The value of pwTemplateMacLearning specifies whether the MAC learning
         process is enabled for the SDP Bind. The value is ignored if MAC
         learning is disabled at service level."
    DEFVAL      { enabled }
    ::= { pwTemplateEntry 8 }

pwTemplateMacAgeing              OBJECT-TYPE
    SYNTAX      TmnxEnabledDisabled
    MAX-ACCESS  read-create
    STATUS      current
    DESCRIPTION
        "The value of pwTemplateMacAgeing specifies whether the MAC aging
         process is enabled for the SDP Bind. The value is ignored if MAC aging
         is disabled at the service level."
    DEFVAL      { enabled }
    ::= { pwTemplateEntry 9 }

pwTemplateDiscardUnknownSource   OBJECT-TYPE
    SYNTAX      TmnxEnabledDisabled
    MAX-ACCESS  read-create
    STATUS      current
    DESCRIPTION
        "With the object pwTemplateMacAddressLimit a limit can be configured
         for the max number of MAC addresses that will be learned on the SDP
         Bind (only for spoke SDPs). When the limit is reached, packets with
         unknown source MAC address are forwarded by default. By setting
         sdpBindTlsDiscardUnknownSource to 'enabled', packets with unknown
         source MAC will be dropped instead."
    DEFVAL      { disabled }
    ::= { pwTemplateEntry 10 }

pwTemplateLimitMacMove           OBJECT-TYPE
    SYNTAX      TlsLimitMacMove
    MAX-ACCESS  read-create
    STATUS      current
    DESCRIPTION
        "The value of pwTemplateLimitMacMove specifies the behavior for when
         the relearn rate specified by svcTlsMacMoveMaxRate is exceeded.

         When pwTemplateLimitMacMove value is set to 'blockable'
         the agent will monitor the MAC relearn rate on the
         SDP  Bind, and it will block it when the relearn rate
         specified by svcTlsMacMoveMaxRate is exceeded. When the
         value is 'nonBlockable' the SDP Bind will not be
         blocked,  and  another  blockable  SDP Bind will be
         blocked instead."
    DEFVAL      { blockable }
    ::= { pwTemplateEntry 11 }

pwTemplateMacPinning             OBJECT-TYPE
    SYNTAX      TmnxEnabledDisabled
    MAX-ACCESS  read-create
    STATUS      current
    DESCRIPTION
        "The value of pwTemplateMacPinning specifies whether or not MAC address
         pinning is active on the SDP Bind (mesh or spoke). Setting the value
         to 'enabled' disables relearning of MAC addresses on other SAPs or
         SDPs within the same VPLS; the MAC address will hence remain attached
         to the SDP Bind for the duration of its age-timer. This object has
         effect only for MAC addresses learned via the normal MAC learning
         process, and not for entries learned via DHCP. The value will be set
         by default to 'disabled'. However for a spoke SDP that belongs to a
         residential SHG, the value is set to enabled by the system, and cannot
         be altered by the operator."
    DEFVAL      { disabled }
    ::= { pwTemplateEntry 12 }

pwTemplateVlanVcTag              OBJECT-TYPE
    SYNTAX      Unsigned32 (0..4095)
    MAX-ACCESS  read-create
    STATUS      current
    DESCRIPTION
        "The value of pwTemplateVlanVcTag specifies the VLAN VC tag for the SDP
         Bind."
    DEFVAL      { '0fff'H }
    ::= { pwTemplateEntry 13 }

pwTemplateMacAddressLimit        OBJECT-TYPE
    SYNTAX      Unsigned32 (0..511999)
    MAX-ACCESS  read-create
    STATUS      current
    DESCRIPTION
        "The value of pwTemplateMacAddressLimit specifies the maximum number of
         learned and static entries allowed in the FDB for the SDP Bind. The
         value 0 specifies no limit for the SDP Bind. The command is valid only
         for spoke SDPs.

         The maximum value of this object depends on the platform/chassis mode."
    DEFVAL      { 0 }
    ::= { pwTemplateEntry 14 }

pwTemplateShgName                OBJECT-TYPE
    SYNTAX      TNamedItemOrEmpty
    MAX-ACCESS  read-create
    STATUS      current
    DESCRIPTION
        "The value of pwTemplateShgName specifies the name of the split-horizon
         group where the spoke SDP Bind belongs to. By default a spoke SDP Bind
         does not belong to any split-horizon group. The name specified must
         correspond to an existing split-horizon group in the TLS service where
         the spoke SDP Bind is defined."
    DEFVAL      { "" }
    ::= { pwTemplateEntry 15 }

pwTemplateShgDescription         OBJECT-TYPE
    SYNTAX      TItemDescription
    MAX-ACCESS  read-create
    STATUS      current
    DESCRIPTION
        "The value of pwTemplateShgDescription specifies a user-provided
         description for split-horizon group on the SDP Bind."
    DEFVAL      { "" }
    ::= { pwTemplateEntry 16 }

pwTemplateShgRestProtSrcMac      OBJECT-TYPE
    SYNTAX      TruthValue
    MAX-ACCESS  read-create
    STATUS      current
    DESCRIPTION
        "The value of pwTemplateShgRestProtSrcMac specifies how the agent will
         handle relearn requests for protected MAC addresses. When the value of
         this object is 'true' requests to relearn a protected MAC address will
         be ignored."
    DEFVAL      { false }
    ::= { pwTemplateEntry 17 }

pwTemplateShgRestUnprotDstMac    OBJECT-TYPE
    SYNTAX      TruthValue
    MAX-ACCESS  read-create
    STATUS      current
    DESCRIPTION
        "The value of pwTemplateShgRestUnprotDstMac specifies how the system
         will forward packets destined to an unprotected MAC address. When the
         value of this object is 'true' packets destined to an unprotected MAC
         address will be dropped."
    DEFVAL      { false }
    ::= { pwTemplateEntry 18 }

pwTemplateEgressMacFilterId      OBJECT-TYPE
    SYNTAX      TFilterID
    MAX-ACCESS  read-create
    STATUS      current
    DESCRIPTION
        "The value of pwTemplateEgressMacFilterId specifies the tMacFilterId
         which indexes an egress filter entry in
         TIMETRA-FILTER-MIB::tMacFilterTable, or zero if no filter is
         specified."
    DEFVAL      { 0 }
    ::= { pwTemplateEntry 19 }

pwTemplateEgressIpFilterId       OBJECT-TYPE
    SYNTAX      TFilterID
    MAX-ACCESS  read-create
    STATUS      current
    DESCRIPTION
        "The value of pwTemplateEgressIpFilterId specifies the tIPFilterId
         which indexes an egress filter entry in
         TIMETRA-FILTER-MIB::tIPFilterTable, or zero if no filter is specified."
    DEFVAL      { 0 }
    ::= { pwTemplateEntry 20 }

pwTemplateEgressIpv6FilterId     OBJECT-TYPE
    SYNTAX      TFilterID
    MAX-ACCESS  read-create
    STATUS      current
    DESCRIPTION
        "The value of pwTemplateEgressIpv6FilterId specifies the tIPv6FilterId
         which indexes an egress filter entry in
         TIMETRA-FILTER-MIB::tIPv6FilterTable, or zero if no filter is
         specified."
    DEFVAL      { 0 }
    ::= { pwTemplateEntry 21 }

pwTemplateIngressMacFilterId     OBJECT-TYPE
    SYNTAX      TFilterID
    MAX-ACCESS  read-create
    STATUS      current
    DESCRIPTION
        "The value of pwTemplateIngressMacFilterId specifies the tMacFilterId
         which indexes an ingress filter entry in
         TIMETRA-FILTER-MIB::tMacFilterTable, or zero if no filter is
         specified."
    DEFVAL      { 0 }
    ::= { pwTemplateEntry 22 }

pwTemplateIngressIpFilterId      OBJECT-TYPE
    SYNTAX      TFilterID
    MAX-ACCESS  read-create
    STATUS      current
    DESCRIPTION
        "The value of pwTemplateIngressIpFilterId specifies the tIPFilterId
         which indexes an ingress filter entry in
         TIMETRA-FILTER-MIB::tIPFilterTable, or zero if no filter is specified."
    DEFVAL      { 0 }
    ::= { pwTemplateEntry 23 }

pwTemplateIngressIpv6FilterId    OBJECT-TYPE
    SYNTAX      TFilterID
    MAX-ACCESS  read-create
    STATUS      current
    DESCRIPTION
        "The value of pwTemplateIngressIpv6FilterId specifies the tIPv6FilterId
         which indexes an ingress filter entry in
         TIMETRA-FILTER-MIB::tIPv6FilterTable, or zero if no filter is
         specified."
    DEFVAL      { 0 }
    ::= { pwTemplateEntry 24 }

pwTemplateIgmpFastLeave          OBJECT-TYPE
    SYNTAX      TmnxEnabledDisabled
    MAX-ACCESS  read-create
    STATUS      current
    DESCRIPTION
        "The value of pwTemplateIgmpFastLeave specifies whether or not
         fastleave is allowed on the SDP Bind.

         If set to 'enabled', the system prunes the port on which an IGMP
         'leave' message has been received without waiting for the Group
         Specific Query to timeout."
    DEFVAL      { disabled }
    ::= { pwTemplateEntry 25 }

pwTemplateIgmpImportPlcy         OBJECT-TYPE
    SYNTAX      TNamedItemOrEmpty
    MAX-ACCESS  read-create
    STATUS      current
    DESCRIPTION
        "The value of pwTemplateIgmpImportPlcy specifies a policy statement
         that must be applied to all incoming IGMP messages on the SDP Bind."
    DEFVAL      { "" }
    ::= { pwTemplateEntry 26 }

pwTemplateIgmpLastMembIntvl      OBJECT-TYPE
    SYNTAX      Unsigned32 (1..50)
    UNITS       "deciseconds"
    MAX-ACCESS  read-create
    STATUS      current
    DESCRIPTION
        "The value of pwTemplateIgmpLastMembIntvl specifies the Max Response
         Time (in deciseconds) used in Group-Specific and Group-Source-Specific
         Queries sent in response to 'leave' messages. This is also the amount
         of time between Group-Specific Query messages.

         This value may be tuned to modify the leave latency of the network. A
         reduced value results in reduced time to detect the loss of the last
         member of a group."
    DEFVAL      { 10 }
    ::= { pwTemplateEntry 27 }

pwTemplateIgmpMaxNbrGrps         OBJECT-TYPE
    SYNTAX      Unsigned32 (0..1000)
    MAX-ACCESS  read-create
    STATUS      current
    DESCRIPTION
        "The value of pwTemplateIgmpMaxNbrGrps specifies how many group
         addresses are allowed for the SDP Bind. The value 0 means that no
         limit is imposed."
    DEFVAL      { 0 }
    ::= { pwTemplateEntry 28 }

pwTemplateIgmpGenQueryIntvl      OBJECT-TYPE
    SYNTAX      Unsigned32 (2..1024)
    UNITS       "seconds"
    MAX-ACCESS  read-create
    STATUS      current
    DESCRIPTION
        "The value of pwTemplateIgmpGenQueryIntvl specifies the interval (in
         seconds) between two consecutive general queries sent by the system on
         the SDP.

         The value of this object is only meaningful when the value of
         pwTemplateIgmpSendQueries is 'enabled'."
    DEFVAL      { 125 }
    ::= { pwTemplateEntry 29 }

pwTemplateIgmpQueryRespIntvl     OBJECT-TYPE
    SYNTAX      Unsigned32 (1..1023)
    UNITS       "seconds"
    MAX-ACCESS  read-create
    STATUS      current
    DESCRIPTION
        "The value of pwTemplateIgmpQueryRespIntvl specifies the maximum
         response time (in seconds) advertised in IGMPv2/v3 queries.

         The value of this object is only meaningful when the value of
         pwTemplateIgmpSendQueries is 'enabled'."
    DEFVAL      { 10 }
    ::= { pwTemplateEntry 30 }

pwTemplateIgmpRobustCount        OBJECT-TYPE
    SYNTAX      Unsigned32 (2..7)
    MAX-ACCESS  read-create
    STATUS      current
    DESCRIPTION
        "The value of pwTemplateIgmpRobustCount specifies the value of the
         Robust count.

         This object allows tuning for the expected packet loss on the SDP. If
         an SDP is expected to be lossy, the Robustness Variable may be
         increased. IGMP snooping is robust to (Robustness Variable-1) packet
         losses.

         The value of this object is only meaningful when the value of
         pwTemplateIgmpSendQueries is 'enabled'."
    DEFVAL      { 2 }
    ::= { pwTemplateEntry 31 }

pwTemplateIgmpSendQueries        OBJECT-TYPE
    SYNTAX      TmnxEnabledDisabled
    MAX-ACCESS  read-create
    STATUS      current
    DESCRIPTION
        "The value of pwTemplateIgmpSendQueries specifies whether the system
         generates General Queries by itself on the SDP."
    DEFVAL      { disabled }
    ::= { pwTemplateEntry 32 }

pwTemplateIgmpMcacPolicyName     OBJECT-TYPE
    SYNTAX      TPolicyStatementNameOrEmpty
    MAX-ACCESS  read-create
    STATUS      obsolete
    DESCRIPTION
        "The value of pwTemplateIgmpMcacPolicyName indicates the name of the
         multicast CAC policy."
    DEFVAL      { "" }
    ::= { pwTemplateEntry 33 }

pwTemplateIgmpMcacUnconstBW      OBJECT-TYPE
    SYNTAX      Integer32 (-1 | 0..2147483647)
    UNITS       "kilobps"
    MAX-ACCESS  read-create
    STATUS      obsolete
    DESCRIPTION
        "The value of pwTemplateIgmpMcacUnconstBW specifies the bandwidth
         assigned for interface's multicast CAC policy traffic in kilobits per
         second(kbps).

         If the default value of '-1' is set, there is no constraint on
         bandwidth allocated at the interface.

         If the value of pwTemplateIgmpMcacUnconstBW is set to '0' and if a
         multicast CAC policy is assigned on the interface, then no group
         (channel) from that policy is allowed on that interface."
    DEFVAL      { -1 }
    ::= { pwTemplateEntry 34 }

pwTemplateIgmpMcacPrRsvMndBW     OBJECT-TYPE
    SYNTAX      Integer32 (-1..2147483647)
    UNITS       "kilobps"
    MAX-ACCESS  read-create
    STATUS      obsolete
    DESCRIPTION
        "The value of pwTemplateIgmpMcacPrRsvMndBW specifies the bandwidth
         pre-reserved for all the mandatory channels on a given interface in
         kilobits per second(kbps).

         If the value of pwTemplateIgmpMcacUnconstBW is '0', no mandatory
         channels are allowed. If the value of pwTemplateIgmpMcacUnconstBW is
         '-1', then all mandatory and optional channels are allowed.

         If the value of pwTemplateIgmpMcacPrRsvMndBW is equal to the value of
         pwTemplateIgmpMcacUnconstBW, then all the unconstrained bandwidth on a
         given interface is allocated to mandatory channels configured through
         multicast CAC policy on that interface and no optional groups
         (channels) are allowed.

         The value of pwTemplateIgmpMcacPrRsvMndBW should always be less than
         or equal to that of pwTemplateIgmpMcacUnconstBW. An attempt to set the
         value of pwTemplateIgmpMcacPrRsvMndBW greater than that of
         pwTemplateIgmpMcacUnconstBW will result in 'inconsistentValue' error."
    DEFVAL      { -1 }
    ::= { pwTemplateEntry 35 }

pwTemplateIgmpVersion            OBJECT-TYPE
    SYNTAX      TmnxIgmpVersion
    MAX-ACCESS  read-create
    STATUS      current
    DESCRIPTION
        "The value of pwTemplateIgmpVersion specifies the version of IGMP for
         the PW template."
    DEFVAL      { version3 }
    ::= { pwTemplateEntry 36 }

pwTemplateForceVlanVcForwarding  OBJECT-TYPE
    SYNTAX      TruthValue
    MAX-ACCESS  read-create
    STATUS      current
    DESCRIPTION
        "The value of pwTemplateForceVlanVcForwarding specifies whether
         or not vc-vlan-type forwarding is forced in the datapath when
         pwTemplateVcType is set to 'ether'.  When
         pwTemplateForceVlanVcForwarding is set to 'true', vc-vlan-type
         forwarding is forced.

         An 'inconsistentValue' error is returned when an attempt is made to
         set the value of pwTemplateForceVlanVcForwarding to 'true' and
         pwTemplateVcType is not set to 'ether'."
    DEFVAL      { false }
    ::= { pwTemplateEntry 37 }

pwTemplateHashLabel              OBJECT-TYPE
    SYNTAX      TruthValue
    MAX-ACCESS  read-create
    STATUS      current
    DESCRIPTION
        "The value of pwTemplateHashLabel specifies whether the use of hash
         label is enabled or not for the PW template."
    DEFVAL      { false }
    ::= { pwTemplateEntry 38 }

pwTemplateControlWord            OBJECT-TYPE
    SYNTAX      TruthValue
    MAX-ACCESS  read-create
    STATUS      current
    DESCRIPTION
        "The value of pwTemplateControlWord specifies whether the use of
         'ControlWord' is enabled on pseudowire packets or not.

         When the value of the object is set to 'true', all VPLS packets are
         encapsulated with the control word when sent over the pseudowire. When
         the value of the object is set to 'false', the use of 'ControlWord' is
         disabled."
    DEFVAL      { false }
    ::= { pwTemplateEntry 39 }

pwTemplateHashLabelSignalCap     OBJECT-TYPE
    SYNTAX      TruthValue
    MAX-ACCESS  read-create
    STATUS      current
    DESCRIPTION
        "The value of pwTemplateHashLabelSignalCap specifies whether to signal
         the hash label capability to the remote PE.

         The default value is 'false' and cannot be changed unless
         pwTemplateHashLabel is set to 'true'."
    DEFVAL      { false }
    ::= { pwTemplateEntry 40 }

pwTemplateRestProtSrcMac         OBJECT-TYPE
    SYNTAX      TruthValue
    MAX-ACCESS  read-create
    STATUS      current
    DESCRIPTION
        "The value of the object pwTemplateRestProtSrcMac specifies how the
         agent will handle relearn requests for protected MAC addresses. When
         the value of this object is 'true' requests to relearn a protected MAC
         address will be ignored.

         In addition, if the value of pwTemplateRestProtSrcMacAction is
         'disable', then the SAP or SDP-BIND where the protected source MAC was
         seen will be brought operationally down."
    DEFVAL      { false }
    ::= { pwTemplateEntry 52 }

pwTemplateRestProtSrcMacAction   OBJECT-TYPE
    SYNTAX      INTEGER {
        disable      (1),
        alarmOnly    (2),
        discardFrame (3)
    }
    MAX-ACCESS  read-create
    STATUS      current
    DESCRIPTION
        "The value of the object pwTemplateRestProtSrcMacAction indicates the
         action to take whenever a relearn request for a protected MAC is
         received on a restricted SAP.

         When the value of this object is 'disable' the SAP will be placed in
         the operational down state, with the operating flag 'recProtSrcMac'
         set.

         When the value of this object is 'alarmOnly', the SAP or SDP-BIND
         which sets the restricted MAC will be left up and only a notification,
         sapReceivedProtSrcMac or sdpBindReceivedProtSrcMac, will be generated.

         When the value of this object is 'discardFrame', the SAP or SDP-BIND
         which sees the restricted MAC will start discarding the frame in
         addition to generating sapReceivedProtSrcMac or
         sdpBindReceivedProtSrcMac notification."
    DEFVAL      { disable }
    ::= { pwTemplateEntry 53 }

pwTemplateAutoLearnMacProtect    OBJECT-TYPE
    SYNTAX      TruthValue
    MAX-ACCESS  read-create
    STATUS      current
    DESCRIPTION
        "The value of pwTemplateAutoLearnMacProtect specifies whether to enable
         automatic population of the MAC protect list with source MAC addresses
         learned on the SAP belonging to this template."
    DEFVAL      { false }
    ::= { pwTemplateEntry 54 }

pwTemplateShgRestProtSrcMacAct   OBJECT-TYPE
    SYNTAX      INTEGER {
        disable      (1),
        alarmOnly    (2),
        discardFrame (3)
    }
    MAX-ACCESS  read-create
    STATUS      current
    DESCRIPTION
        "The value of the object pwTemplateShgRestProtSrcMacAct indicates the
         action to take whenever a relearn request for a protected MAC is
         received on a restricted SAP or SDP-BIND belonging to
         pwTemplateShgName.

         When the value of this object is 'disable' the SAP or SDP-BIND
         belonging to pwTemplateShgName will be placed in the operational down
         state, with the operating flag 'recProtSrcMac' set.

         When the value of this object is 'alarmOnly', the SAP belonging to
         pwTemplateShgName will be left up and only a notification,
         sapReceivedProtSrcMac or sdpBindReceivedProtSrcMac,  will be generated.

         When the value of this object is 'discardFrame', the SAP or SDP-BIND
         belonging to pwTemplateShgName will start discarding the frame in
         addition to generating sapReceivedProtSrcMac or
         sdpBindReceivedProtSrcMac notification."
    DEFVAL      { disable }
    ::= { pwTemplateEntry 55 }

pwTemplateShgAutoLearnMacProtect OBJECT-TYPE
    SYNTAX      TruthValue
    MAX-ACCESS  read-create
    STATUS      current
    DESCRIPTION
        "The value of pwTemplateShgAutoLearnMacProtect specifies whether to
         enable automatic population of the MAC protect list with source MAC
         addresses learned on the SAP or SDP-BIND belonging to
         pwTemplateShgName."
    DEFVAL      { false }
    ::= { pwTemplateEntry 56 }

pwTemplateIngQoSNetworkPlcyId    OBJECT-TYPE
    SYNTAX      TSdpIngressPolicyID (0..65535)
    MAX-ACCESS  read-create
    STATUS      current
    DESCRIPTION
        "The value of the pwTemplateIngQoSNetworkPlcyId specifies the ingress
         QoS network policy applied to this PW template."
    DEFVAL      { 0 }
    ::= { pwTemplateEntry 57 }

pwTemplateEgrQoSNetworkPlcyId    OBJECT-TYPE
    SYNTAX      TSdpEgressPolicyID (0..65535)
    MAX-ACCESS  read-create
    STATUS      current
    DESCRIPTION
        "The value of the pwTemplateEgrQoSNetworkPlcyId specifies the egress
         QoS network policy applied to this PW template."
    DEFVAL      { 0 }
    ::= { pwTemplateEntry 58 }

pwTemplateIngQoSFpRedirectQGrp   OBJECT-TYPE
    SYNTAX      TNamedItemOrEmpty
    MAX-ACCESS  read-create
    STATUS      current
    DESCRIPTION
        "The value of pwTemplateIngQoSFpRedirectQGrp specifies the
         forwarding-plane queue group Policy for this PW template.

         This object must be set along with pwTemplateIngQoSNetworkPlcyId or
         pwTemplateIngQoSNetworkPlcyName object.

         An 'inconsistentValue' error is returned if
         pwTemplateIngQoSFpRedirectQGrp is set to a non-default value and an
         entry corresponding to tmnxFPNum to which this PW template belongs
         does not exist in tmnxFPAccIngQGrpTable."
    DEFVAL      { "" }
    ::= { pwTemplateEntry 59 }

pwTemplateEgrQoSPortRedirectQGrp OBJECT-TYPE
    SYNTAX      TNamedItemOrEmpty
    MAX-ACCESS  read-create
    STATUS      current
    DESCRIPTION
        "The value of pwTemplateEgrQoSPortRedirectQGrp specifies the
         forwarding-plane queue group Policy for this PW template.

         This object must be set along with pwTemplateEgrQoSNetworkPlcyId or
         pwTemplateEgrQoSNetworkPlcyName object.

         An 'inconsistentValue' error is returned if
         pwTemplateEgrQoSPortRedirectQGrp is set to a non-default value and an
         entry corresponding to tmnxFPNum to which this PW template belongs
         does not exist in tmnxFPAccIngQGrpTable."
    DEFVAL      { "" }
    ::= { pwTemplateEntry 60 }

pwTemplateIngQoSInstanceId       OBJECT-TYPE
    SYNTAX      TQosQGrpInstanceIDorZero
    MAX-ACCESS  read-create
    STATUS      current
    DESCRIPTION
        "The value of pwTemplateIngQoSInstanceId specifies the instance of the
         forwarding-plane ingress Queue Group for this PW template."
    DEFVAL      { 0 }
    ::= { pwTemplateEntry 61 }

pwTemplateEgrQoSInstanceId       OBJECT-TYPE
    SYNTAX      TQosQGrpInstanceIDorZero
    MAX-ACCESS  read-create
    STATUS      current
    DESCRIPTION
        "The value of pwTemplateEgrQoSInstanceId specifies the instance of the
         forwarding-plane egress Queue Group for this PW template."
    DEFVAL      { 0 }
    ::= { pwTemplateEntry 62 }

pwTemplateBlockOnPeerFault       OBJECT-TYPE
    SYNTAX      TruthValue
    MAX-ACCESS  read-create
    STATUS      current
    DESCRIPTION
        "The value of pwTemplateBlockOnPeerFault specifies whether to block
         user traffic being forwarded when peer pw status bits have faults for
         this PW template."
    DEFVAL      { false }
    ::= { pwTemplateEntry 63 }

pwTemplateForceQinqVcForwarding  OBJECT-TYPE
    SYNTAX      TruthValue
    MAX-ACCESS  read-create
    STATUS      obsolete
    DESCRIPTION
        "The value of pwTemplateForceQinqVcForwarding specifies whether or not
         the datapath should forcefully insert two VLAN tags when
         pwTemplateVcType is either set to 'ether' or 'vlan'.

         An 'inconsistentValue' error is returned when an attempt is made to
         set the value of pwTemplateForceQinqVcForwarding to 'true' and
         pwTemplateVcType is not set to either 'ether' or 'vlan'."
    DEFVAL      { false }
    ::= { pwTemplateEntry 64 }

pwTemplatePreferProvSdp          OBJECT-TYPE
    SYNTAX      TruthValue
    MAX-ACCESS  read-create
    STATUS      current
    DESCRIPTION
        "The value of pwTemplatePreferProvSdp specifies whether or not
          to use provisioned SDP when available.

          An 'inconsistentValue' error is returned if pwTemplatePreferProvSdp
          is set to true when pwTemplateUseProvisionedSdp is set to false.

          An 'inconsistentValue' error is returned if pwTemplatePreferProvSdp
          is modified after creation of the entry."
    DEFVAL      { false }
    ::= { pwTemplateEntry 65 }

pwTemplateEntropyLabel           OBJECT-TYPE
    SYNTAX      TruthValue
    MAX-ACCESS  read-create
    STATUS      current
    DESCRIPTION
        "The value of pwTemplateEntropyLabel specifies whether the use of
         entropy label is enabled or not for the PW template."
    DEFVAL      { false }
    ::= { pwTemplateEntry 66 }

pwTemplateName                   OBJECT-TYPE
    SYNTAX      TLNamedItemOrEmpty
    MAX-ACCESS  read-create
    STATUS      current
    DESCRIPTION
        "The value of pwTemplateName specifies the name to associate with this
         PW template."
    DEFVAL      { ''H }
    ::= { pwTemplateEntry 67 }

pwTemplateGreDelivery            OBJECT-TYPE
    SYNTAX      TruthValue
    MAX-ACCESS  read-create
    STATUS      current
    DESCRIPTION
        "The value of pwTemplateGreDelivery specifies whether or not to use a
         GRE tunnel should be used when creating an auto SDP. An
         'inconsistentValue' error is returned if pwTemplateGreDelivery is
         modified after creation of the entry."
    DEFVAL      { false }
    ::= { pwTemplateEntry 68 }

pwTemplateIngQoSNetworkPlcyName  OBJECT-TYPE
    SYNTAX      TLNamedItemOrEmpty
    MAX-ACCESS  read-create
    STATUS      current
    DESCRIPTION
        "The value of the pwTemplateIngQoSNetworkPlcyName specifies the ingress
         QoS network policy name applied to this PW template."
    DEFVAL      { "" }
    ::= { pwTemplateEntry 69 }

pwTemplateEgrQoSNetworkPlcyName  OBJECT-TYPE
    SYNTAX      TLNamedItemOrEmpty
    MAX-ACCESS  read-create
    STATUS      current
    DESCRIPTION
        "The value of the pwTemplateEgrQoSNetworkPlcyName specifies the egress
         QoS network policy name applied to this PW template."
    DEFVAL      { "" }
    ::= { pwTemplateEntry 70 }

pwTemplateIngressIpFilterName    OBJECT-TYPE
    SYNTAX      TLNamedItemOrEmpty
    MAX-ACCESS  read-create
    STATUS      current
    DESCRIPTION
        "The value of pwTemplateIngressIpFilterName specifies the ingress
         Filter name.

         When the value of this object is set to non-default, the value of
         object pwTemplateIngressIpFilterId is ignored."
    DEFVAL      { "" }
    ::= { pwTemplateEntry 71 }

pwTemplateIngressIpv6FilterName  OBJECT-TYPE
    SYNTAX      TLNamedItemOrEmpty
    MAX-ACCESS  read-create
    STATUS      current
    DESCRIPTION
        "The value of pwTemplateIngressIpv6FilterName specifies the ingress
         Filter name.

         When the value of this object is set to non-default, the value of
         object pwTemplateIngressIpv6FilterId is ignored."
    DEFVAL      { "" }
    ::= { pwTemplateEntry 72 }

pwTemplateIngressMacFilterName   OBJECT-TYPE
    SYNTAX      TLNamedItemOrEmpty
    MAX-ACCESS  read-create
    STATUS      current
    DESCRIPTION
        "The value of pwTemplateIngressMacFilterName specifies the ingress
         Filter name.

         When the value of this object is set to non-default, the value of
         object pwTemplateIngressMacFilterId is ignored."
    DEFVAL      { "" }
    ::= { pwTemplateEntry 73 }

pwTemplateEgressIpFilterName     OBJECT-TYPE
    SYNTAX      TLNamedItemOrEmpty
    MAX-ACCESS  read-create
    STATUS      current
    DESCRIPTION
        "The value of pwTemplateEgressIpFilterName specifies the ingress Filter
         name.

         When the value of this object is set to non-default, the value of
         object pwTemplateEgressIpFilterId is ignored."
    DEFVAL      { "" }
    ::= { pwTemplateEntry 74 }

pwTemplateEgressIpv6FilterName   OBJECT-TYPE
    SYNTAX      TLNamedItemOrEmpty
    MAX-ACCESS  read-create
    STATUS      current
    DESCRIPTION
        "The value of pwTemplateEgressIpv6FilterName specifies the ingress
         Filter name.

         When the value of this object is set to non-default, the value of
         object pwTemplateEgressIpv6FilterId is ignored."
    DEFVAL      { "" }
    ::= { pwTemplateEntry 75 }

pwTemplateEgressMacFilterName    OBJECT-TYPE
    SYNTAX      TLNamedItemOrEmpty
    MAX-ACCESS  read-create
    STATUS      current
    DESCRIPTION
        "The value of pwTemplateEgressMacFilterName specifies the ingress
         Filter name.

         When the value of this object is set to non-default, the value of
         object pwTemplateEgressMacFilterId is ignored."
    DEFVAL      { "" }
    ::= { pwTemplateEntry 76 }

pwTemplateForceQinqVcFwding      OBJECT-TYPE
    SYNTAX      INTEGER {
        none     (0),
        ctagctag (1),
        stagctag (2)
    }
    MAX-ACCESS  read-create
    STATUS      current
    DESCRIPTION
        "The value of pwTemplateForceQinqVcFwding specifies whether or not the
         datapath should forcefully insert two VLAN tags which are copied from
         the qinq service-delimiting vlan values.

         The pwTemplateVcType should be either set to 'ether' or 'vlan'."
    DEFVAL      { none }
    ::= { pwTemplateEntry 77 }

pwTemplateIgmpSnpgGrpSrcTblLC    OBJECT-TYPE
    SYNTAX      TimeStamp
    MAX-ACCESS  read-only
    STATUS      current
    DESCRIPTION
        "The value of pwTemplateIgmpSnpgGrpSrcTblLC indicates the sysUpTime at
         the time of the last modification of pwTemplateIgmpSnpgGrpSrcTable.

         If no changes were made to the entry since the last re-initialization
         of the local network management subsystem, then this object contains a
         zero value."
    ::= { tmnxSdpObjs 19 }

pwTemplateIgmpSnpgGrpSrcTable    OBJECT-TYPE
    SYNTAX      SEQUENCE OF PwTemplateIgmpSnpgGrpSrcEntry
    MAX-ACCESS  not-accessible
    STATUS      current
    DESCRIPTION
        "A table that contains entries for static IGMP Snooping groups."
    ::= { tmnxSdpObjs 20 }

pwTemplateIgmpSnpgGrpSrcEntry    OBJECT-TYPE
    SYNTAX      PwTemplateIgmpSnpgGrpSrcEntry
    MAX-ACCESS  not-accessible
    STATUS      current
    DESCRIPTION
        "Information about a specific static IGMP Snooping groups."
    INDEX       {
        pwTemplateId,
        pwTemplateIgmpSnpgGrpAddrType,
        pwTemplateIgmpSnpgGrpAddr,
        pwTemplateIgmpSnpgSrcAddrType,
        pwTemplateIgmpSnpgSrcAddr
    }
    ::= { pwTemplateIgmpSnpgGrpSrcTable 1 }

PwTemplateIgmpSnpgGrpSrcEntry    ::= SEQUENCE
{
    pwTemplateIgmpSnpgGrpAddrType    InetAddressType,
    pwTemplateIgmpSnpgGrpAddr        InetAddress,
    pwTemplateIgmpSnpgSrcAddrType    InetAddressType,
    pwTemplateIgmpSnpgSrcAddr        InetAddress,
    pwTemplateIgmpSnpgRowStatus      RowStatus,
    pwTemplateIgmpSnpgLastChngd      TimeStamp
}

pwTemplateIgmpSnpgGrpAddrType    OBJECT-TYPE
    SYNTAX      InetAddressType
    MAX-ACCESS  not-accessible
    STATUS      current
    DESCRIPTION
        "The IP multicast group address type for this entry."
    ::= { pwTemplateIgmpSnpgGrpSrcEntry 1 }

pwTemplateIgmpSnpgGrpAddr        OBJECT-TYPE
    SYNTAX      InetAddress (SIZE (0|4))
    MAX-ACCESS  not-accessible
    STATUS      current
    DESCRIPTION
        "The IP multicast group address for this entry."
    ::= { pwTemplateIgmpSnpgGrpSrcEntry 2 }

pwTemplateIgmpSnpgSrcAddrType    OBJECT-TYPE
    SYNTAX      InetAddressType
    MAX-ACCESS  not-accessible
    STATUS      current
    DESCRIPTION
        "The source address type for this entry."
    ::= { pwTemplateIgmpSnpgGrpSrcEntry 3 }

pwTemplateIgmpSnpgSrcAddr        OBJECT-TYPE
    SYNTAX      InetAddress (SIZE (0|4))
    MAX-ACCESS  not-accessible
    STATUS      current
    DESCRIPTION
        "The source address for this entry."
    ::= { pwTemplateIgmpSnpgGrpSrcEntry 4 }

pwTemplateIgmpSnpgRowStatus      OBJECT-TYPE
    SYNTAX      RowStatus
    MAX-ACCESS  read-create
    STATUS      current
    DESCRIPTION
        "The value of pwTemplateIgmpSnpgRowStatus is used for the creation and
         deletion of static IGMP snooping entries."
    ::= { pwTemplateIgmpSnpgGrpSrcEntry 5 }

pwTemplateIgmpSnpgLastChngd      OBJECT-TYPE
    SYNTAX      TimeStamp
    MAX-ACCESS  read-only
    STATUS      current
    DESCRIPTION
        "The value of pwTemplateIgmpSnpgLastChngd indicates the sysUpTime at
         the time of the last modification of this entry.

         If no changes were made to the entry since the last re-initialization
         of the local network management subsystem, then this object contains a
         zero value."
    ::= { pwTemplateIgmpSnpgGrpSrcEntry 6 }

pwTemplateMfibAllowedMdaTblLC    OBJECT-TYPE
    SYNTAX      TimeStamp
    MAX-ACCESS  read-only
    STATUS      current
    DESCRIPTION
        "The value of pwTemplateMfibAllowedMdaTblLC indicates the sysUpTime at
         the time of the last modification of pwTemplateMfibAllowedMdaTable.

         If no changes were made to the entry since the last re-initialization
         of the local network management subsystem, then this object contains a
         zero value."
    ::= { tmnxSdpObjs 21 }

pwTemplateMfibAllowedMdaTable    OBJECT-TYPE
    SYNTAX      SEQUENCE OF PwTemplateMfibAllowedMdaEntry
    MAX-ACCESS  not-accessible
    STATUS      current
    DESCRIPTION
        "The pwTemplateMfibAllowedMdaTable has an entry for each MFIB allowed
         MDA destination for an PW template."
    ::= { tmnxSdpObjs 22 }

pwTemplateMfibAllowedMdaEntry    OBJECT-TYPE
    SYNTAX      PwTemplateMfibAllowedMdaEntry
    MAX-ACCESS  not-accessible
    STATUS      current
    DESCRIPTION
        "Each row entry represents an MFIB allowed MDA destination for an PW
         template configured in the system. Entries can be created and deleted
         via SNMP SET operations on the object pwTemplateMfibMdaRowStatus."
    INDEX       {
        pwTemplateId,
        tmnxChassisIndex,
        tmnxCardSlotNum,
        tmnxMDASlotNum
    }
    ::= { pwTemplateMfibAllowedMdaTable 1 }

PwTemplateMfibAllowedMdaEntry    ::= SEQUENCE
{ pwTemplateMfibMdaRowStatus       RowStatus }

pwTemplateMfibMdaRowStatus       OBJECT-TYPE
    SYNTAX      RowStatus
    MAX-ACCESS  read-create
    STATUS      current
    DESCRIPTION
        "The value of pwTemplateMfibMdaRowStatus controls the creation and
         deletion of rows in this table."
    ::= { pwTemplateMfibAllowedMdaEntry 1 }

sdpBindTlsMrpTableLastChanged    OBJECT-TYPE
    SYNTAX      TimeStamp
    MAX-ACCESS  read-only
    STATUS      current
    DESCRIPTION
        "The value of sdpBindTlsMrpTableLastChanged indicates the sysUpTime at
         the time of the last modification of sdpBindTlsMrpTable.

         If no changes were made to the entry since the last re-initialization
         of the local network management subsystem, then this object contains a
         zero value."
    ::= { tmnxSdpObjs 23 }

sdpBindTlsMrpTable               OBJECT-TYPE
    SYNTAX      SEQUENCE OF SdpBindTlsMrpEntry
    MAX-ACCESS  not-accessible
    STATUS      current
    DESCRIPTION
        "The sdpBindTlsMrpTable allows the operator to modify attributes of the
         Multiple Registration Protocol (MRP) feature for the TLS SDP Bind.

         This table contains an entry for each TLS SDP Bind created by the user
         using either sdpBindTlsTable or sdpBindMeshTlsTable.

         Rows in this table are created and deleted automatically by the
         system."
    ::= { tmnxSdpObjs 24 }

sdpBindTlsMrpEntry               OBJECT-TYPE
    SYNTAX      SdpBindTlsMrpEntry
    MAX-ACCESS  not-accessible
    STATUS      current
    DESCRIPTION
        "Each row entry contains objects that allows the modification of the
         Multiple Registration Protocol feature for a specific SDP-Binding in a
         TLS service."
    INDEX       {
        svcId,
        sdpBindId
    }
    ::= { sdpBindTlsMrpTable 1 }

SdpBindTlsMrpEntry               ::= SEQUENCE
{
    sdpBindTlsMrpLastChngd           TimeStamp,
    sdpBindTlsMrpJoinTime            Unsigned32,
    sdpBindTlsMrpLeaveTime           Unsigned32,
    sdpBindTlsMrpLeaveAllTime        Unsigned32,
    sdpBindTlsMrpPeriodicTime        Unsigned32,
    sdpBindTlsMrpPeriodicEnabled     TruthValue,
    sdpBindTlsMrpRxPdus              Counter32,
    sdpBindTlsMrpDroppedPdus         Counter32,
    sdpBindTlsMrpTxPdus              Counter32,
    sdpBindTlsMrpRxNewEvent          Counter32,
    sdpBindTlsMrpRxJoinInEvent       Counter32,
    sdpBindTlsMrpRxInEvent           Counter32,
    sdpBindTlsMrpRxJoinEmptyEvent    Counter32,
    sdpBindTlsMrpRxEmptyEvent        Counter32,
    sdpBindTlsMrpRxLeaveEvent        Counter32,
    sdpBindTlsMrpTxNewEvent          Counter32,
    sdpBindTlsMrpTxJoinInEvent       Counter32,
    sdpBindTlsMrpTxInEvent           Counter32,
    sdpBindTlsMrpTxJoinEmptyEvent    Counter32,
    sdpBindTlsMrpTxEmptyEvent        Counter32,
    sdpBindTlsMrpTxLeaveEvent        Counter32,
    sdpBindTlsMrpPolicy              TNamedItemOrEmpty
}

sdpBindTlsMrpLastChngd           OBJECT-TYPE
    SYNTAX      TimeStamp
    MAX-ACCESS  read-only
    STATUS      current
    DESCRIPTION
        "The value of sdpBindTlsMrpLastChngd indicates the sysUpTime at the
         time of the last modification of this entry.

         If no changes were made to the entry since the last re-initialization
         of the local network management subsystem, then this object contains a
         zero value."
    ::= { sdpBindTlsMrpEntry 1 }

sdpBindTlsMrpJoinTime            OBJECT-TYPE
    SYNTAX      Unsigned32 (1..10)
    UNITS       "deciseconds"
    MAX-ACCESS  read-write
    STATUS      current
    DESCRIPTION
        "The value of sdpBindTlsMrpJoinTime specifies a timer value in 10ths of
         seconds which determines the maximum rate at which attribute join
         messages can be sent on the SDP."
    DEFVAL      { 2 }
    ::= { sdpBindTlsMrpEntry 2 }

sdpBindTlsMrpLeaveTime           OBJECT-TYPE
    SYNTAX      Unsigned32 (30..60)
    UNITS       "deciseconds"
    MAX-ACCESS  read-write
    STATUS      current
    DESCRIPTION
        "The value of sdpBindTlsMrpLeaveTime specifies a timer value in 10ths
         of seconds which determines the amount of time a registered attribute
         is held in leave state before the registration is removed."
    DEFVAL      { 30 }
    ::= { sdpBindTlsMrpEntry 3 }

sdpBindTlsMrpLeaveAllTime        OBJECT-TYPE
    SYNTAX      Unsigned32 (60..300)
    UNITS       "deciseconds"
    MAX-ACCESS  read-write
    STATUS      current
    DESCRIPTION
        "The value of sdpBindTlsMrpLeaveAllTime specifies a timer value in
         10ths of seconds which determines the frequency where all attribute
         declarations on the SDP are all refreshed."
    DEFVAL      { 100 }
    ::= { sdpBindTlsMrpEntry 4 }

sdpBindTlsMrpPeriodicTime        OBJECT-TYPE
    SYNTAX      Unsigned32 (10..100)
    UNITS       "deciseconds"
    MAX-ACCESS  read-write
    STATUS      current
    DESCRIPTION
        "The value of sdpBindTlsMrpPeriodicTime specifies a timer value in
         10ths of seconds which determines the frequency of retransmission of
         attribute declarations."
    DEFVAL      { 10 }
    ::= { sdpBindTlsMrpEntry 5 }

sdpBindTlsMrpPeriodicEnabled     OBJECT-TYPE
    SYNTAX      TruthValue
    MAX-ACCESS  read-write
    STATUS      current
    DESCRIPTION
        "The value of sdpBindTlsMrpPeriodicEnabled specifies whether
         retransmission of attribute declarations is enabled."
    DEFVAL      { false }
    ::= { sdpBindTlsMrpEntry 6 }

sdpBindTlsMrpRxPdus              OBJECT-TYPE
    SYNTAX      Counter32
    MAX-ACCESS  read-only
    STATUS      current
    DESCRIPTION
        "The value of sdpBindTlsMrpRxPdus indicates the number of MRP packets
         received on this SDP Bind."
    ::= { sdpBindTlsMrpEntry 7 }

sdpBindTlsMrpDroppedPdus         OBJECT-TYPE
    SYNTAX      Counter32
    MAX-ACCESS  read-only
    STATUS      current
    DESCRIPTION
        "The value of sdpBindTlsMrpDroppedPdus indicates the number of dropped
         MRP packets on this SDP Bind."
    ::= { sdpBindTlsMrpEntry 8 }

sdpBindTlsMrpTxPdus              OBJECT-TYPE
    SYNTAX      Counter32
    MAX-ACCESS  read-only
    STATUS      current
    DESCRIPTION
        "The value of sdpBindTlsMrpTxPdus indicates the number of MRP packets
         transmitted on this SDP Bind."
    ::= { sdpBindTlsMrpEntry 9 }

sdpBindTlsMrpRxNewEvent          OBJECT-TYPE
    SYNTAX      Counter32
    MAX-ACCESS  read-only
    STATUS      current
    DESCRIPTION
        "The value of sdpBindTlsMrpRxNewEvent indicates the number of 'New' MRP
         events received on this SDP Bind."
    ::= { sdpBindTlsMrpEntry 10 }

sdpBindTlsMrpRxJoinInEvent       OBJECT-TYPE
    SYNTAX      Counter32
    MAX-ACCESS  read-only
    STATUS      current
    DESCRIPTION
        "The value of sdpBindTlsMrpRxJoinInEvent indicates the number of
         'Join-In' MRP events received on this SDP Bind."
    ::= { sdpBindTlsMrpEntry 11 }

sdpBindTlsMrpRxInEvent           OBJECT-TYPE
    SYNTAX      Counter32
    MAX-ACCESS  read-only
    STATUS      current
    DESCRIPTION
        "The value of sdpBindTlsMrpRxInEvent indicates the number of 'In' MRP
         events received on this SDP Bind."
    ::= { sdpBindTlsMrpEntry 12 }

sdpBindTlsMrpRxJoinEmptyEvent    OBJECT-TYPE
    SYNTAX      Counter32
    MAX-ACCESS  read-only
    STATUS      current
    DESCRIPTION
        "The value of sdpBindTlsMrpRxJoinEmptyEvent indicates the number of
         'Join Empty' MRP events received on this SDP Bind."
    ::= { sdpBindTlsMrpEntry 13 }

sdpBindTlsMrpRxEmptyEvent        OBJECT-TYPE
    SYNTAX      Counter32
    MAX-ACCESS  read-only
    STATUS      current
    DESCRIPTION
        "The value of sdpBindTlsMrpRxEmptyEvent indicates the number of 'Empty'
         MRP events received on this SDP Bind."
    ::= { sdpBindTlsMrpEntry 14 }

sdpBindTlsMrpRxLeaveEvent        OBJECT-TYPE
    SYNTAX      Counter32
    MAX-ACCESS  read-only
    STATUS      current
    DESCRIPTION
        "The value of sdpBindTlsMrpRxLeaveEvent indicates the number of 'Leave'
         MRP events received on this SDP Bind."
    ::= { sdpBindTlsMrpEntry 15 }

sdpBindTlsMrpTxNewEvent          OBJECT-TYPE
    SYNTAX      Counter32
    MAX-ACCESS  read-only
    STATUS      current
    DESCRIPTION
        "The value of sdpBindTlsMrpTxNewEvent indicates the number of 'New' MRP
         events transmitted on this SDP Bind."
    ::= { sdpBindTlsMrpEntry 16 }

sdpBindTlsMrpTxJoinInEvent       OBJECT-TYPE
    SYNTAX      Counter32
    MAX-ACCESS  read-only
    STATUS      current
    DESCRIPTION
        "The value of sdpBindTlsMrpTxJoinInEvent indicates the number of
         'Join-In' MRP events transmitted on this SDP Bind."
    ::= { sdpBindTlsMrpEntry 17 }

sdpBindTlsMrpTxInEvent           OBJECT-TYPE
    SYNTAX      Counter32
    MAX-ACCESS  read-only
    STATUS      current
    DESCRIPTION
        "The value of sdpBindTlsMrpTxInEvent indicates the number of 'In' MRP
         events transmitted on this SDP Bind."
    ::= { sdpBindTlsMrpEntry 18 }

sdpBindTlsMrpTxJoinEmptyEvent    OBJECT-TYPE
    SYNTAX      Counter32
    MAX-ACCESS  read-only
    STATUS      current
    DESCRIPTION
        "The value of sdpBindTlsMrpTxJoinEmptyEvent indicates the number of
         'Join Empty' MRP events transmitted on this SDP Bind."
    ::= { sdpBindTlsMrpEntry 19 }

sdpBindTlsMrpTxEmptyEvent        OBJECT-TYPE
    SYNTAX      Counter32
    MAX-ACCESS  read-only
    STATUS      current
    DESCRIPTION
        "The value of sdpBindTlsMrpTxEmptyEvent indicates the number of 'Empty'
         MRP events transmitted on this SDP Bind."
    ::= { sdpBindTlsMrpEntry 20 }

sdpBindTlsMrpTxLeaveEvent        OBJECT-TYPE
    SYNTAX      Counter32
    MAX-ACCESS  read-only
    STATUS      current
    DESCRIPTION
        "The value of sdpBindTlsMrpTxLeaveEvent indicates the number of 'Leave'
         MRP events transmitted on this SDP Bind."
    ::= { sdpBindTlsMrpEntry 21 }

sdpBindTlsMrpPolicy              OBJECT-TYPE
    SYNTAX      TNamedItemOrEmpty
    MAX-ACCESS  read-write
    STATUS      current
    DESCRIPTION
        "The value of sdpBindTlsMrpPolicy specifies the mrp policy to control
         which Group BMAC attributes will advertise on the egress SDP Bind."
    DEFVAL      { "" }
    ::= { sdpBindTlsMrpEntry 22 }

sdpBindTlsMmrpTable              OBJECT-TYPE
    SYNTAX      SEQUENCE OF SdpBindTlsMmrpEntry
    MAX-ACCESS  not-accessible
    STATUS      current
    DESCRIPTION
        "This table contains an entry for each MAC address managed
         by Multiple MAC Registration Protocol (MMRP) on the SDP
         Bind for the TLS.  Entries are dynamically created and
         destroyed by the system as the MAC Addresses are registered
         or declared in MMRP."
    ::= { tmnxSdpObjs 25 }

sdpBindTlsMmrpEntry              OBJECT-TYPE
    SYNTAX      SdpBindTlsMmrpEntry
    MAX-ACCESS  not-accessible
    STATUS      current
    DESCRIPTION
        "MMRP specific information about a MAC address managed by MMRP on a SDP
         Bind in a TLS."
    INDEX       {
        svcId,
        sdpBindId,
        sdpBindTlsMmrpMacAddr
    }
    ::= { sdpBindTlsMmrpTable 1 }

SdpBindTlsMmrpEntry              ::= SEQUENCE
{
    sdpBindTlsMmrpMacAddr            MacAddress,
    sdpBindTlsMmrpDeclared           TruthValue,
    sdpBindTlsMmrpRegistered         TruthValue,
    sdpBindTlsMmrpEndStation         TruthValue
}

sdpBindTlsMmrpMacAddr            OBJECT-TYPE
    SYNTAX      MacAddress
    MAX-ACCESS  not-accessible
    STATUS      current
    DESCRIPTION
        "The value of sdpBindTlsMmrpMacAddr indicates an ethernet MAC address
         which is being managed by MMRP on this SAP."
    ::= { sdpBindTlsMmrpEntry 1 }

sdpBindTlsMmrpDeclared           OBJECT-TYPE
    SYNTAX      TruthValue
    MAX-ACCESS  read-only
    STATUS      current
    DESCRIPTION
        "The value of sdpBindTlsMmrpDeclared indicates whether the MRP
         applicant on this SAP is declaring this MAC address on behalf of MMRP."
    ::= { sdpBindTlsMmrpEntry 2 }

sdpBindTlsMmrpRegistered         OBJECT-TYPE
    SYNTAX      TruthValue
    MAX-ACCESS  read-only
    STATUS      current
    DESCRIPTION
        "The value of sdpBindTlsMmrpRegistered indicates whether the MRP
         registrant on this SAP has notified MMRP of a registration of this MAC
         address."
    ::= { sdpBindTlsMmrpEntry 3 }

sdpBindTlsMmrpEndStation         OBJECT-TYPE
    SYNTAX      TruthValue
    MAX-ACCESS  read-only
    STATUS      current
    DESCRIPTION
        "The value of sdpBindTlsMmrpEndStation indicates whether the MRP
         registrant on this SAP originated per end-station."
    ::= { sdpBindTlsMmrpEntry 4 }

sdpAutoBindBgpInfoTableLC        OBJECT-TYPE
    SYNTAX      TimeStamp
    MAX-ACCESS  read-only
    STATUS      current
    DESCRIPTION
        "The value of sdpAutoBindBgpInfoTableLC indicates the sysUpTime at the
         time of the last modification of sdpAutoBindBgpInfoTable.

         If no changes were made to the entry since the last re-initialization
         of the local network management subsystem, then this object contains a
         zero value."
    ::= { tmnxSdpObjs 26 }

sdpAutoBindBgpInfoTable          OBJECT-TYPE
    SYNTAX      SEQUENCE OF SdpAutoBindBgpInfoEntry
    MAX-ACCESS  not-accessible
    STATUS      current
    DESCRIPTION
        "The sdpAutoBindBgpInfoTable has an entry for each SDP Bind entry from
         sdpBindTable which was created as a result of BGP Auto-discovery."
    ::= { tmnxSdpObjs 27 }

sdpAutoBindBgpInfoEntry          OBJECT-TYPE
    SYNTAX      SdpAutoBindBgpInfoEntry
    MAX-ACCESS  not-accessible
    STATUS      current
    DESCRIPTION
        "Each row entry contains BGP-related information for an SDP Bind entry
         created as a result of BGP Auto-discovery."
    INDEX       {
        svcId,
        sdpBindId
    }
    ::= { sdpAutoBindBgpInfoTable 1 }

SdpAutoBindBgpInfoEntry          ::= SEQUENCE
{
    sdpAutoBindBgpInfoTemplateId     PWTemplateId,
    sdpAutoBindBgpInfoAGI            TmnxVPNRouteDistinguisher,
    sdpAutoBindBgpInfoSAII           Unsigned32,
    sdpAutoBindBgpInfoTAII           Unsigned32
}

sdpAutoBindBgpInfoTemplateId     OBJECT-TYPE
    SYNTAX      PWTemplateId
    MAX-ACCESS  read-only
    STATUS      current
    DESCRIPTION
        "The value of sdpAutoBindBgpInfoTemplateId indicates the the value of
         the pwTemplateId object for the PW template entry used to create this
         SDP Bind."
    ::= { sdpAutoBindBgpInfoEntry 1 }

sdpAutoBindBgpInfoAGI            OBJECT-TYPE
    SYNTAX      TmnxVPNRouteDistinguisher
    MAX-ACCESS  read-only
    STATUS      current
    DESCRIPTION
        "The value of sdpAutoBindBgpInfoAGI indicates the Attachment Group
         Identifier (AGI) portion of the Generalized Id FEC element from the
         pseudowire setup for this SDP Bind."
    ::= { sdpAutoBindBgpInfoEntry 2 }

sdpAutoBindBgpInfoSAII           OBJECT-TYPE
    SYNTAX      Unsigned32
    MAX-ACCESS  read-only
    STATUS      current
    DESCRIPTION
        "The value of sdpAutoBindBgpInfoSAII indicates the Source Attachment
         Individual Identifier (SAII) portion of the Generalized Id FEC element
         from the pseudowire setup for this SDP Bind."
    ::= { sdpAutoBindBgpInfoEntry 3 }

sdpAutoBindBgpInfoTAII           OBJECT-TYPE
    SYNTAX      Unsigned32
    MAX-ACCESS  read-only
    STATUS      current
    DESCRIPTION
        "The value of sdpAutoBindBgpInfoTAII indicates the Target Attachment
         Individual Identifier (TAII) portion of the Generalized Id FEC element
         from the pseudowire setup for this SDP Bind."
    ::= { sdpAutoBindBgpInfoEntry 4 }

svcApplyEvalPwTemplate           OBJECT IDENTIFIER ::= { tmnxSdpObjs 28 }

svcApplyEvalPwTemplateSvcId      OBJECT-TYPE
    SYNTAX      TmnxServId
    MAX-ACCESS  read-write
    STATUS      current
    DESCRIPTION
        "The value of the object svcApplyEvalPwTemplateSvcId specifies the
         service identifier to which this action applies."
    DEFVAL      { 0 }
    ::= { svcApplyEvalPwTemplate 1 }

svcApplyEvalPwTemplateId         OBJECT-TYPE
    SYNTAX      PWTemplateId
    MAX-ACCESS  read-write
    STATUS      current
    DESCRIPTION
        "The value of the object svcApplyEvalPwTemplateId specifies the
         pwTemplateId to apply on the service 'svcApplyEvalPwTemplateSvcId'."
    DEFVAL      { 0 }
    ::= { svcApplyEvalPwTemplate 2 }

svcApplyEvalPwTemplateAction     OBJECT-TYPE
    SYNTAX      TmnxActionType
    MAX-ACCESS  read-write
    STATUS      current
    DESCRIPTION
        "The value of svcApplyEvalPwTemplateAction when set to 'doAction'
            triggers the action to re-evaluate pseudo-wire template policy
         'svcApplyEvalPwTemplateId' on the 'svcApplyEvalPwTemplateSvcId'
         service.

         Reading this object returns the value 'notApplicable'."
    DEFVAL      { notApplicable }
    ::= { svcApplyEvalPwTemplate 3 }

svcApplyEvalPwTemplateSuccess    OBJECT-TYPE
    SYNTAX      TruthValue
    MAX-ACCESS  read-only
    STATUS      current
    DESCRIPTION
        "The value of the object svcApplyEvalPwTemplateSuccess indicates
         whether the action was successful.

         If the value of the object equals 'false', then the value of
         svcApplyEvalPwTemplateErrorMsg indicates the reason of the failure."
    DEFVAL      { false }
    ::= { svcApplyEvalPwTemplate 4 }

svcApplyEvalPwTemplateErrorMsg   OBJECT-TYPE
    SYNTAX      DisplayString (SIZE (0..255))
    MAX-ACCESS  read-only
    STATUS      current
    DESCRIPTION
        "The value of the object svcApplyEvalPwTemplateErrorMsg indicates the
         reason of failure, in case the value of the object
         svcApplyEvalPwTemplateSuccess is equal to 'false'.

         If the value of the object svcApplyEvalPwTemplateSuccess is equal to
         'true', this object contains an empty string."
    ::= { svcApplyEvalPwTemplate 5 }

svcApplyEvalPwTemplateTime       OBJECT-TYPE
    SYNTAX      TimeStamp
    MAX-ACCESS  read-only
    STATUS      current
    DESCRIPTION
        "The value of the object svcApplyEvalPwTemplateTime indicates the value
         of sysUpTime at the last time that the object
         svcApplyEvalPwTemplateSuccess was written by the system."
    ::= { svcApplyEvalPwTemplate 6 }

sdpBindPbbTable                  OBJECT-TYPE
    SYNTAX      SEQUENCE OF SdpBindPbbEntry
    MAX-ACCESS  not-accessible
    STATUS      current
    DESCRIPTION
        "A table that contains Provider Backbone Bridging (PBB/IEEE 802.1ah)
         spoke SDP Bind information."
    ::= { tmnxSdpObjs 29 }

sdpBindPbbEntry                  OBJECT-TYPE
    SYNTAX      SdpBindPbbEntry
    MAX-ACCESS  not-accessible
    STATUS      current
    DESCRIPTION
        "PBB I-Component instance-specific information about an SDP Bind in the
         B-Component instance.

         Entries in this table can be created or deleted via SNMP operations."
    INDEX       {
        sdpBindPbbSvcIdIVpls,
        sdpBindPbbSvcIdBVpls,
        sdpBindPbbId
    }
    ::= { sdpBindPbbTable 1 }

SdpBindPbbEntry                  ::= SEQUENCE
{
    sdpBindPbbSvcIdIVpls             TmnxServId,
    sdpBindPbbSvcIdBVpls             TmnxServId,
    sdpBindPbbId                     SdpBindId,
    sdpBindPbbRowStatus              RowStatus,
    sdpBindPbbLastMgmtChange         TimeStamp,
    sdpBindPbbIgmpSnpgMRouter        TruthValue,
    sdpBindPbbMldSnpgMRouter         TruthValue
}

sdpBindPbbSvcIdIVpls             OBJECT-TYPE
    SYNTAX      TmnxServId
    MAX-ACCESS  not-accessible
    STATUS      current
    DESCRIPTION
        "The value of the object sdpBindPbbSvcIdIVpls specifies the Service
         identifier of the I-Component instance."
    ::= { sdpBindPbbEntry 1 }

sdpBindPbbSvcIdBVpls             OBJECT-TYPE
    SYNTAX      TmnxServId
    MAX-ACCESS  not-accessible
    STATUS      current
    DESCRIPTION
        "The value of the object sdpBindPbbSvcIdBVpls specifies the Service
         identifier of the B-Component instance."
    ::= { sdpBindPbbEntry 2 }

sdpBindPbbId                     OBJECT-TYPE
    SYNTAX      SdpBindId
    MAX-ACCESS  not-accessible
    STATUS      current
    DESCRIPTION
        "The value of the object sdpBindPbbId specifies the identifier of the
         SDP Binding in the B-Component instance."
    ::= { sdpBindPbbEntry 3 }

sdpBindPbbRowStatus              OBJECT-TYPE
    SYNTAX      RowStatus
    MAX-ACCESS  read-create
    STATUS      current
    DESCRIPTION
        "The value of sdpBindPbbRowStatus specifies the row status of this row.

         The only values supported during a set operation are 'createAndGo' and
         'destroy'."
    ::= { sdpBindPbbEntry 4 }

sdpBindPbbLastMgmtChange         OBJECT-TYPE
    SYNTAX      TimeStamp
    MAX-ACCESS  read-only
    STATUS      current
    DESCRIPTION
        "The value of sdpBindPbbLastMgmtChange indicates the sysUpTime at the
         time of the most recent management-initiated change to this table row."
    ::= { sdpBindPbbEntry 5 }

sdpBindPbbIgmpSnpgMRouter        OBJECT-TYPE
    SYNTAX      TruthValue
    MAX-ACCESS  read-create
    STATUS      current
    DESCRIPTION
        "The value of the object sdpBindPbbIgmpSnpgMRouter specifies if a
         multicast router is attached behind this SDP Bind."
    DEFVAL      { false }
    ::= { sdpBindPbbEntry 6 }

sdpBindPbbMldSnpgMRouter         OBJECT-TYPE
    SYNTAX      TruthValue
    MAX-ACCESS  read-create
    STATUS      current
    DESCRIPTION
        "The value of the object sdpBindPbbMldSnpgMRouter specifies if a
         multicast router is attached behind this SDP Bind."
    DEFVAL      { false }
    ::= { sdpBindPbbEntry 7 }

sdpBindFPropBMacAddrTblLastChgd  OBJECT-TYPE
    SYNTAX      TimeStamp
    MAX-ACCESS  read-only
    STATUS      current
    DESCRIPTION
        "The value of sdpBindFPropBMacAddrTblLastChgd indicates the sysUpTime
         at the last modification of sdpBindFPropBMacAddrTable.

         If no changes were made to the table since the last re-initialization
         of the local network management subsystem, this object contains a zero
         value."
    ::= { tmnxSdpObjs 30 }

sdpBindFPropBMacAddrTable        OBJECT-TYPE
    SYNTAX      SEQUENCE OF SdpBindFPropBMacAddrEntry
    MAX-ACCESS  not-accessible
    STATUS      current
    DESCRIPTION
        "sdpBindFPropBMacAddrTable contains the optional configured backbone MAC
         (BMac) addresses (or MAC names) for each SDP binding.  This table
         extends the information in sdpBindTable."
    ::= { tmnxSdpObjs 31 }

sdpBindFPropBMacAddrEntry        OBJECT-TYPE
    SYNTAX      SdpBindFPropBMacAddrEntry
    MAX-ACCESS  not-accessible
    STATUS      current
    DESCRIPTION
        "sdpBindFPropBMacAddrEntry defines a row in the
         sdpBindFPropBMacAddrTable.  Rows are created and destroyed using
         sdpBindFPropBMacAddrRowStatus.  A prerequisite for row creation:  a
         row with the same svcId and sdpBindId must be present in the
         sdpBindTable."
    INDEX       {
        svcId,
        sdpBindId,
        sdpBindFPropBMacAddrOrMacNameTag,
        sdpBindFPropBMacAddrOrMacName
    }
    ::= { sdpBindFPropBMacAddrTable 1 }

SdpBindFPropBMacAddrEntry        ::= SEQUENCE
{
    sdpBindFPropBMacAddrOrMacNameTag INTEGER,
    sdpBindFPropBMacAddrOrMacName    TNamedItem,
    sdpBindFPropBMacAddrRowStatus    RowStatus
}

sdpBindFPropBMacAddrOrMacNameTag OBJECT-TYPE
    SYNTAX      INTEGER {
        macName (1),
        macAddr (2)
    }
    MAX-ACCESS  not-accessible
    STATUS      current
    DESCRIPTION
        "The value of sdpBindFPropBMacAddrOrMacNameTag specifies whether
         sdpBindFPropBMacAddrOrMacName contains a MAC name, or a MAC address."
    ::= { sdpBindFPropBMacAddrEntry 1 }

sdpBindFPropBMacAddrOrMacName    OBJECT-TYPE
    SYNTAX      TNamedItem
    MAX-ACCESS  not-accessible
    STATUS      current
    DESCRIPTION
        "The value of sdpBindFPropBMacAddrOrMacName specifies a MAC name or MAC
         address configured against a <svcId, sdpBindId> index pair.

         When sdpBindFPropBMacAddrOrMacNameTag is 'macName (1)',
         sdpBindFPropBMacAddrOrMacName must contain a MAC name which is present
         in the svcMacName column of the svcMacNameTable.

         When sdpBindFPropBMacAddrOrMacNameTag is 'macAddr (2)',
         sdpBindFPropBMacAddrOrMacName must contain a MAC address, encoded in
         network byte order and IEEE 802.3 canonical bit order as defined in
         IEEE Std 802-2001.

         All the MAC addresses configured for a particular SDP (whether
         configured as MAC addresses, or via MAC names) must refer to one
         B-VPLS on the remote system."
    ::= { sdpBindFPropBMacAddrEntry 2 }

sdpBindFPropBMacAddrRowStatus    OBJECT-TYPE
    SYNTAX      RowStatus
    MAX-ACCESS  read-create
    STATUS      current
    DESCRIPTION
        "The value of sdpBindFPropBMacAddrRowStatus specifies the status of
         this row."
    ::= { sdpBindFPropBMacAddrEntry 3 }

sdpAutoBindBgpVplsTableLC        OBJECT-TYPE
    SYNTAX      TimeStamp
    MAX-ACCESS  read-only
    STATUS      current
    DESCRIPTION
        "The value of sdpAutoBindBgpVplsTableLC indicates the sysUpTime at the
         time of the last modification of sdpAutoBindBgpVplsTable.

         If no changes were made to the entry since the last re-initialization
         of the local network management subsystem, then this object contains a
         zero value."
    ::= { tmnxSdpObjs 32 }

sdpAutoBindBgpVplsTable          OBJECT-TYPE
    SYNTAX      SEQUENCE OF SdpAutoBindBgpVplsEntry
    MAX-ACCESS  not-accessible
    STATUS      current
    DESCRIPTION
        "The sdpAutoBindBgpVplsTable has an entry for each SDP Bind entry from
         sdpBindTable which was created as a result of BGP VPLS binding."
    ::= { tmnxSdpObjs 33 }

sdpAutoBindBgpVplsEntry          OBJECT-TYPE
    SYNTAX      SdpAutoBindBgpVplsEntry
    MAX-ACCESS  not-accessible
    STATUS      current
    DESCRIPTION
        "Each row entry contains BGP-related information for an SDP Bind entry
         created as a result of BGP VPLS binding."
    INDEX       {
        svcId,
        sdpBindId
    }
    ::= { sdpAutoBindBgpVplsTable 1 }

SdpAutoBindBgpVplsEntry          ::= SEQUENCE
{ sdpAutoBindBgpVplsTemplateId     PWTemplateId }

sdpAutoBindBgpVplsTemplateId     OBJECT-TYPE
    SYNTAX      PWTemplateId
    MAX-ACCESS  read-only
    STATUS      current
    DESCRIPTION
        "The value of sdpAutoBindBgpVplsTemplateId indicates the the value of
         the pwTemplateId object for the PW template entry used to create this
         SDP Bind."
    ::= { sdpAutoBindBgpVplsEntry 1 }

sdpAtBndBgp129Type2TableLC       OBJECT-TYPE
    SYNTAX      TimeStamp
    MAX-ACCESS  read-only
    STATUS      current
    DESCRIPTION
        "The value of sdpAtBndBgp129Type2TableLC indicates the sysUpTime at the
         time of the last modification of sdpAtBndBgp129Type2Table.

         If no changes were made to the entry since the last re-initialization
         of the local network management subsystem, then this object contains a
         zero value."
    ::= { tmnxSdpObjs 34 }

sdpAtBndBgp129Type2Table         OBJECT-TYPE
    SYNTAX      SEQUENCE OF SdpAtBndBgp129Type2Entry
    MAX-ACCESS  not-accessible
    STATUS      current
    DESCRIPTION
        "The sdpAtBndBgp129Type2Table has an entry for each SDP Bind entry from
         sdpBindTable which was created as a result of BGP Auto-discovery with
         a FEC-129 Type 2."
    ::= { tmnxSdpObjs 35 }

sdpAtBndBgp129Type2Entry         OBJECT-TYPE
    SYNTAX      SdpAtBndBgp129Type2Entry
    MAX-ACCESS  not-accessible
    STATUS      current
    DESCRIPTION
        "Each row entry contains BGP-related information for an SDP Bind entry
         created as a result of BGP Auto-discovery with a FEC-129 Type 2."
    INDEX       {
        svcId,
        sdpBindId
    }
    ::= { sdpAtBndBgp129Type2Table 1 }

SdpAtBndBgp129Type2Entry         ::= SEQUENCE
{
    sdpAtBndBgp129Type2TemplateId    PWTemplateId,
    sdpAtBndBgp129Type2SaiiGlobalId  TmnxPwGlobalId,
    sdpAtBndBgp129Type2SaiiPrefix    Unsigned32,
    sdpAtBndBgp129Type2SaiiAcId      Unsigned32,
    sdpAtBndBgp129Type2TaiiGlobalId  TmnxPwGlobalId,
    sdpAtBndBgp129Type2TaiiPrefix    Unsigned32,
    sdpAtBndBgp129Type2TaiiAcId      Unsigned32
}

sdpAtBndBgp129Type2TemplateId    OBJECT-TYPE
    SYNTAX      PWTemplateId
    MAX-ACCESS  read-only
    STATUS      current
    DESCRIPTION
        "The value of sdpAtBndBgp129Type2TemplateId indicates the the value of
         the pwTemplateId object for the PW template entry used to create this
         SDP Bind."
    ::= { sdpAtBndBgp129Type2Entry 1 }

sdpAtBndBgp129Type2SaiiGlobalId  OBJECT-TYPE
    SYNTAX      TmnxPwGlobalId
    MAX-ACCESS  read-only
    STATUS      current
    DESCRIPTION
        "The value of sdpAtBndBgp129Type2SaiiGlobalId indicates the global
         identifier of Source Attachment Individual Identifier (SAII) portion
         of the Generalized Id FEC element as used by this multi-segment
         pseudo-wire provider-edge in this service."
    ::= { sdpAtBndBgp129Type2Entry 2 }

sdpAtBndBgp129Type2SaiiPrefix    OBJECT-TYPE
    SYNTAX      Unsigned32
    MAX-ACCESS  read-only
    STATUS      current
    DESCRIPTION
        "The value of sdpAtBndBgp129Type2SaiiPrefix indicates the prefix to the
         Source Attachment Individual Identifier (SAII) portion of the
         Generalized Id FEC element as used by this multi-segment pseudo-wire
         provider-edge in this service."
    ::= { sdpAtBndBgp129Type2Entry 3 }

sdpAtBndBgp129Type2SaiiAcId      OBJECT-TYPE
    SYNTAX      Unsigned32
    MAX-ACCESS  read-only
    STATUS      current
    DESCRIPTION
        "The value of sdpAtBndBgp129Type2SaiiAcId indicates the attachment
         circuit identifier part of Source Attachment Individual Identifier
         (SAII) portion of the Generalized Id FEC element as used by this
         multi-segment pseudo-wire provider-edge in this service."
    ::= { sdpAtBndBgp129Type2Entry 4 }

sdpAtBndBgp129Type2TaiiGlobalId  OBJECT-TYPE
    SYNTAX      TmnxPwGlobalId
    MAX-ACCESS  read-only
    STATUS      current
    DESCRIPTION
        "The value of sdpAtBndBgp129Type2TaiiGlobalId indicates the global
         identifier of Taget Attachment Individual Identifier (TAII) portion of
         the Generalized Id FEC element as used by this multi-segment
         pseudo-wire provider-edge in this service."
    ::= { sdpAtBndBgp129Type2Entry 5 }

sdpAtBndBgp129Type2TaiiPrefix    OBJECT-TYPE
    SYNTAX      Unsigned32
    MAX-ACCESS  read-only
    STATUS      current
    DESCRIPTION
        "The value of sdpAtBndBgp129Type2TaiiPrefix indicates the prefix to the
         Taget Attachment Individual Identifier (TAII) portion of the
         Generalized Id FEC element as used by this multi-segment pseudo-wire
         provider-edge in this service."
    ::= { sdpAtBndBgp129Type2Entry 6 }

sdpAtBndBgp129Type2TaiiAcId      OBJECT-TYPE
    SYNTAX      Unsigned32
    MAX-ACCESS  read-only
    STATUS      current
    DESCRIPTION
        "The value of sdpAtBndBgp129Type2TaiiAcId indicates the attachment
         circuit identifier part of Taget Attachment Individual Identifier
         (TAII) portion of the Generalized Id FEC element as used by this
         multi-segment pseudo-wire provider-edge in this service."
    ::= { sdpAtBndBgp129Type2Entry 7 }

sdpBindEthCfmTableLastChanged    OBJECT-TYPE
    SYNTAX      TimeStamp
    MAX-ACCESS  read-only
    STATUS      current
    DESCRIPTION
        "The value of sdpBindEthCfmTableLastChanged indicates the sysUpTime at
         the time of the last modification of the sdpBindEthCfmTable.

         If no changes were made to the entry since the last re-initialization
         of the local network management subsystem, then this object contains a
         zero value."
    ::= { tmnxSdpObjs 36 }

sdpBindEthCfmTable               OBJECT-TYPE
    SYNTAX      SEQUENCE OF SdpBindEthCfmEntry
    MAX-ACCESS  not-accessible
    STATUS      current
    DESCRIPTION
        "The sdpBindEthCfmEntry has an entry for each SDP Bind entry from
         sdpBindTable which was created on a service with ETH-CFM support."
    ::= { tmnxSdpObjs 37 }

sdpBindEthCfmEntry               OBJECT-TYPE
    SYNTAX      SdpBindEthCfmEntry
    MAX-ACCESS  not-accessible
    STATUS      current
    DESCRIPTION
        "Each row entry contains BGP-related information for an SDP Bind entry
         created as a result of BGP Auto-discovery with a FEC-129 Type 2."
    INDEX       {
        svcId,
        sdpBindId
    }
    ::= { sdpBindEthCfmTable 1 }

SdpBindEthCfmEntry               ::= SEQUENCE
{
    sdpBindEthCfmRowLastChanged      TimeStamp,
    sdpBindEthCfmVMepFilter          TruthValue,
    sdpBindEthCfmSquelchIngress      BITS,
    sdpBindEthCfmCollectLmmStats     TruthValue,
    sdpBindEthCfmCollLmmFcSts        TFCSet,
    sdpBindEthCfmCollLmmFcStsInP     TFCSet
}

sdpBindEthCfmRowLastChanged      OBJECT-TYPE
    SYNTAX      TimeStamp
    MAX-ACCESS  read-only
    STATUS      current
    DESCRIPTION
        "The value of sdpBindEthCfmRowLastChanged indicates the sysUpTime at
         the time of the last modification to an object for this row.

         If no changes were made to the entry since the instantiation of the
         row, then this object contains a zero value."
    ::= { sdpBindEthCfmEntry 1 }

sdpBindEthCfmVMepFilter          OBJECT-TYPE
    SYNTAX      TruthValue
    MAX-ACCESS  read-create
    STATUS      current
    DESCRIPTION
        "The value of sdpBindEthCfmVMepFilter specifies whether ETH-CFM PDUs
         egressing the sap or sdp-binding at the same level or lower than that
         of the configured service MEP (the virtual MEP) should be discarded or
         continue to egress.

         Only PDUs that were originated from the virtual MEP or from
         the networks side of the service will be affected, local
         down MEP ETH-CFM transmission are not.  When set to 'true'
         ETH-CFM PDUs with the same or lower level as the virtual
         MEP will be discarded.  When set to 'false', egressing
         ETH-CFM PDUs will pass freely as per the existing ETH-CFM
         configuration."
    DEFVAL      { false }
    ::= { sdpBindEthCfmEntry 2 }

sdpBindEthCfmSquelchIngress      OBJECT-TYPE
    SYNTAX      BITS {
        level0 (0),
        level1 (1),
        level2 (2),
        level3 (3),
        level4 (4),
        level5 (5),
        level6 (6),
        level7 (7)
    }
    MAX-ACCESS  read-create
    STATUS      current
    DESCRIPTION
        "The value of sdpBindEthCfmSquelchIngress specifies the ETH-CFM level
         or levels that are silently discarded on ingress to the SDP binding.
         Any received ETH-CFM PDU matching a level that has been set will be
         dropped without regard for any other ETH-CFM criteria.

         No statistical information or drop count will be available for any
         ETH-CFM PDU that is silently discarded by this option."
    DEFVAL      { {} }
    ::= { sdpBindEthCfmEntry 3 }

sdpBindEthCfmCollectLmmStats     OBJECT-TYPE
    SYNTAX      TruthValue
    MAX-ACCESS  read-create
    STATUS      current
    DESCRIPTION
        "The value of sdpBindEthCfmCollectLmmStats specifies whether or not to
         compute the Y.1731 Ethernet Loss Measurement (ETH-LM) RxFCl and TxFCl
         service frame counters for the specified SDP. Note that when
         sdpBindEthCfmCollectLmmStats is set to 'true', all data traffic
         regardless of forwarding class level, both in and out of profile, will
         be aggregated to a single stat counter.

         Configuration of sdpBindEthCfmCollectLmmStats is mutually exclusive
         with the forwarding class level aware objects
         sdpBindEthCfmCollLmmFcSts and sdpBindEthCfmCollLmmFcStsInP.

         The RxFCl and TxFCl counters are used by ETH-LM tests. An ETH-LM test
         is created using TIMETRA-OAM-PM-MIB::tmnxOamPmCfgLossLmmRowStatus."
    REFERENCE
        "ITU-T G.8013/Y.1731, 'OAM functions and mechanisms for Ethernet based
         networks', 11/2013, Section 8.1 'Frame loss measurement (ETH-LM)'."
    DEFVAL      { false }
    ::= { sdpBindEthCfmEntry 4 }

sdpBindEthCfmCollLmmFcSts        OBJECT-TYPE
    SYNTAX      TFCSet
    MAX-ACCESS  read-create
    STATUS      current
    DESCRIPTION
        "The value of sdpBindEthCfmCollLmmFcSts specifies which forwarding
         class levels have enabled the computation for Y.1731 Ethernet Loss
         Measurement (ETH-LM) RxFCl and TxFCl service frame counters for the
         specified SDP. If the bit corresponding to a forwarding class level is
         set, then a unique counter will be used to track all the combined in
         and out of profile traffic associated with that forwarding class.

         Note that no sdpBindEthCfmCollLmmFcSts bits can be set if
         sdpBindEthCfmCollectLmmStats is set to 'true' as the two are mutually
         exclusive.

         The RxFCl and TxFCl counters are used by ETH-LM tests. An ETH-LM test
         is created using TIMETRA-OAM-PM-MIB::tmnxOamPmCfgLossLmmRowStatus."
    REFERENCE
        "ITU-T G.8013/Y.1731, 'OAM functions and mechanisms for Ethernet based
         networks', 11/2013, Section 8.1 'Frame loss measurement (ETH-LM)'."
    DEFVAL      { {} }
    ::= { sdpBindEthCfmEntry 5 }

sdpBindEthCfmCollLmmFcStsInP     OBJECT-TYPE
    SYNTAX      TFCSet
    MAX-ACCESS  read-create
    STATUS      current
    DESCRIPTION
        "The value of sdpBindEthCfmCollLmmFcStsInP specifies which forwarding
         class levels (in profile only) have enabled the computation for Y.1731
         Ethernet Loss Measurement (ETH-LM) RxFCl and TxFCl service frame
         counters for the specified SDP. If the bit corresponding to a
         forwarding class level is set, then a unique counter will be used to
         track only all the in profile data traffic that is associated with
         that forwarding class level.

         Note that no sdpBindEthCfmCollLmmFcStsInP bits can be set if
         sdpBindEthCfmCollectLmmStats is set to 'true' as the two are mutually
         exclusive.

         The RxFCl and TxFCl counters are used by ETH-LM tests. An ETH-LM test
         is created using TIMETRA-OAM-PM-MIB::tmnxOamPmCfgLossLmmRowStatus."
    REFERENCE
        "ITU-T G.8013/Y.1731, 'OAM functions and mechanisms for Ethernet based
         networks', 11/2013, Section 8.1 'Frame loss measurement (ETH-LM)'."
    DEFVAL      { {} }
    ::= { sdpBindEthCfmEntry 6 }

sdpBindTlsSpbTblLastChanged      OBJECT-TYPE
    SYNTAX      TimeStamp
    MAX-ACCESS  read-only
    STATUS      current
    DESCRIPTION
        "The value of sdpBindTlsSpbTblLastChanged indicates the sysUpTime at
         the time of the last modification of sdpBindTlsSpbTable.

         If no changes were made to the entry since the last re-initialization
         of the local network management subsystem, then this object contains a
         zero value."
    ::= { tmnxSdpObjs 38 }

sdpBindTlsSpbTable               OBJECT-TYPE
    SYNTAX      SEQUENCE OF SdpBindTlsSpbEntry
    MAX-ACCESS  not-accessible
    STATUS      current
    DESCRIPTION
        "A table that contains TLS SDP-Bind specific Shortest Path Bridging
         (SPB) information."
    ::= { tmnxSdpObjs 39 }

sdpBindTlsSpbEntry               OBJECT-TYPE
    SYNTAX      SdpBindTlsSpbEntry
    MAX-ACCESS  not-accessible
    STATUS      current
    DESCRIPTION
        "A row entry that contains TLS SDP-Bind specific SPB information."
    INDEX       {
        svcId,
        sdpBindId
    }
    ::= { sdpBindTlsSpbTable 1 }

SdpBindTlsSpbEntry               ::= SEQUENCE
{
    sdpBindTlsSpbRowStatus           RowStatus,
    sdpBindTlsSpbLastChgd            TimeStamp,
    sdpBindTlsSpbIfIndex             InterfaceIndexOrZero,
    sdpBindTlsSpbAdminState          TmnxAdminState
}

sdpBindTlsSpbRowStatus           OBJECT-TYPE
    SYNTAX      RowStatus
    MAX-ACCESS  read-create
    STATUS      current
    DESCRIPTION
        "This value of the object sdpBindTlsSpbRowStatus specifies the status
         of this row."
    ::= { sdpBindTlsSpbEntry 1 }

sdpBindTlsSpbLastChgd            OBJECT-TYPE
    SYNTAX      TimeStamp
    MAX-ACCESS  read-only
    STATUS      current
    DESCRIPTION
        "The value of sdpBindTlsSpbLastChgd indicates the timestamp of last
         change to this row in sdpBindTlsSpbTable."
    ::= { sdpBindTlsSpbEntry 2 }

sdpBindTlsSpbIfIndex             OBJECT-TYPE
    SYNTAX      InterfaceIndexOrZero
    MAX-ACCESS  read-only
    STATUS      current
    DESCRIPTION
        "The value of sdpBindTlsSpbIfIndex indicates the interface index
         assigned to this SDP-Bind for Shortest Path Bridging."
    ::= { sdpBindTlsSpbEntry 3 }

sdpBindTlsSpbAdminState          OBJECT-TYPE
    SYNTAX      TmnxAdminState
    MAX-ACCESS  read-create
    STATUS      current
    DESCRIPTION
        "The sdpBindTlsSpbAdminState specifies the desired administrative state
         for Shortest Path Bridging on this sdp-bind."
    DEFVAL      { outOfService }
    ::= { sdpBindTlsSpbEntry 4 }

sdpPwPortTblLastChanged          OBJECT-TYPE
    SYNTAX      TimeStamp
    MAX-ACCESS  read-only
    STATUS      current
    DESCRIPTION
        "The value of sdpPwPortTblLastChanged indicates the sysUpTime at the
         time of the last modification of sdpPwPortTable.

         If no changes were made to the entry since the last re-initialization
         of the local network management subsystem, then this object contains a
         zero value."
    ::= { tmnxSdpObjs 40 }

sdpPwPortTable                   OBJECT-TYPE
    SYNTAX      SEQUENCE OF SdpPwPortEntry
    MAX-ACCESS  not-accessible
    STATUS      current
    DESCRIPTION
        "A table that contains SDP specific pseudo-wire port information."
    ::= { tmnxSdpObjs 41 }

sdpPwPortEntry                   OBJECT-TYPE
    SYNTAX      SdpPwPortEntry
    MAX-ACCESS  not-accessible
    STATUS      current
    DESCRIPTION
        "A row entry that contains port specific pseudo-wire information."
    INDEX       {
        sdpId,
        sdpPwPortId
    }
    ::= { sdpPwPortTable 1 }

SdpPwPortEntry                   ::= SEQUENCE
{
    sdpPwPortId                      Unsigned32,
    sdpPwPortRowStatus               RowStatus,
    sdpPwPortLastChgd                TimeStamp,
    sdpPwPortAdminStatus             ServiceAdminStatus,
    sdpPwPortVcId                    TmnxVcId,
    sdpPwPortEncapType               INTEGER,
    sdpPwPortOperStatus              INTEGER,
    sdpPwPortOperFlags               BITS,
    sdpPwPortVcType                  SdpBindVcType,
    sdpPwPortVlanVcTag               Unsigned32,
    sdpPwPortEgrShapVPort            TNamedItemOrEmpty,
    sdpPwPortEgrShapDefIntDestId     TNamedItemOrEmpty,
    sdpPwPortEgrShapSapSecShaper     TNamedItemOrEmpty,
    sdpPwPortMonOperGrp              TNamedItemOrEmpty,
    sdpPwPortIngVcLabel              Unsigned32,
    sdpPwPortEgrVcLabel              Unsigned32,
    sdpPwPortControlWord             TruthValue
}

sdpPwPortId                      OBJECT-TYPE
    SYNTAX      Unsigned32 (1..32767)
    MAX-ACCESS  not-accessible
    STATUS      current
    DESCRIPTION
        "This value of the object sdpPwPortId specifies the pseudo-wire port
         identifier associated with the SDP."
    ::= { sdpPwPortEntry 1 }

sdpPwPortRowStatus               OBJECT-TYPE
    SYNTAX      RowStatus
    MAX-ACCESS  read-create
    STATUS      current
    DESCRIPTION
        "This value of the object sdpPwPortRowStatus specifies the status of
         this row.

         The value of sdpPwPortVcId must be set to a non-default value when
         creating a row."
    ::= { sdpPwPortEntry 2 }

sdpPwPortLastChgd                OBJECT-TYPE
    SYNTAX      TimeStamp
    MAX-ACCESS  read-only
    STATUS      current
    DESCRIPTION
        "The value of sdpPwPortLastChgd indicates the timestamp of last change
         to this row in sdpPwPortTable."
    ::= { sdpPwPortEntry 3 }

sdpPwPortAdminStatus             OBJECT-TYPE
    SYNTAX      ServiceAdminStatus
    MAX-ACCESS  read-create
    STATUS      current
    DESCRIPTION
        "The value of the object sdpPwPortAdminStatus specifies the
         administrative state of this pseudo-wire port entry."
    DEFVAL      { down }
    ::= { sdpPwPortEntry 4 }

sdpPwPortVcId                    OBJECT-TYPE
    SYNTAX      TmnxVcId
    MAX-ACCESS  read-create
    STATUS      current
    DESCRIPTION
        "The value of sdpPwPortVcId specifies the virtual circuit identifier
         associated with this pseudo-wire port entry.

            An 'inconsistentValue' error is returned if an attempt is made to
            create a row entry in this table without specifying value of this
            object."
    ::= { sdpPwPortEntry 5 }

sdpPwPortEncapType               OBJECT-TYPE
    SYNTAX      INTEGER {
        none  (0),
        dot1q (2),
        qinq  (10)
    }
    MAX-ACCESS  read-create
    STATUS      obsolete
    DESCRIPTION
        "The value of sdpPwPortEncapType specifies the encapsulation type of
         this pseudo-wire port entry.

         The sdpPwPortEncapType object is replaced with
         TIMETRA-PORT-MIB::tmnxPwPortEncapType object."
    DEFVAL      { dot1q }
    ::= { sdpPwPortEntry 6 }

sdpPwPortOperStatus              OBJECT-TYPE
    SYNTAX      INTEGER {
        up   (1),
        down (5)
    }
    MAX-ACCESS  read-only
    STATUS      current
    DESCRIPTION
        "The value of sdpPwPortOperStatus indicates the operating status of
         this Service-SDP binding.
            'up'               The Service-SDP binding is operational.

            'down'             The binding is administratively down."
    ::= { sdpPwPortEntry 7 }

sdpPwPortOperFlags               OBJECT-TYPE
    SYNTAX      BITS {
        sdpBindAdminDown        (0),
        svcAdminDown            (1),
        stitchingSvcTxDown      (2),
        sdpOperDown             (3),
        sdpPathMtuTooSmall      (4),
        noIngressVcLabel        (5),
        noEgressVcLabel         (6),
        svcMtuMismatch          (7),
        vcTypeMismatch          (8),
        relearnLimitExceeded    (9),
        iesIfAdminDown          (10),
        releasedIngressVcLabel  (11),
        labelsExhausted         (12),
        svcParamMismatch        (13),
        insufficientBandwidth   (14),
        pwPeerFaultStatusBits   (15),
        meshSdpDown             (16),
        notManagedByMcRing      (17),
        outOfResource           (18),
        mhStandby               (19),
        oamDownMepFault         (20),
        oamUpMepFault           (21),
        standbySigSlaveTxDown   (22),
        operGrpDown             (23),
        withdrawnIngressVcLabel (24),
        labelStackLimitExceeded (25)
    }
    MAX-ACCESS  read-only
    STATUS      current
    DESCRIPTION
        "This object indicates all the conditions that affect the operating
         status of this pseudo-wire port:

         The bit values are as follows:

         sdpBindAdminDown        (0)  - SDP Bind is admin down.
         svcAdminDown            (1)  - Service is admin down.
         stitchingSvcTxDown      (2)  - PW-PORT FPE stitching svc
                                     transmit is down
         sdpOperDown             (3)  - SDP is oper down.
         sdpPathMtuTooSmall      (4)  - SDP's path MTU minus SDP Bind control
                                     word size is less than Service MTU.
         noIngressVcLabel        (5)  - No ingress VC label.
         noEgressVcLabel         (6)  - No egress VC label.
         svcMtuMismatch          (7)  - Service MTU mismatch with the
                                     remote PE.
         vcTypeMismatch          (8)  - VC type mismatch with the remote PE.
         relearnLimitExceeded    (9)  - MAC relearn limit was exceeded
                                     (TLS only).
         iesIfAdminDown         (10)  - IP interface is admin down
                                     (IES and VPRN only).
         releasedIngressVcLabel (11)  - Peer released our ingress VC label.
         labelsExhausted        (12)  - Label Manager has ran out of labels.
         svcParamMismatch       (13)  - Service-specific parameter mismatch.
         insufficientBandwidth  (14)  - Insufficient bandwidth to allocate
                                     to SDP binding.
         pwPeerFaultStatusBits  (15)  - Received PW fault status bits from
                                     peer.
         meshSdpDown            (16)  - Mesh SDP Down.
         notManagedByMcRing     (17)  - Not managed by mc-ring.
         outOfResource          (18)  - Such as memory.
         mhStandby              (19)  - Standby due to BGP.
                                     multi-home protocol.
         oamDownMepFault        (20)  - ETH-CFM down MEP fault detected.
         oamUpMepFault          (21)  - ETH-CFM up MEP fault detected.
         standbySigSlaveTxDown  (22)  - Transmit is down for
                                     standby-sig-spoke.
         operGrpDown            (23)  - Operational group is down.
         withdrawnIngressVcLabel(24)  - Withdrawn due to incompatibility.
         labelStackLimitExceeded(25)  - label stack overhead exceeding the
                                     egress IOM limitation."
    ::= { sdpPwPortEntry 8 }

sdpPwPortVcType                  OBJECT-TYPE
    SYNTAX      SdpBindVcType
    MAX-ACCESS  read-create
    STATUS      current
    DESCRIPTION
        "The value of sdpPwPortVcType specifies the type of virtual circuit
         (VC) associated with this pseudo-wire port entry."
    DEFVAL      { ether }
    ::= { sdpPwPortEntry 9 }

sdpPwPortVlanVcTag               OBJECT-TYPE
    SYNTAX      Unsigned32 (0..4095)
    MAX-ACCESS  read-create
    STATUS      current
    DESCRIPTION
        "The value of sdpPwPortVlanVcTag specifies the VLAN VC tag for this
         pseudo-wire port entry."
    DEFVAL      { '0fff'H }
    ::= { sdpPwPortEntry 10 }

sdpPwPortEgrShapVPort            OBJECT-TYPE
    SYNTAX      TNamedItemOrEmpty
    MAX-ACCESS  read-create
    STATUS      current
    DESCRIPTION
        "The value of sdpPwPortEgrShapVPort specifies the virtual port name of
         the shaper on the egress side for this pseudo-wire port entry."
    DEFVAL      { ''H }
    ::= { sdpPwPortEntry 11 }

sdpPwPortEgrShapDefIntDestId     OBJECT-TYPE
    SYNTAX      TNamedItemOrEmpty
    MAX-ACCESS  read-create
    STATUS      current
    DESCRIPTION
        "The value of sdpPwPortEgrShapDefIntDestId specifies the default
         intermediate destination identifier on the egress side which will
            eventually map to an HSMDAv2 secondary shaper for this
         pseudo-wire port entry."
    DEFVAL      { ''H }
    ::= { sdpPwPortEntry 12 }

sdpPwPortEgrShapSapSecShaper     OBJECT-TYPE
    SYNTAX      TNamedItemOrEmpty
    MAX-ACCESS  read-create
    STATUS      current
    DESCRIPTION
        "The value of sdpPwPortEgrShapSapSecShaper specifies the SAP secondary
         shaper associated on the egress side for this pseudo-wire port entry."
    DEFVAL      { ''H }
    ::= { sdpPwPortEntry 13 }

sdpPwPortMonOperGrp              OBJECT-TYPE
    SYNTAX      TNamedItemOrEmpty
    MAX-ACCESS  read-create
    STATUS      current
    DESCRIPTION
        "The value of the sdpPwPortMonOperGrp specifies the monitoring
         operational group name associated with this pseudo-wire port entry."
    DEFVAL      { ''H }
    ::= { sdpPwPortEntry 14 }

sdpPwPortIngVcLabel              OBJECT-TYPE
    SYNTAX      Unsigned32 (0 | 1..1048575)
    MAX-ACCESS  read-create
    STATUS      current
    DESCRIPTION
        "The value of sdpPwPortIngVcLabel specifies the static MPLS VC label
         used by the far-end device to send packets to this SDP."
    DEFVAL      { 0 }
    ::= { sdpPwPortEntry 15 }

sdpPwPortEgrVcLabel              OBJECT-TYPE
    SYNTAX      Unsigned32 (0 | 16..1048575)
    MAX-ACCESS  read-create
    STATUS      current
    DESCRIPTION
        "The value of sdpPwPortEgrVcLabel specifies the static MPLS VC label
         used by this device to send packets to the far-end device in this SDP."
    DEFVAL      { 0 }
    ::= { sdpPwPortEntry 16 }

sdpPwPortControlWord             OBJECT-TYPE
    SYNTAX      TruthValue
    MAX-ACCESS  read-create
    STATUS      current
    DESCRIPTION
        "The sdpPwPortControlWord specifies whether the use of the
         'ControlWord' is preferred or not."
    DEFVAL      { false }
    ::= { sdpPwPortEntry 17 }

sdpGrpTblLastChanged             OBJECT-TYPE
    SYNTAX      TimeStamp
    MAX-ACCESS  read-only
    STATUS      current
    DESCRIPTION
        "The value of sdpGrpTblLastChanged indicates the sysUpTime at the time
         of the last modification of sdpGrpTable.

         If no changes were made to the entry since the last re-initialization
         of the local network management subsystem, then this object contains a
         zero value."
    ::= { tmnxSdpObjs 42 }

sdpGrpTable                      OBJECT-TYPE
    SYNTAX      SEQUENCE OF SdpGrpEntry
    MAX-ACCESS  not-accessible
    STATUS      current
    DESCRIPTION
        "A table that contains SDP Group information."
    ::= { tmnxSdpObjs 43 }

sdpGrpEntry                      OBJECT-TYPE
    SYNTAX      SdpGrpEntry
    MAX-ACCESS  not-accessible
    STATUS      current
    DESCRIPTION
        "Each row specifies information about a specific SDP Group."
    INDEX       { sdpGrpName }
    ::= { sdpGrpTable 1 }

SdpGrpEntry                      ::= SEQUENCE
{
    sdpGrpName                       TNamedItem,
    sdpGrpRowStatus                  RowStatus,
    sdpGrpLastChange                 TimeStamp,
    sdpGrpValue                      Unsigned32
}

sdpGrpName                       OBJECT-TYPE
    SYNTAX      TNamedItem
    MAX-ACCESS  not-accessible
    STATUS      current
    DESCRIPTION
        "The value of the object sdpGrpName specifies the SDP Group identifier."
    ::= { sdpGrpEntry 1 }

sdpGrpRowStatus                  OBJECT-TYPE
    SYNTAX      RowStatus
    MAX-ACCESS  read-create
    STATUS      current
    DESCRIPTION
        "This value of the object sdpGrpRowStatus specifies the status of this
         row."
    ::= { sdpGrpEntry 2 }

sdpGrpLastChange                 OBJECT-TYPE
    SYNTAX      TimeStamp
    MAX-ACCESS  read-only
    STATUS      current
    DESCRIPTION
        "The value of sdpGrpLastChange indicates the timestamp of last change
         to this row in sdpGrpTable.

         If no changes were made to the entry since the last re-initialization
         of the local network management subsystem, then this object contains a
         zero value."
    ::= { sdpGrpEntry 3 }

sdpGrpValue                      OBJECT-TYPE
    SYNTAX      Unsigned32 (0..31)
    MAX-ACCESS  read-create
    STATUS      current
    DESCRIPTION
        "This value of the object sdpGrpValue specifies the value associated
         with this SDP group."
    DEFVAL      { 0 }
    ::= { sdpGrpEntry 4 }

sdpSdpGrpTblLastChanged          OBJECT-TYPE
    SYNTAX      TimeStamp
    MAX-ACCESS  read-only
    STATUS      current
    DESCRIPTION
        "The value of sdpSdpGrpTblLastChanged indicates the sysUpTime at the
         time of the last modification of sdpSdpGrpTable.

         If no changes were made to the entry since the last re-initialization
         of the local network management subsystem, then this object contains a
         zero value."
    ::= { tmnxSdpObjs 44 }

sdpSdpGrpTable                   OBJECT-TYPE
    SYNTAX      SEQUENCE OF SdpSdpGrpEntry
    MAX-ACCESS  not-accessible
    STATUS      current
    DESCRIPTION
        "A table that contains SDP group information in which SDPs
         participates."
    ::= { tmnxSdpObjs 45 }

sdpSdpGrpEntry                   OBJECT-TYPE
    SYNTAX      SdpSdpGrpEntry
    MAX-ACCESS  not-accessible
    STATUS      current
    DESCRIPTION
        "Each row specifies information about a specific SDP participation with
         a specific SDP group."
    INDEX       {
        sdpId,
        sdpGrpName
    }
    ::= { sdpSdpGrpTable 1 }

SdpSdpGrpEntry                   ::= SEQUENCE
{
    sdpSdpGrpRowStatus               RowStatus,
    sdpSdpGrpLastChange              TimeStamp
}

sdpSdpGrpRowStatus               OBJECT-TYPE
    SYNTAX      RowStatus
    MAX-ACCESS  read-create
    STATUS      current
    DESCRIPTION
        "This value of the object sdpSdpGrpRowStatus specifies the status of
         this row."
    ::= { sdpSdpGrpEntry 1 }

sdpSdpGrpLastChange              OBJECT-TYPE
    SYNTAX      TimeStamp
    MAX-ACCESS  read-only
    STATUS      current
    DESCRIPTION
        "The value of sdpSdpGrpLastChange indicates the timestamp of last
         change to this row in sdpSdpGrpTable.

         If no changes were made to the entry since the last re-initialization
         of the local network management subsystem, then this object contains a
         zero value."
    ::= { sdpSdpGrpEntry 2 }

pwTempIncSdpGrpTableLastChanged  OBJECT-TYPE
    SYNTAX      TimeStamp
    MAX-ACCESS  read-only
    STATUS      current
    DESCRIPTION
        "The value of pwTempIncSdpGrpTableLastChanged indicates the sysUpTime
         at the time of the last modification of pwTempIncSdpGrpTable.

         If no changes were made to the entry since the last re-initialization
         of the local network management subsystem, then this object contains a
         zero value."
    ::= { tmnxSdpObjs 46 }

pwTempIncSdpGrpTable             OBJECT-TYPE
    SYNTAX      SEQUENCE OF PwTempIncSdpGrpEntry
    MAX-ACCESS  not-accessible
    STATUS      current
    DESCRIPTION
        "A table that contains entries for pseudowire (PW) templates specifying
         included SDP groups."
    ::= { tmnxSdpObjs 47 }

pwTempIncSdpGrpEntry             OBJECT-TYPE
    SYNTAX      PwTempIncSdpGrpEntry
    MAX-ACCESS  not-accessible
    STATUS      current
    DESCRIPTION
        "Each entry contains specific included SDP group information for a
         specific pseudowire (PW) template."
    INDEX       {
        pwTemplateId,
        sdpGrpName
    }
    ::= { pwTempIncSdpGrpTable 1 }

PwTempIncSdpGrpEntry             ::= SEQUENCE
{
    pwTempIncSdpGrpRowStatus         RowStatus,
    pwTempIncSdpGrpLastChanged       TimeStamp
}

pwTempIncSdpGrpRowStatus         OBJECT-TYPE
    SYNTAX      RowStatus
    MAX-ACCESS  read-create
    STATUS      current
    DESCRIPTION
        "The value of pwTempIncSdpGrpRowStatus is used for the creation and
         deletion of entries in the table."
    ::= { pwTempIncSdpGrpEntry 1 }

pwTempIncSdpGrpLastChanged       OBJECT-TYPE
    SYNTAX      TimeStamp
    MAX-ACCESS  read-only
    STATUS      current
    DESCRIPTION
        "The value of pwTempIncSdpGrpLastChanged indicates the sysUpTime at the
         time of the last modification of this entry.

         If no changes were made to the entry since the last re-initialization
         of the local network management subsystem, then this object contains a
         zero value."
    ::= { pwTempIncSdpGrpEntry 2 }

pwTempExcSdpGrpTableLastChanged  OBJECT-TYPE
    SYNTAX      TimeStamp
    MAX-ACCESS  read-only
    STATUS      current
    DESCRIPTION
        "The value of pwTempExcSdpGrpTableLastChanged indicates the sysUpTime
         at the time of the last modification of pwTempExcSdpGrpTable.

         If no changes were made to the entry since the last re-initialization
         of the local network management subsystem, then this object contains a
         zero value."
    ::= { tmnxSdpObjs 48 }

pwTempExcSdpGrpTable             OBJECT-TYPE
    SYNTAX      SEQUENCE OF PwTempExcSdpGrpEntry
    MAX-ACCESS  not-accessible
    STATUS      current
    DESCRIPTION
        "A table that contains entries for pseudowire (PW) templates specifying
         excluded SDP groups."
    ::= { tmnxSdpObjs 49 }

pwTempExcSdpGrpEntry             OBJECT-TYPE
    SYNTAX      PwTempExcSdpGrpEntry
    MAX-ACCESS  not-accessible
    STATUS      current
    DESCRIPTION
        "Each entry contains specific excluded SDP group information for a
         specific pseudowire (PW) template."
    INDEX       {
        pwTemplateId,
        sdpGrpName
    }
    ::= { pwTempExcSdpGrpTable 1 }

PwTempExcSdpGrpEntry             ::= SEQUENCE
{
    pwTempExcSdpGrpRowStatus         RowStatus,
    pwTempExcSdpGrpLastChanged       TimeStamp
}

pwTempExcSdpGrpRowStatus         OBJECT-TYPE
    SYNTAX      RowStatus
    MAX-ACCESS  read-create
    STATUS      current
    DESCRIPTION
        "The value of pwTempExcSdpGrpRowStatus is used for the creation and
         deletion of entries in the table."
    ::= { pwTempExcSdpGrpEntry 1 }

pwTempExcSdpGrpLastChanged       OBJECT-TYPE
    SYNTAX      TimeStamp
    MAX-ACCESS  read-only
    STATUS      current
    DESCRIPTION
        "The value of pwTempExcSdpGrpLastChanged indicates the sysUpTime at the
         time of the last modification of this entry.

         If no changes were made to the entry since the last re-initialization
         of the local network management subsystem, then this object contains a
         zero value."
    ::= { pwTempExcSdpGrpEntry 2 }

sdpBindPwPathTableLastChanged    OBJECT-TYPE
    SYNTAX      TimeStamp
    MAX-ACCESS  read-only
    STATUS      current
    DESCRIPTION
        "The value of sdpBindPwPathTableLastChanged indicates the sysUpTime at
         the time of the last modification of sdpBindPwPathTable.

         If no changes were made to the entry since the last re-initialization
         of the local network management subsystem, then this object contains a
         zero value."
    ::= { tmnxSdpObjs 50 }

sdpBindPwPathTable               OBJECT-TYPE
    SYNTAX      SEQUENCE OF SdpBindPwPathEntry
    MAX-ACCESS  not-accessible
    STATUS      current
    DESCRIPTION
        "The sdpBindPwPathTable contains Pseudo-Wire path information per SDP
         binding."
    ::= { tmnxSdpObjs 51 }

sdpBindPwPathEntry               OBJECT-TYPE
    SYNTAX      SdpBindPwPathEntry
    MAX-ACCESS  not-accessible
    STATUS      current
    DESCRIPTION
        "The sdpBindPwPathEntry contains Pseudo-Wire path information for
         specific SDP binding."
    INDEX       {
        svcId,
        sdpBindId
    }
    ::= { sdpBindPwPathTable 1 }

SdpBindPwPathEntry               ::= SEQUENCE
{
    sdpBindPwPathRowStatus           RowStatus,
    sdpBindPwPathLastChanged         TimeStamp,
    sdpBindPwPathAgi                 TmnxVPNRouteDistinguisher,
    sdpBindPwPathSaiiGlobalId        TmnxMplsTpGlobalID,
    sdpBindPwPathSaiiNodeId          TmnxMplsTpNodeID,
    sdpBindPwPathSaiiAcId            Unsigned32,
    sdpBindPwPathTaiiGlobalId        TmnxMplsTpGlobalID,
    sdpBindPwPathTaiiNodeId          TmnxMplsTpNodeID,
    sdpBindPwPathTaiiAcId            Unsigned32
}

sdpBindPwPathRowStatus           OBJECT-TYPE
    SYNTAX      RowStatus
    MAX-ACCESS  read-create
    STATUS      current
    DESCRIPTION
        "The value of sdpBindPwPathRowStatus is used for the creation and
         deletion of entries in the table."
    ::= { sdpBindPwPathEntry 1 }

sdpBindPwPathLastChanged         OBJECT-TYPE
    SYNTAX      TimeStamp
    MAX-ACCESS  read-only
    STATUS      current
    DESCRIPTION
        "The value of sdpBindPwPathLastChanged indicates the sysUpTime at the
         time of the last modification of this entry.

         If no changes were made to the entry since the last re-initialization
         of the local network management subsystem, then this object contains a
         zero value."
    ::= { sdpBindPwPathEntry 2 }

sdpBindPwPathAgi                 OBJECT-TYPE
    SYNTAX      TmnxVPNRouteDistinguisher
    MAX-ACCESS  read-create
    STATUS      current
    DESCRIPTION
        "The value of sdpBindPwPathAgi specifies the Attachment Group
         Identifier (AGI) portion of the Generalized Id FEC element from the
         pseudowire setup for this SDP Bind."
    DEFVAL      { '0000000000000000'H }
    ::= { sdpBindPwPathEntry 3 }

sdpBindPwPathSaiiGlobalId        OBJECT-TYPE
    SYNTAX      TmnxMplsTpGlobalID
    MAX-ACCESS  read-create
    STATUS      current
    DESCRIPTION
        "The value of sdpBindPwPathSaiiGlobalId specifies the global identifier
         of Source Attachment Individual Identifier (SAII) portion of the
         Generalized Id FEC element as used by this SDP binding in this
         service."
    DEFVAL      { 0 }
    ::= { sdpBindPwPathEntry 4 }

sdpBindPwPathSaiiNodeId          OBJECT-TYPE
    SYNTAX      TmnxMplsTpNodeID
    MAX-ACCESS  read-create
    STATUS      current
    DESCRIPTION
        "The value of sdpBindPwPathSaiiNodeId specifies the MPLS-TP node
         identifier to the Source Attachment Individual Identifier (SAII)
         portion of the Generalized Id FEC element as used by this SDP binding
         in this service."
    DEFVAL      { 0 }
    ::= { sdpBindPwPathEntry 5 }

sdpBindPwPathSaiiAcId            OBJECT-TYPE
    SYNTAX      Unsigned32
    MAX-ACCESS  read-create
    STATUS      current
    DESCRIPTION
        "The value of sdpBindPwPathSaiiAcId specifies the attachment circuit
         identifier part of Source Attachment Individual Identifier (SAII)
         portion of the Generalized Id FEC element as used by this SDP binding
         in this service."
    DEFVAL      { 0 }
    ::= { sdpBindPwPathEntry 6 }

sdpBindPwPathTaiiGlobalId        OBJECT-TYPE
    SYNTAX      TmnxMplsTpGlobalID
    MAX-ACCESS  read-create
    STATUS      current
    DESCRIPTION
        "The value of sdpBindPwPathTaiiGlobalId specifies the global identifier
         of Target Attachment Individual Identifier (TAII) portion of the
         Generalized Id FEC element as used by this SDP binding in this
         service."
    DEFVAL      { 0 }
    ::= { sdpBindPwPathEntry 7 }

sdpBindPwPathTaiiNodeId          OBJECT-TYPE
    SYNTAX      TmnxMplsTpNodeID
    MAX-ACCESS  read-create
    STATUS      current
    DESCRIPTION
        "The value of sdpBindPwPathTaiiNodeId specifies the MPLS-TP node
         identifier to the Target Attachment Individual Identifier (TAII)
         portion of the Generalized Id FEC element as used by this SDP binding
         in this service."
    DEFVAL      { 0 }
    ::= { sdpBindPwPathEntry 8 }

sdpBindPwPathTaiiAcId            OBJECT-TYPE
    SYNTAX      Unsigned32
    MAX-ACCESS  read-create
    STATUS      current
    DESCRIPTION
        "The value of sdpBindPwPathTaiiAcId specifies the attachment circuit
         identifier part of Target Attachment Individual Identifier (TAII)
         portion of the Generalized Id FEC element as used by this SDP binding
         in this service."
    DEFVAL      { 0 }
    ::= { sdpBindPwPathEntry 9 }

sdpBindCtrlChanPwTableLastChgd   OBJECT-TYPE
    SYNTAX      TimeStamp
    MAX-ACCESS  read-only
    STATUS      current
    DESCRIPTION
        "The value of sdpBindCtrlChanPwTableLastChgd indicates the sysUpTime at
         the time of the last modification of sdpBindCtrlChanPwTable.

         If no changes were made to the entry since the last re-initialization
         of the local network management subsystem, then this object contains a
         zero value."
    ::= { tmnxSdpObjs 52 }

sdpBindCtrlChanPwTable           OBJECT-TYPE
    SYNTAX      SEQUENCE OF SdpBindCtrlChanPwEntry
    MAX-ACCESS  not-accessible
    STATUS      current
    DESCRIPTION
        "The sdpBindCtrlChanPwTable contains control channel Pseudo-Wire
         information per SDP binding."
    ::= { tmnxSdpObjs 53 }

sdpBindCtrlChanPwEntry           OBJECT-TYPE
    SYNTAX      SdpBindCtrlChanPwEntry
    MAX-ACCESS  not-accessible
    STATUS      current
    DESCRIPTION
        "The sdpBindCtrlChanPwEntry contains control channel Pseudo-Wire
         information for specific SDP binding."
    INDEX       {
        svcId,
        sdpBindId
    }
    ::= { sdpBindCtrlChanPwTable 1 }

SdpBindCtrlChanPwEntry           ::= SEQUENCE
{
    sdpBindCtrlChanPwLastChanged     TimeStamp,
    sdpBindCtrlChanPwStatus          TmnxEnabledDisabled,
    sdpBindCtrlChanPwRefreshTimer    Unsigned32,
    sdpBindCtrlChanPwPeerExpired     TruthValue,
    sdpBindCtrlChanPwRequestTimer    Unsigned32,
    sdpBindCtrlChanPwRetryTimer      Unsigned32,
    sdpBindCtrlChanPwTimeoutMult     Unsigned32,
    sdpBindCtrlChanPwAck             TruthValue
}

sdpBindCtrlChanPwLastChanged     OBJECT-TYPE
    SYNTAX      TimeStamp
    MAX-ACCESS  read-only
    STATUS      current
    DESCRIPTION
        "The value of sdpBindCtrlChanPwLastChanged indicates the sysUpTime at
         the time of the last modification of this entry.

         If no changes were made to the entry since the last re-initialization
         of the local network management subsystem, then this object contains a
         zero value."
    ::= { sdpBindCtrlChanPwEntry 1 }

sdpBindCtrlChanPwStatus          OBJECT-TYPE
    SYNTAX      TmnxEnabledDisabled
    MAX-ACCESS  read-write
    STATUS      current
    DESCRIPTION
        "The value of sdpBindCtrlChanPwStatus specifies the status of control
         channel for the pseudo-wire path for this SDP binding."
    DEFVAL      { disabled }
    ::= { sdpBindCtrlChanPwEntry 2 }

sdpBindCtrlChanPwRefreshTimer    OBJECT-TYPE
    SYNTAX      Unsigned32 (0 | 10..65535)
    UNITS       "seconds"
    MAX-ACCESS  read-write
    STATUS      current
    DESCRIPTION
        "The value of sdpBindCtrlChanPwRefreshTimer specifies the refresh timer
         value to be used when control channel for the pseudo-wire path is
         enabled for this SDP binding.

         An 'inconsistentValue' error is returned if the value of
         sdpBindCtrlChanPwRequestTimer is set to non-zero when
         sdpBindCtrlChanPwRefreshTimer is set to non-zero."
    DEFVAL      { 0 }
    ::= { sdpBindCtrlChanPwEntry 3 }

sdpBindCtrlChanPwPeerExpired     OBJECT-TYPE
    SYNTAX      TruthValue
    MAX-ACCESS  read-only
    STATUS      current
    DESCRIPTION
        "The value of sdpBindCtrlChanPwPeerExpired indicates whether
         sdpBindCtrlChanPwStatus was not received after 3.5 times of
         sdpBindCtrlChanPwRefreshTimer value for the pseudo-wire path for this
         SDP binding."
    ::= { sdpBindCtrlChanPwEntry 4 }

sdpBindCtrlChanPwRequestTimer    OBJECT-TYPE
    SYNTAX      Unsigned32 (0 | 10..65535)
    UNITS       "seconds"
    MAX-ACCESS  read-write
    STATUS      current
    DESCRIPTION
        "The value of sdpBindCtrlChanPwRequestTimer specifies the request timer
         value to be used when control channel for the pseudo-wire path is
         enabled for this SDP binding.

         An 'inconsistentValue' error is returned if the value of
         sdpBindCtrlChanPwRequestTimer is set to non-zero when
         sdpBindCtrlChanPwRefreshTimer is set to non-zero.

         An 'inconsistentValue' error is returned if the value of
         sdpBindCtrlChanPwRequestTimer is set to non-zero when value of either
         sdpBindCtrlChanPwRetryTimer or sdpBindCtrlChanPwTimeoutMult is also
         set to zero."
    DEFVAL      { 0 }
    ::= { sdpBindCtrlChanPwEntry 5 }

sdpBindCtrlChanPwRetryTimer      OBJECT-TYPE
    SYNTAX      Unsigned32 (0 | 3..60)
    UNITS       "seconds"
    MAX-ACCESS  read-write
    STATUS      current
    DESCRIPTION
        "The value of sdpBindCtrlChanPwRetryTimer specifies the retry timer
         value to be used for the request timer when control channel for the
         pseudo-wire path is enabled for this SDP binding.

         An 'inconsistentValue' error is returned if the value of
         sdpBindCtrlChanPwRequestTimer is set to non-zero when value of either
         sdpBindCtrlChanPwRetryTimer or sdpBindCtrlChanPwTimeoutMult is also
         set to zero."
    DEFVAL      { 0 }
    ::= { sdpBindCtrlChanPwEntry 6 }

sdpBindCtrlChanPwTimeoutMult     OBJECT-TYPE
    SYNTAX      Unsigned32 (0 | 3..15)
    MAX-ACCESS  read-write
    STATUS      current
    DESCRIPTION
        "The value of sdpBindCtrlChanPwTimeoutMult specifies the timeout
         multiplier value to be used for the retry timer to resend the request
         when control channel for the pseudo-wire path is enabled for this SDP
         binding.

         An 'inconsistentValue' error is returned if the value of
         sdpBindCtrlChanPwRequestTimer is set to non-zero when value of either
         sdpBindCtrlChanPwRetryTimer or sdpBindCtrlChanPwTimeoutMult is also
         set to zero."
    DEFVAL      { 0 }
    ::= { sdpBindCtrlChanPwEntry 7 }

sdpBindCtrlChanPwAck             OBJECT-TYPE
    SYNTAX      TruthValue
    MAX-ACCESS  read-write
    STATUS      current
    DESCRIPTION
        "The value of sdpBindCtrlChanPwAck specifies whether acknowledgement is
         enabled to respond to control channel status messages sent by the peer
         and processed on receipt from peer for this SDP binding."
    REFERENCE
        "http://tools.ietf.org/html/rfc6478#page-7"
    DEFVAL      { false }
    ::= { sdpBindCtrlChanPwEntry 8 }

sdpAutoBindBgpVpwsTable          OBJECT-TYPE
    SYNTAX      SEQUENCE OF SdpAutoBindBgpVpwsEntry
    MAX-ACCESS  not-accessible
    STATUS      current
    DESCRIPTION
        "The sdpAutoBindBgpVpwsTable has an entry for each SDP Bind entry from
         sdpBindTable which was created as a result of BGP VPWS binding."
    ::= { tmnxSdpObjs 54 }

sdpAutoBindBgpVpwsEntry          OBJECT-TYPE
    SYNTAX      SdpAutoBindBgpVpwsEntry
    MAX-ACCESS  not-accessible
    STATUS      current
    DESCRIPTION
        "Each row entry contains BGP-related information for an SDP Bind entry
         created as a result of BGP VPWS binding."
    INDEX       {
        svcId,
        sdpBindId
    }
    ::= { sdpAutoBindBgpVpwsTable 1 }

SdpAutoBindBgpVpwsEntry          ::= SEQUENCE
{ sdpAutoBindBgpVpwsTemplateId     PWTemplateId }

sdpAutoBindBgpVpwsTemplateId     OBJECT-TYPE
    SYNTAX      PWTemplateId
    MAX-ACCESS  read-only
    STATUS      current
    DESCRIPTION
        "The value of sdpAutoBindBgpVpwsTemplateId indicates the the value of
         the pwTemplateId object for the PW template entry used to create this
         SDP Bind."
    ::= { sdpAutoBindBgpVpwsEntry 1 }

sdpBindL2tpv3Table               OBJECT-TYPE
    SYNTAX      SEQUENCE OF SdpBindL2tpv3Entry
    MAX-ACCESS  not-accessible
    STATUS      current
    DESCRIPTION
        "The sdpBindL2tpv3Table has an entry for each SDP Bind entry from
         sdpBindTable when sdpDelivery of the SDP is set to 'l2tpv3'."
    ::= { tmnxSdpObjs 55 }

sdpBindL2tpv3Entry               OBJECT-TYPE
    SYNTAX      SdpBindL2tpv3Entry
    MAX-ACCESS  not-accessible
    STATUS      current
    DESCRIPTION
        "Each row entry contains L2TP v3 information for an SDP Bind entry
         created when sdpDelivery of the SDP is set to 'l2tpv3'."
    INDEX       {
        svcId,
        sdpBindId
    }
    ::= { sdpBindL2tpv3Table 1 }

SdpBindL2tpv3Entry               ::= SEQUENCE
{
    sdpBindL2tpv3IngressCookie       OCTET STRING,
    sdpBindL2tpv3EgressCookie        OCTET STRING,
    sdpBindL2tpv3SessMismatch        TruthValue,
    sdpBindL2tpv3SessMismatchLstClrd TimeStamp,
    sdpBindL2tpv3IngressCookie2      OCTET STRING
}

sdpBindL2tpv3IngressCookie       OBJECT-TYPE
    SYNTAX      OCTET STRING (SIZE (8))
    MAX-ACCESS  read-write
    STATUS      current
    DESCRIPTION
        "The value of sdpBindL2tpv3IngressCookie specifies the value of cookie
         to match on the L2TP-V3 tunnel on the ingress side of this sdp-bind."
    DEFVAL      { '0000000000000000'H }
    ::= { sdpBindL2tpv3Entry 1 }

sdpBindL2tpv3EgressCookie        OBJECT-TYPE
    SYNTAX      OCTET STRING (SIZE (8))
    MAX-ACCESS  read-write
    STATUS      current
    DESCRIPTION
        "The value of sdpBindL2tpv3EgressCookie specifies the value of L2TP-V3
         tunnel cookie that will be sent on the egress side of this sdp-bind."
    DEFVAL      { '0000000000000000'H }
    ::= { sdpBindL2tpv3Entry 2 }

sdpBindL2tpv3SessMismatch        OBJECT-TYPE
    SYNTAX      TruthValue
    MAX-ACCESS  read-only
    STATUS      current
    DESCRIPTION
        "The value of sdpBindL2tpv3SessMismatch indicates whether
         a session mismatch occurred on the L2TP-V3 tunnel on this sdp-bind
         because of one or more of the following reasons (since last time this
         was cleared):
         - sdpBindL2tpv3IngressCookie mismatch,
         - sdpLocalEndInetAddress mismatch,
         - sdpFarEndInetAddress mismatch,
         - invalid session identifier."
    ::= { sdpBindL2tpv3Entry 3 }

sdpBindL2tpv3SessMismatchLstClrd OBJECT-TYPE
    SYNTAX      TimeStamp
    MAX-ACCESS  read-only
    STATUS      current
    DESCRIPTION
        "The value of sdpBindL2tpv3SessMismatchLstClrd indicates the time when
         session mismatch on the L2TP-V3 tunnel on this sdp-bind was last
         cleared."
    ::= { sdpBindL2tpv3Entry 4 }

sdpBindL2tpv3IngressCookie2      OBJECT-TYPE
    SYNTAX      OCTET STRING (SIZE (8))
    MAX-ACCESS  read-write
    STATUS      current
    DESCRIPTION
        "The value of sdpBindL2tpv3IngressCookie2 specifies the value of second
         cookie to match on the L2TP-V3 tunnel on the ingress side of this
         sdp-bind."
    DEFVAL      { '0000000000000000'H }
    ::= { sdpBindL2tpv3Entry 5 }

sdpBindTlsStaticIsidRngTable     OBJECT-TYPE
    SYNTAX      SEQUENCE OF SdpBindTlsStaticIsidRngEntry
    MAX-ACCESS  not-accessible
    STATUS      current
    DESCRIPTION
        "This table maintains the ISID range information for SDP BINDs."
    ::= { tmnxSdpObjs 56 }

sdpBindTlsStaticIsidRngEntry     OBJECT-TYPE
    SYNTAX      SdpBindTlsStaticIsidRngEntry
    MAX-ACCESS  not-accessible
    STATUS      current
    DESCRIPTION
        "This entry maintains the static range information for a specific
         SDP-BIND in a specific VPLS service."
    INDEX       {
        svcId,
        sdpBindId,
        sdpBindTlsStaticIsidRngId
    }
    ::= { sdpBindTlsStaticIsidRngTable 1 }

SdpBindTlsStaticIsidRngEntry     ::= SEQUENCE
{
    sdpBindTlsStaticIsidRngId        Unsigned32,
    sdpBindTlsStaticIsidRngRowStatus RowStatus,
    sdpBindTlsStaticIsidRngLastChgd  TimeStamp,
    sdpBindTlsStaticIsidRngLow       TmnxISID,
    sdpBindTlsStaticIsidRngHigh      TmnxISID
}

sdpBindTlsStaticIsidRngId        OBJECT-TYPE
    SYNTAX      Unsigned32 (1..8191)
    MAX-ACCESS  not-accessible
    STATUS      current
    DESCRIPTION
        "The value of sdpBindTlsStaticIsidRngId specifies the range identifier
         for the ISID policy."
    ::= { sdpBindTlsStaticIsidRngEntry 1 }

sdpBindTlsStaticIsidRngRowStatus OBJECT-TYPE
    SYNTAX      RowStatus
    MAX-ACCESS  read-create
    STATUS      current
    DESCRIPTION
        "The value of sdpBindTlsStaticIsidRngRowStatus is used for the creation
         and deletion of rows in this table."
    ::= { sdpBindTlsStaticIsidRngEntry 2 }

sdpBindTlsStaticIsidRngLastChgd  OBJECT-TYPE
    SYNTAX      TimeStamp
    MAX-ACCESS  read-only
    STATUS      current
    DESCRIPTION
        "The value of sdpBindTlsStaticIsidRngLastChgd indicates the timestamp
         of last change to this row in sdpBindTlsStaticIsidRngTable."
    ::= { sdpBindTlsStaticIsidRngEntry 3 }

sdpBindTlsStaticIsidRngLow       OBJECT-TYPE
    SYNTAX      TmnxISID
    MAX-ACCESS  read-create
    STATUS      current
    DESCRIPTION
        "The value of sdpBindTlsStaticIsidRngLow specifies the low value of the
         range for this entry."
    DEFVAL      { 0 }
    ::= { sdpBindTlsStaticIsidRngEntry 4 }

sdpBindTlsStaticIsidRngHigh      OBJECT-TYPE
    SYNTAX      TmnxISID
    MAX-ACCESS  read-create
    STATUS      current
    DESCRIPTION
        "The value of sdpBindTlsStaticIsidRngHigh specifies the high value of
         the range for this entry."
    DEFVAL      { 0 }
    ::= { sdpBindTlsStaticIsidRngEntry 5 }

sdpBindDhcp6InfoTable            OBJECT-TYPE
    SYNTAX      SEQUENCE OF SdpBindDhcp6InfoEntry
    MAX-ACCESS  not-accessible
    STATUS      current
    DESCRIPTION
        "A table that contains DHCP6 information related to a SDP Bind.

         A row will exist in this table for each spoke SDP in a TLS Service.
         Rows are created and deleted automatically by the system."
    ::= { tmnxSdpObjs 57 }

sdpBindDhcp6InfoEntry            OBJECT-TYPE
    SYNTAX      SdpBindDhcp6InfoEntry
    MAX-ACCESS  not-accessible
    STATUS      current
    DESCRIPTION
        "DHCP6 specific information about an SDP Bind."
    AUGMENTS    { sdpBindDhcpInfoEntry }
    ::= { sdpBindDhcp6InfoTable 1 }

SdpBindDhcp6InfoEntry            ::= SEQUENCE
{
    sdpBindDhcp6Description          ServObjDesc,
    sdpBindDhcp6Snoop                TmnxEnabledDisabled
}

sdpBindDhcp6Description          OBJECT-TYPE
    SYNTAX      ServObjDesc
    MAX-ACCESS  read-write
    STATUS      current
    DESCRIPTION
        "The value of the object sdpBindDhcp6Description specifies a user
         provided description for DHCP6 on this Sdp Bind."
    DEFVAL      { ''H }
    ::= { sdpBindDhcp6InfoEntry 1 }

sdpBindDhcp6Snoop                OBJECT-TYPE
    SYNTAX      TmnxEnabledDisabled
    MAX-ACCESS  read-write
    STATUS      current
    DESCRIPTION
        "The value of the object sdpBindDhcp6Snoop specifies whether or not
         DHCP6 snooping is enabled on the Sdp Bind."
    DEFVAL      { disabled }
    ::= { sdpBindDhcp6InfoEntry 2 }

sdpBindTlsStaticIsidTable        OBJECT-TYPE
    SYNTAX      SEQUENCE OF SdpBindTlsStaticIsidEntry
    MAX-ACCESS  not-accessible
    STATUS      current
    DESCRIPTION
        "This table maintains the information for each static ISID for
         SDP-BINDs."
    ::= { tmnxSdpObjs 58 }

sdpBindTlsStaticIsidEntry        OBJECT-TYPE
    SYNTAX      SdpBindTlsStaticIsidEntry
    MAX-ACCESS  not-accessible
    STATUS      current
    DESCRIPTION
        "This entry maintains the information for a specific ISID associated
         with the specific SDP-BIND in a specific VPLS service.

         Entries are created and deleted by the system."
    INDEX       {
        svcId,
        sdpBindId,
        sdpBindTlsStaticIsid
    }
    ::= { sdpBindTlsStaticIsidTable 1 }

SdpBindTlsStaticIsidEntry        ::= SEQUENCE
{
    sdpBindTlsStaticIsid             TmnxISID,
    sdpBindTlsStaticIsidStatus       TmnxIsidMFibStatus
}

sdpBindTlsStaticIsid             OBJECT-TYPE
    SYNTAX      TmnxISID
    MAX-ACCESS  not-accessible
    STATUS      current
    DESCRIPTION
        "The value of sdpBindTlsStaticIsid indicates ISID of this entry."
    ::= { sdpBindTlsStaticIsidEntry 1 }

sdpBindTlsStaticIsidStatus       OBJECT-TYPE
    SYNTAX      TmnxIsidMFibStatus
    MAX-ACCESS  read-only
    STATUS      current
    DESCRIPTION
        "The value of sdpBindTlsStaticIsidStatus indicates the MFIB status of
         this ISID."
    ::= { sdpBindTlsStaticIsidEntry 2 }

sdpBindEthLoopbackTable          OBJECT-TYPE
    SYNTAX      SEQUENCE OF SdpBindEthLoopbackEntry
    MAX-ACCESS  not-accessible
    STATUS      current
    DESCRIPTION
        "The table sdpBindEthLoopbackTable provides operators with the ability
         to provide loopback functions on a specific SDP binding in order to
         test Ethernet Virtual Circuits (EVC)."
    ::= { tmnxSdpObjs 59 }

sdpBindEthLoopbackEntry          OBJECT-TYPE
    SYNTAX      SdpBindEthLoopbackEntry
    MAX-ACCESS  not-accessible
    STATUS      current
    DESCRIPTION
        "Each entry represents an active SDP binding loopback. The SDP binding
         is placed in loopback by row creation and is removed by row
         destruction.

         Rows in table sdpBindEthLoopbackTable are created and destroyed by
         SNMP set operations on the object sdpBindEthLoopbackRowStatus. Rows in
         table sdpBindEthLoopbackTable may be destroyed by the system when the
         associated SDP binding has been deleted. A maximum of 64 rows may be
         created. Rows are kept in volatile storage and lost upon a system
         reboot."
    INDEX       {
        svcId,
        sdpBindId
    }
    ::= { sdpBindEthLoopbackTable 1 }

SdpBindEthLoopbackEntry          ::= SEQUENCE
{
    sdpBindEthLoopbackRowStatus      RowStatus,
    sdpBindEthLoopbackMode           INTEGER,
    sdpBindEthLoopbackMacSwap        TmnxEnabledDisabled,
    sdpBindEthLoopbackMacSwapAddr    MacAddress,
    sdpBindEthLoopbackMacSwapAddrAll TruthValue
}

sdpBindEthLoopbackRowStatus      OBJECT-TYPE
    SYNTAX      RowStatus
    MAX-ACCESS  read-create
    STATUS      current
    DESCRIPTION
        "The value of the object sdpBindEthLoopbackRowStatus specifies the row
         status. It allows entries to be created and deleted in
         sdpBindEthLoopbackTable.

         Rows are created by specifying the value 'createAndGo(4)' and deleted
         by specifying the value 'destroy(6)'. If the associated SDP is
         deleted, the sdpBindEthLoopbackEntry row will be deleted by the
         system.

         Row creation will fail if the service identifier and the SDP binding
         do not exist in MIB table sdpBindTable with a
         TIMETRA-SERV-MIB::svcType of 'epipe(1)' or 'tls(3)', which encompasses
         EPIPE, PBB (Provider Backbone Bridging) EPIPE, VPLS (Virtual Private
         LAN Service), and I-VPLS services."
    ::= { sdpBindEthLoopbackEntry 1 }

sdpBindEthLoopbackMode           OBJECT-TYPE
    SYNTAX      INTEGER {
        ingress (1),
        egress  (2)
    }
    MAX-ACCESS  read-create
    STATUS      current
    DESCRIPTION
        "The value of the object sdpBindEthLoopbackMode specifies how traffic
         will be reflected.

         If the value is set to 'ingress(1)', traffic arriving at the SDP
         binding ingress will be reflected back out the same SDP binding. If
         the value is set to 'egress(2)', traffic arriving at the SDP binding
         egress will be reflected back into the service in the direction of the
         original source."
    ::= { sdpBindEthLoopbackEntry 2 }

sdpBindEthLoopbackMacSwap        OBJECT-TYPE
    SYNTAX      TmnxEnabledDisabled
    MAX-ACCESS  read-create
    STATUS      current
    DESCRIPTION
        "The value of the object sdpBindEthLoopbackMacSwap specifies the
         enabling or disabling of source address and destination address
         swapping for the reflected packets when the arriving packet is
         unicast. With sdpBindEthLoopbackMacSwap enabled, any broadcast or
         multicast packets arriving on a looped point will be dropped."
    DEFVAL      { disabled }
    ::= { sdpBindEthLoopbackEntry 3 }

sdpBindEthLoopbackMacSwapAddr    OBJECT-TYPE
    SYNTAX      MacAddress
    MAX-ACCESS  read-create
    STATUS      current
    DESCRIPTION
        "The value of the object sdpBindEthLoopbackMacSwapAddr specifies the
         source MAC address used in the reflected packet when the arriving
         packet is broadcast or multicast. This does not apply to arriving
         unicast packets."
    DEFVAL      { '000000000000'H }
    ::= { sdpBindEthLoopbackEntry 4 }

sdpBindEthLoopbackMacSwapAddrAll OBJECT-TYPE
    SYNTAX      TruthValue
    MAX-ACCESS  read-create
    STATUS      current
    DESCRIPTION
        "The value of the object sdpBindEthLoopbackMacSwapAddrAll specifies
         whether or not to use the configured sdpBindEthLoopbackMacSwapAddr as
         the source address for all reflected parameters."
    DEFVAL      { false }
    ::= { sdpBindEthLoopbackEntry 5 }

sdpBindTlsFdbMacStatsTable       OBJECT-TYPE
    SYNTAX      SEQUENCE OF SdpBindTlsFdbMacStatsEntry
    MAX-ACCESS  not-accessible
    STATUS      current
    DESCRIPTION
        "This table maintains the count of MAC address entries per FDB type for
         the SDPs in VPLS services."
    ::= { tmnxSdpObjs 60 }

sdpBindTlsFdbMacStatsEntry       OBJECT-TYPE
    SYNTAX      SdpBindTlsFdbMacStatsEntry
    MAX-ACCESS  not-accessible
    STATUS      current
    DESCRIPTION
        "This entry maintains the count of MAC address entries per FDB type for
         the SDP in a VPLS service."
    INDEX       {
        svcId,
        sdpBindId,
        tlsFdbType
    }
    ::= { sdpBindTlsFdbMacStatsTable 1 }

SdpBindTlsFdbMacStatsEntry       ::= SEQUENCE
{ sdpBindTlsFdbMacStatsNumEntries  Unsigned32 }

sdpBindTlsFdbMacStatsNumEntries  OBJECT-TYPE
    SYNTAX      Unsigned32
    MAX-ACCESS  read-only
    STATUS      current
    DESCRIPTION
        "The value of sdpBindTlsFdbMacStatsNumEntries indicates the number of
         MAC address entries of the FDB type in the SDP in this service."
    ::= { sdpBindTlsFdbMacStatsEntry 1 }

sdpBindPwLoopbackTable           OBJECT-TYPE
    SYNTAX      SEQUENCE OF SdpBindPwLoopbackEntry
    MAX-ACCESS  not-accessible
    STATUS      current
    DESCRIPTION
        "The table sdpBindPwLoopbackTable provides operators with the ability
         to provide loopback functions on a specific SDP binding in order to
         test pseudo-wire Virtual Circuits (EVC)."
    ::= { tmnxSdpObjs 61 }

sdpBindPwLoopbackEntry           OBJECT-TYPE
    SYNTAX      SdpBindPwLoopbackEntry
    MAX-ACCESS  not-accessible
    STATUS      current
    DESCRIPTION
        "Each entry represents an active SDP binding loopback. The SDP binding
         is placed in loopback by row creation and is removed by row
         destruction.

         Rows in table sdpBindPwLoopbackTable are created and destroyed by SNMP
         set operations on the object sdpBindPwLoopbackRowStatus. Rows in table
         sdpBindPwLoopbackTable may be destroyed by the system when the
         associated SDP binding has been deleted. A maximum of 64 rows may be
         created. Rows are kept in volatile storage and lost upon a system
         reboot."
    INDEX       {
        svcId,
        sdpBindId
    }
    ::= { sdpBindPwLoopbackTable 1 }

SdpBindPwLoopbackEntry           ::= SEQUENCE
{ sdpBindPwLoopbackRowStatus       RowStatus }

sdpBindPwLoopbackRowStatus       OBJECT-TYPE
    SYNTAX      RowStatus
    MAX-ACCESS  read-create
    STATUS      current
    DESCRIPTION
        "The value of the object sdpBindPwLoopbackRowStatus specifies the row
         status. It allows entries to be created and deleted in
         sdpBindPwLoopbackTable.

         Rows are created by specifying the value 'createAndGo(4)' and deleted
         by specifying the value 'destroy(6)'. If the associated SDP is
         deleted, the sdpBindPwLoopbackEntry row will be deleted by the system.

         Row creation will fail if the service identifier and the SDP binding
         do not exist in MIB table sdpBindTable with a
         TIMETRA-SERV-MIB::svcType of 'apipe', 'cpipe', 'epipe' or 'tls'."
    ::= { sdpBindPwLoopbackEntry 1 }

sdpBindPwAdminLockTable          OBJECT-TYPE
    SYNTAX      SEQUENCE OF SdpBindPwAdminLockEntry
    MAX-ACCESS  not-accessible
    STATUS      current
    DESCRIPTION
        "The table sdpBindPwAdminLockTable provides operators with the ability
         to provide administrative lock functions on a specific SDP binding in
         order to test pseudo-wire Virtual Circuits."
    ::= { tmnxSdpObjs 62 }

sdpBindPwAdminLockEntry          OBJECT-TYPE
    SYNTAX      SdpBindPwAdminLockEntry
    MAX-ACCESS  not-accessible
    STATUS      current
    DESCRIPTION
        "Each entry represents an active SDP binding adminstrative lock
         operation. The SDP binding is placed in adminstrative lock by row
         creation and is removed by row destruction.

         Rows in table sdpBindPwAdminLockTable are created and destroyed by
         SNMP set operations on the object sdpBindPwAdminLockRowStatus. Rows in
         table sdpBindPwAdminLockTable may be destroyed by the system when the
         associated SDP binding has been deleted. A maximum of 64 rows may be
         created. Rows are kept in volatile storage and lost upon a system
         reboot."
    INDEX       {
        svcId,
        sdpBindId
    }
    ::= { sdpBindPwAdminLockTable 1 }

SdpBindPwAdminLockEntry          ::= SEQUENCE
{
    sdpBindPwAdminLockRowStatus      RowStatus,
    sdpBindPwAdminLockTestSvc        TmnxServId
}

sdpBindPwAdminLockRowStatus      OBJECT-TYPE
    SYNTAX      RowStatus
    MAX-ACCESS  read-create
    STATUS      current
    DESCRIPTION
        "The value of the object sdpBindPwAdminLockRowStatus specifies the row
         status. It allows entries to be created and deleted in
         sdpBindPwAdminLockTable.

         Rows are created by specifying the value 'createAndGo(4)' and deleted
         by specifying the value 'destroy(6)'. If the associated SDP is
         deleted, the sdpBindPwAdminLockEntry row will be deleted by the
         system.

         Row creation will fail if the service identifier and the SDP binding
         do not exist in MIB table sdpBindTable with a
         TIMETRA-SERV-MIB::svcType of 'apipe', 'cpipe', 'epipe' or 'tls'."
    ::= { sdpBindPwAdminLockEntry 1 }

sdpBindPwAdminLockTestSvc        OBJECT-TYPE
    SYNTAX      TmnxServId
    MAX-ACCESS  read-create
    STATUS      current
    DESCRIPTION
        "The value of the sdpBindPwAdminLockTestSvc specifies the test service
         identifier associated with this administrative lock operation.

         An 'inconsistentValue' error is returned if this object is set to a
         different value at any time after the row is already created."
    DEFVAL      { 0 }
    ::= { sdpBindPwAdminLockEntry 2 }

pwTemplateAugTableLastChgd       OBJECT-TYPE
    SYNTAX      TimeStamp
    MAX-ACCESS  read-only
    STATUS      current
    DESCRIPTION
        "The value of pwTemplateAugTableLastChgd indicates the sysUpTime at the
         time of the last modification of pwTemplateAugTable.

         If no changes were made to the entry since the last re-initialization
         of the local network management subsystem, then this object contains a
         zero value."
    ::= { tmnxSdpObjs 63 }

pwTemplateAugTable               OBJECT-TYPE
    SYNTAX      SEQUENCE OF PwTemplateAugEntry
    MAX-ACCESS  not-accessible
    STATUS      current
    DESCRIPTION
        "A table that contains entries for pseudowire (PW) templates specifying
         additional SDP auto-binding information."
    ::= { tmnxSdpObjs 64 }

pwTemplateAugEntry               OBJECT-TYPE
    SYNTAX      PwTemplateAugEntry
    MAX-ACCESS  not-accessible
    STATUS      current
    DESCRIPTION
        "This pwTemplateAugEntry contains additional information about a
         specific PW template."
    AUGMENTS    { pwTemplateEntry }
    ::= { pwTemplateAugTable 1 }

PwTemplateAugEntry               ::= SEQUENCE
{
    pwTemplateAugLastChgd            TimeStamp,
    pwTemplateAugStpAutoEdge         TmnxEnabledDisabled,
    pwTemplateAugStpRapidStart       TmnxEnabledDisabled,
    pwTemplateAugStpAdminPtToPt      INTEGER,
    pwTemplateAugStpPathCost         Integer32,
    pwTemplateAugStpPriority         Integer32,
    pwTemplateAugStpRootGuard        TruthValue,
    pwTemplateAugStpAdminStatus      TmnxEnabledDisabledAdminState,
    pwTemplateAugL2ptTermination     TmnxEnabledDisabled,
    pwTemplateAugL2ptProtocols       L2ptProtocols,
    pwTemplateAugGreAllowFrag        TruthValue,
    pwTemplateAugAluNgeKeyGroupIn    AluNgeKeygroupIdOrZero,
    pwTemplateAugAluNgeKeyGroupOut   AluNgeKeygroupIdOrZero
}

pwTemplateAugLastChgd            OBJECT-TYPE
    SYNTAX      TimeStamp
    MAX-ACCESS  read-only
    STATUS      current
    DESCRIPTION
        "The value of pwTemplateAugLastChgd indicates the timestamp of last
         change to this row in pwTemplateAugTable."
    ::= { pwTemplateAugEntry 1 }

pwTemplateAugStpAutoEdge         OBJECT-TYPE
    SYNTAX      TmnxEnabledDisabled
    MAX-ACCESS  read-write
    STATUS      current
    DESCRIPTION
        "The value of the pwTemplateAugStpAutoEdge specifies whether this
         pseudo-wire template is enabled for auto-edge detection as defined by
         Rapid Spanning Tree Protocol."
    DEFVAL      { enabled }
    ::= { pwTemplateAugEntry 2 }

pwTemplateAugStpRapidStart       OBJECT-TYPE
    SYNTAX      TmnxEnabledDisabled
    MAX-ACCESS  read-write
    STATUS      current
    DESCRIPTION
        "The value of the pwTemplateAugStpRapidStart specifies whether Rapid
         Start is enabled on this pseudo-wire template.

         When the value is 'enabled' the Spanning Tree Protocol state
         transitions on this pseudo-wire template are driven by the value of
         the 'HelloTime', instead of the value of 'ForwardDelay', thus allowing
         a faster transition into the forwarding state."
    DEFVAL      { disabled }
    ::= { pwTemplateAugEntry 3 }

pwTemplateAugStpAdminPtToPt      OBJECT-TYPE
    SYNTAX      INTEGER {
        forceTrue  (0),
        forceFalse (1)
    }
    MAX-ACCESS  read-write
    STATUS      current
    DESCRIPTION
        "The value of the pwTemplateAugStpAdminPtToPt specifies the
         administrative point-to-point status of the LAN segment attached to
         this sdp.

         A value of 'forceTrue' indicates that this port should always be
         treated as if it is connected to a point-to-point link.

         A value of 'forceFalse' indicates that this port should be treated as
         having a shared media connection."
    REFERENCE
        "IEEE 802.1w clause 6.4.3, 6.5, 14.8.2"
    DEFVAL      { forceTrue }
    ::= { pwTemplateAugEntry 4 }

pwTemplateAugStpPathCost         OBJECT-TYPE
    SYNTAX      Integer32 (1..200000000)
    MAX-ACCESS  read-write
    STATUS      current
    DESCRIPTION
        "The value of the pwTemplateAugStpPathCost specifies the contribution
         of this pseudo-wire template to the path cost of paths towards the
            spanning tree root which include this pseudo-wire template."
    DEFVAL      { 10 }
    ::= { pwTemplateAugEntry 5 }

pwTemplateAugStpPriority         OBJECT-TYPE
    SYNTAX      Integer32 (0..255)
    MAX-ACCESS  read-write
    STATUS      current
    DESCRIPTION
        "The value of the object pwTemplateAugStpPriority specifies the value
         of the port priority field which is contained in the most significant
         4 bits of the 16-bit Port ID associated with this pseudo-wire template
         . As only the most significant 4 bits of the value are used, the
         actual value of this object is limited to multiples of 16: e.g. the
         agent rounds down the value to one of: 0, 16, 32, .. , 224, 240."
    DEFVAL      { 128 }
    ::= { pwTemplateAugEntry 6 }

pwTemplateAugStpRootGuard        OBJECT-TYPE
    SYNTAX      TruthValue
    MAX-ACCESS  read-write
    STATUS      current
    DESCRIPTION
        "The value of the object pwTemplateAugStpRootGuard specifies whether
         this port is allowed to become STP root port. It corresponds to the
         parameter 'restrictedRole' in 802.1Q. If set, it can cause lack of
         spanning tree connectivity."
    DEFVAL      { false }
    ::= { pwTemplateAugEntry 7 }

pwTemplateAugStpAdminStatus      OBJECT-TYPE
    SYNTAX      TmnxEnabledDisabledAdminState
    MAX-ACCESS  read-write
    STATUS      current
    DESCRIPTION
        "The value of the object pwTemplateAugStpAdminStatus specifies whether
         this pseudo-wire template participates in the Spanning Tree Protocol."
    DEFVAL      { enabled }
    ::= { pwTemplateAugEntry 8 }

pwTemplateAugL2ptTermination     OBJECT-TYPE
    SYNTAX      TmnxEnabledDisabled
    MAX-ACCESS  read-write
    STATUS      current
    DESCRIPTION
        "The value of the pwTemplateAugL2ptTermination specifies whether
         received L2 Protocol Tunnel packets are terminated on this pseudo-wire
         template."
    DEFVAL      { disabled }
    ::= { pwTemplateAugEntry 9 }

pwTemplateAugL2ptProtocols       OBJECT-TYPE
    SYNTAX      L2ptProtocols
    MAX-ACCESS  read-write
    STATUS      current
    DESCRIPTION
        "The value of the pwTemplateAugL2ptProtocols specifies which L2
         Protocol Tunnel PDUs are terminated on this pseudo-wire template."
    DEFVAL      { {} }
    ::= { pwTemplateAugEntry 10 }

pwTemplateAugGreAllowFrag        OBJECT-TYPE
    SYNTAX      TruthValue
    MAX-ACCESS  read-write
    STATUS      current
    DESCRIPTION
        "The value of pwTemplateAugGreAllowFrag specifies whether to allow GRE
         encapsulated packets to be sent without setting the DF bit.

         This object is valid only when pwTemplateGreDelivery is set to 'true'."
    DEFVAL      { false }
    ::= { pwTemplateAugEntry 11 }

pwTemplateAugAluNgeKeyGroupIn    OBJECT-TYPE
    SYNTAX      AluNgeKeygroupIdOrZero
    MAX-ACCESS  read-write
    STATUS      current
    DESCRIPTION
        "The pwTemplateAugAluNgeKeyGroupIn specifies keygroup identifier for
         the inbound direction."
    DEFVAL      { 0 }
    ::= { pwTemplateAugEntry 12 }

pwTemplateAugAluNgeKeyGroupOut   OBJECT-TYPE
    SYNTAX      AluNgeKeygroupIdOrZero
    MAX-ACCESS  read-write
    STATUS      current
    DESCRIPTION
        "The pwTemplateAugAluNgeKeyGroupOut specifies keygroup identifier for
         the outbound direction."
    DEFVAL      { 0 }
    ::= { pwTemplateAugEntry 13 }

sdpSegRouteTableLastChgd         OBJECT-TYPE
    SYNTAX      TimeStamp
    MAX-ACCESS  read-only
    STATUS      current
    DESCRIPTION
        "The value of sdpSegRouteTableLastChgd indicates the sysUpTime at the
         time of the last modification of sdpSegRouteTable.

         If no changes were made to the entry since the last re-initialization
         of the local network management subsystem, then this object contains a
         zero value."
    ::= { tmnxSdpObjs 65 }

sdpSegRouteTable                 OBJECT-TYPE
    SYNTAX      SEQUENCE OF SdpSegRouteEntry
    MAX-ACCESS  not-accessible
    STATUS      current
    DESCRIPTION
        "A table that contains SDP segment routing information."
    ::= { tmnxSdpObjs 66 }

sdpSegRouteEntry                 OBJECT-TYPE
    SYNTAX      SdpSegRouteEntry
    MAX-ACCESS  not-accessible
    STATUS      current
    DESCRIPTION
        "Information about a specific SDP segment routing."
    INDEX       { sdpId }
    ::= { sdpSegRouteTable 1 }

SdpSegRouteEntry                 ::= SEQUENCE
{
    sdpSegRouteIsIs                  TmnxEnabledDisabled,
    sdpSegRouteIsIsOperInstId        Integer32,
    sdpSegRouteIsIsLspId             Unsigned32,
    sdpSegRouteOspf                  TmnxEnabledDisabled,
    sdpSegRouteOspfOperInstId        Integer32,
    sdpSegRouteOspfLspId             Unsigned32,
    sdpSegRouteTeOperInstId          Integer32
}

sdpSegRouteIsIs                  OBJECT-TYPE
    SYNTAX      TmnxEnabledDisabled
    MAX-ACCESS  read-write
    STATUS      current
    DESCRIPTION
        "The value of the sdpSegRouteIsIs specifies whether Segment Routing is
         enabled for IS-IS on this SDP."
    DEFVAL      { disabled }
    ::= { sdpSegRouteEntry 1 }

sdpSegRouteIsIsOperInstId        OBJECT-TYPE
    SYNTAX      Integer32
    MAX-ACCESS  read-only
    STATUS      current
    DESCRIPTION
        "The value of the sdpSegRouteIsIsOperInstId indicates the IS-IS
         instance identifier in use for this SDP.

         Value of '-1' indicates no valid value for the instance identifier."
    ::= { sdpSegRouteEntry 3 }

sdpSegRouteIsIsLspId             OBJECT-TYPE
    SYNTAX      Unsigned32
    MAX-ACCESS  read-only
    STATUS      current
    DESCRIPTION
        "The value of sdpSegRouteIsIsLspId indicates the Id for the segment
         routed IS-IS LSP if sdpSegRouteIsIs is set to 'enabled' and there is a
         valid route to the sdpFarEndIpAddress."
    ::= { sdpSegRouteEntry 4 }

sdpSegRouteOspf                  OBJECT-TYPE
    SYNTAX      TmnxEnabledDisabled
    MAX-ACCESS  read-write
    STATUS      current
    DESCRIPTION
        "The value of the sdpSegRouteOspf specifies whether Segment Routing is
         enabled for OSPF on this SDP."
    DEFVAL      { disabled }
    ::= { sdpSegRouteEntry 10 }

sdpSegRouteOspfOperInstId        OBJECT-TYPE
    SYNTAX      Integer32
    MAX-ACCESS  read-only
    STATUS      current
    DESCRIPTION
        "The value of the sdpSegRouteOspfOperInstId indicates the OSPF instance
         identifier in use for this SDP.

         Value of '-1' indicates no valid value for the instance identifier."
    ::= { sdpSegRouteEntry 12 }

sdpSegRouteOspfLspId             OBJECT-TYPE
    SYNTAX      Unsigned32
    MAX-ACCESS  read-only
    STATUS      current
    DESCRIPTION
        "The value of sdpSegRouteOspfLspId indicates the Id for the segment
         routed OSPF LSP if sdpSegRouteOspf is set to 'enabled' and there is a
         valid route to the sdpFarEndIpAddress."
    ::= { sdpSegRouteEntry 13 }

sdpSegRouteTeOperInstId          OBJECT-TYPE
    SYNTAX      Integer32
    MAX-ACCESS  read-only
    STATUS      current
    DESCRIPTION
        "The value of the sdpSegRouteTeOperInstId indicates the traffic
         engineering (TE) instance identifier in use for this SDP.

         Value of '-1' indicates no valid value for the instance identifier."
    ::= { sdpSegRouteEntry 14 }

sdpEvpnMHEthSegTable             OBJECT-TYPE
    SYNTAX      SEQUENCE OF SdpEvpnMHEthSegEntry
    MAX-ACCESS  not-accessible
    STATUS      current
    DESCRIPTION
        "The sdpEvpnMHEthSegTable contains entries for ethernet segment
         information associated with a SDP binding."
    ::= { tmnxSdpObjs 67 }

sdpEvpnMHEthSegEntry             OBJECT-TYPE
    SYNTAX      SdpEvpnMHEthSegEntry
    MAX-ACCESS  not-accessible
    STATUS      current
    DESCRIPTION
        "An ethernet segment entry in the sdpEvpnMHEthSegTable."
    INDEX       {
        svcId,
        sdpBindId
    }
    ::= { sdpEvpnMHEthSegTable 1 }

SdpEvpnMHEthSegEntry             ::= SEQUENCE
{
    sdpEvpnMHEthSegName              TNamedItemOrEmpty,
    sdpEvpnMHEthSegStatus            TmnxEvpnMHEthSegStatus
}

sdpEvpnMHEthSegName              OBJECT-TYPE
    SYNTAX      TNamedItemOrEmpty
    MAX-ACCESS  read-only
    STATUS      current
    DESCRIPTION
        "The value of sdpEvpnMHEthSegName indicates the ethernet segment name
         associated with the given SDP binding."
    ::= { sdpEvpnMHEthSegEntry 1 }

sdpEvpnMHEthSegStatus            OBJECT-TYPE
    SYNTAX      TmnxEvpnMHEthSegStatus
    MAX-ACCESS  read-only
    STATUS      current
    DESCRIPTION
        "The value of sdpEvpnMHEthSegStatus indicates the status of the
         ethernet segment associated with the given SDP binding."
    ::= { sdpEvpnMHEthSegEntry 2 }

sdpBindExtTableLastChanged       OBJECT-TYPE
    SYNTAX      TimeStamp
    MAX-ACCESS  read-only
    STATUS      current
    DESCRIPTION
        "The value of sdpBindExtTableLastChanged indicates the sysUpTime at the
         time of the last modification of sdpBindExtTable.

         If no changes were made to the entry since the last re-initialization
         of the local network management subsystem, then this object contains a
         zero value."
    ::= { tmnxSdpObjs 68 }

sdpBindExtTable                  OBJECT-TYPE
    SYNTAX      SEQUENCE OF SdpBindExtEntry
    MAX-ACCESS  not-accessible
    STATUS      current
    DESCRIPTION
        "A table that extends sdpBindTable."
    ::= { tmnxSdpObjs 69 }

sdpBindExtEntry                  OBJECT-TYPE
    SYNTAX      SdpBindExtEntry
    MAX-ACCESS  not-accessible
    STATUS      current
    DESCRIPTION
        "sdpBindExtEntry extends sdpBindEntry."
    AUGMENTS    { sdpBindEntry }
    ::= { sdpBindExtTable 1 }

SdpBindExtEntry                  ::= SEQUENCE
{
    sdpBindExtEntropyLabel           TruthValue,
    sdpBindExtLastMgmtChange         TimeStamp
}

sdpBindExtEntropyLabel           OBJECT-TYPE
    SYNTAX      TruthValue
    MAX-ACCESS  read-create
    STATUS      current
    DESCRIPTION
        "The value of sdpBindExtEntropyLabel specifies whether the use of
         entropy label is enabled or not on this SDP Bind."
    DEFVAL      { false }
    ::= { sdpBindExtEntry 1 }

sdpBindExtLastMgmtChange         OBJECT-TYPE
    SYNTAX      TimeStamp
    MAX-ACCESS  read-only
    STATUS      current
    DESCRIPTION
        "The value of sysUpTime at the time of the most recent
         management-initiated change to this Service-SDP binding."
    ::= { sdpBindExtEntry 2 }

sdpSegRouteTeLspTableLastChgd    OBJECT-TYPE
    SYNTAX      TimeStamp
    MAX-ACCESS  read-only
    STATUS      current
    DESCRIPTION
        "The value of sdpSegRouteTeLspTableLastChgd indicates the sysUpTime at
         the time of the last modification of sdpSegRouteTeLspTable.

         If no changes were made to the entry since the last re-initialization
         of the local network management subsystem, then this object contains a
         zero value."
    ::= { tmnxSdpObjs 70 }

sdpSegRouteTeLspTable            OBJECT-TYPE
    SYNTAX      SEQUENCE OF SdpSegRouteTeLspEntry
    MAX-ACCESS  not-accessible
    STATUS      current
    DESCRIPTION
        "A table that contains SDP segment routing traffic engineering (SR-TE)
         LSPs used to reach the far-end ESR device.

         All the LSPs in this list must terminate at the IP address specified
         by sdpFarEndIpAddress or sdpFarEndNodeId (for sdpDelivery of 'mpls').
         This object is otherwise insignificant and should contain a value of
         0.

         When this list has more than one element, the Nokia SROS router will
         use ALL of the LSPs for load balancing purposes. Each LSP ID in the
         list corresponds to the vRtrMplsLspIndex of the given MPLS LSP."
    ::= { tmnxSdpObjs 71 }

sdpSegRouteTeLspEntry            OBJECT-TYPE
    SYNTAX      SdpSegRouteTeLspEntry
    MAX-ACCESS  not-accessible
    STATUS      current
    DESCRIPTION
        "Information about a specific SDP segment routing traffic engineering
         (SR-TE) LSP."
    INDEX       {
        sdpId,
        sdpSegRouteTeLspId
    }
    ::= { sdpSegRouteTeLspTable 1 }

SdpSegRouteTeLspEntry            ::= SEQUENCE
{
    sdpSegRouteTeLspId               TmnxVRtrMplsLspID,
    sdpSegRouteTeLspRowStatus        RowStatus,
    sdpSegRouteTeLspLastChanged      TimeStamp
}

sdpSegRouteTeLspId               OBJECT-TYPE
    SYNTAX      TmnxVRtrMplsLspID
    MAX-ACCESS  not-accessible
    STATUS      current
    DESCRIPTION
        "The value of the sdpSegRouteTeLspId specifies LSP identifier
         associated with the 'Segment Routing Traffic Engineering' SDP which is
         used to reach the far-end ESR device.

         This LSP must terminate at the IP address specified by
         sdpFarEndIpAddress or sdpFarEndNodeId (for sdpDelivery of 'mpls')."
    ::= { sdpSegRouteTeLspEntry 1 }

sdpSegRouteTeLspRowStatus        OBJECT-TYPE
    SYNTAX      RowStatus
    MAX-ACCESS  read-create
    STATUS      current
    DESCRIPTION
        "The value of the sdpSegRouteTeLspRowStatus specifies the row status of
         the entry."
    ::= { sdpSegRouteTeLspEntry 2 }

sdpSegRouteTeLspLastChanged      OBJECT-TYPE
    SYNTAX      TimeStamp
    MAX-ACCESS  read-only
    STATUS      current
    DESCRIPTION
        "The value of sysUpTime at the time of the most recent change to this
         entry."
    ::= { sdpSegRouteTeLspEntry 3 }

sdpMplsLspTableLastChgd          OBJECT-TYPE
    SYNTAX      TimeStamp
    MAX-ACCESS  read-only
    STATUS      current
    DESCRIPTION
        "The value of sdpMplsLspTableLastChgd indicates the sysUpTime at the
         time of the last modification of sdpMplsLspTable.

         If no changes were made to the entry since the last re-initialization
         of the local network management subsystem, then this object contains a
         zero value."
    ::= { tmnxSdpObjs 72 }

sdpMplsLspTable                  OBJECT-TYPE
    SYNTAX      SEQUENCE OF SdpMplsLspEntry
    MAX-ACCESS  not-accessible
    STATUS      current
    DESCRIPTION
        "A table that contains SDP MPLS LSPs used to reach the far-end ESR
         device.

         All the LSPs in this list must terminate at the IP address specified
         by sdpFarEndIpAddress or sdpFarEndNodeId (for sdpDelivery of 'mpls').
         This object is otherwise insignificant and should contain a value of
         0.

         When this list has more than one element, the Nokia SROS router will
         use ALL of the LSPs for load balancing purposes. Each LSP ID in the
         list corresponds to the vRtrMplsLspIndex of the given MPLS LSP."
    ::= { tmnxSdpObjs 73 }

sdpMplsLspEntry                  OBJECT-TYPE
    SYNTAX      SdpMplsLspEntry
    MAX-ACCESS  not-accessible
    STATUS      current
    DESCRIPTION
        "Information about a specific SDP MPLS LSP."
    INDEX       {
        sdpId,
        sdpMplsLspId
    }
    ::= { sdpMplsLspTable 1 }

SdpMplsLspEntry                  ::= SEQUENCE
{
    sdpMplsLspId                     TmnxVRtrMplsLspIDNoZero,
    sdpMplsLspRowStatus              RowStatus,
    sdpMplsLspLastChanged            TimeStamp
}

sdpMplsLspId                     OBJECT-TYPE
    SYNTAX      TmnxVRtrMplsLspIDNoZero
    MAX-ACCESS  not-accessible
    STATUS      current
    DESCRIPTION
        "The value of the sdpMplsLspId specifies LSP identifier associated with
         the MPLS SDP which is used to reach the far-end ESR device.

         This LSP must terminate at the IP address specified by
         sdpFarEndIpAddress or sdpFarEndNodeId (for sdpDelivery of 'mpls')."
    ::= { sdpMplsLspEntry 1 }

sdpMplsLspRowStatus              OBJECT-TYPE
    SYNTAX      RowStatus
    MAX-ACCESS  read-create
    STATUS      current
    DESCRIPTION
        "The value of the sdpMplsLspRowStatus specifies the row status of the
         entry."
    ::= { sdpMplsLspEntry 2 }

sdpMplsLspLastChanged            OBJECT-TYPE
    SYNTAX      TimeStamp
    MAX-ACCESS  read-only
    STATUS      current
    DESCRIPTION
        "The value of sysUpTime at the time of the most recent change to this
         entry."
    ::= { sdpMplsLspEntry 3 }

tmnxSdpNotifyObjs                OBJECT IDENTIFIER ::= { tmnxSdpObjs 100 }

sdpNotifySdpId                   OBJECT-TYPE
    SYNTAX      SdpId
    MAX-ACCESS  accessible-for-notify
    STATUS      current
    DESCRIPTION
        "The ID of the SDP where SDP Bindings are associated. This object is
         used by the sdpBindSdpStateChangeProcessed notification to indicate
         the SDP that changed state and that resulted in having the associated
         sdpBindStatusChanged events suppressed for all SDP Bindings on that
         SDP."
    ::= { tmnxSdpNotifyObjs 1 }

dynamicSdpStatus                 OBJECT-TYPE
    SYNTAX      ConfigStatus
    MAX-ACCESS  accessible-for-notify
    STATUS      current
    DESCRIPTION
        "The value of dynamicSdpStatus indicates the status of the dynamic SDP
         which is used by the dynamicSdpConfigChanged and
         dynamicSdpBindConfigChanged notifications to indicate what state the
         dynamic SDP or SDP Bind has entered: 'created', 'modified', or
         'deleted'."
    ::= { tmnxSdpNotifyObjs 2 }

dynamicSdpOrigin                 OBJECT-TYPE
    SYNTAX      TmnxCreateOrigin
    MAX-ACCESS  accessible-for-notify
    STATUS      current
    DESCRIPTION
        "The value of dynamicSdpOrigin indicates the origin of the dynamic SDP.
         The origin indicates the protocol or mechanism that created the
         dynamic SDP."
    ::= { tmnxSdpNotifyObjs 3 }

dynamicSdpCreationError          OBJECT-TYPE
    SYNTAX      DisplayString
    MAX-ACCESS  accessible-for-notify
    STATUS      current
    DESCRIPTION
        "The value of the object dynamicSdpCreationError indicates the reason
         why the system was unable to create the dynamic SDP."
    ::= { tmnxSdpNotifyObjs 4 }

dynamicSdpBindCreationError      OBJECT-TYPE
    SYNTAX      DisplayString
    MAX-ACCESS  accessible-for-notify
    STATUS      current
    DESCRIPTION
        "The value of the object dynamicSdpBindCreationError indicates the
         reason why the system was unable to create the dynamic SDP Binding."
    ::= { tmnxSdpNotifyObjs 5 }

sdpBindNotifyMacAddr             OBJECT-TYPE
    SYNTAX      MacAddress
    MAX-ACCESS  accessible-for-notify
    STATUS      current
    DESCRIPTION
        "The value of the object sdpBindNotifyMacAddr indicates the MAC address
         associated with a VPLS SDP Binding."
    ::= { tmnxSdpNotifyObjs 6 }

sdpEgIfNetDomainInconsCount      OBJECT-TYPE
    SYNTAX      Unsigned32
    MAX-ACCESS  accessible-for-notify
    STATUS      current
    DESCRIPTION
        "The value of the object sdpEgIfNetDomainInconsCount indicates the
         number of SDPs which have an inconsistent network-domain for the SDP
         and egress network interfaces of the SDP."
    ::= { tmnxSdpNotifyObjs 7 }

sdpMSPwPeId                      OBJECT-TYPE
    SYNTAX      TmnxSpokeSdpIdOrZero
    MAX-ACCESS  accessible-for-notify
    STATUS      current
    DESCRIPTION
        "The value of the object sdpMSPwPeId specifies the multi-segment
         pseudo-wire provider-edge identifier for the service associated with
         this notification."
    ::= { tmnxSdpNotifyObjs 8 }

sdpBindIpipeCeIpAddrType         OBJECT-TYPE
    SYNTAX      InetAddressType
    MAX-ACCESS  accessible-for-notify
    STATUS      current
    DESCRIPTION
        "The value of sdpBindIpipeCeIpAddrType indicates the type of CE address
         on an IPIPE SDP. The CE IP address is specified by
         sdpBindIpipeCeIpAddress."
    ::= { tmnxSdpNotifyObjs 9 }

sdpBindIpipeCeIpAddress          OBJECT-TYPE
    SYNTAX      InetAddress (SIZE (0|4|16))
    MAX-ACCESS  accessible-for-notify
    STATUS      current
    DESCRIPTION
        "The value of sdpBindIpipeCeIpAddress indicates the CE IP address of
         type sdpBindIpipeCeIpAddrType on an IPIPE SDP."
    ::= { tmnxSdpNotifyObjs 10 }

sdpPbbActvPwWithNonActvCtrlPw    OBJECT-TYPE
    SYNTAX      TruthValue
    MAX-ACCESS  accessible-for-notify
    STATUS      current
    DESCRIPTION
        "The value of sdpPbbActvPwWithNonActvCtrlPw indicates that the
         first pseudo-wire (PW) with sdpBindUseSdpBMac set to 'true' becomes
         active on the  Backbone Edge Bridge (BEB) where the control PW is
         standby or down on that SDP.

         Value of 'false' for sdpPbbActvPwWithNonActvCtrlPw indicates that the
         last PW with sdpBindUseSdpBMac set to 'true' becomes standby or down
         on the BEB where control PW is standby or down on that SDP."
    ::= { tmnxSdpNotifyObjs 11 }

tmnxSdpConformance               OBJECT IDENTIFIER ::= { tmnxServConformance 4 }

tmnxSdpCompliances               OBJECT IDENTIFIER ::= { tmnxSdpConformance 1 }

tmnxSdp77x0V6v1Compliance        MODULE-COMPLIANCE
    STATUS      obsolete
    DESCRIPTION
        "The compliance statement for management of services SDPs on Nokia 7750
         SR and 7710 SR series systems."
    MODULE
        MANDATORY-GROUPS {
            tmnxSdpV6v0Group,
            tmnxSdpBindV6v0Group,
            tmnxSdpBindTlsV6v0Group,
            tmnxSdpBindMeshV6v0Group,
            tmnxSdpApipeV6v0Group,
            tmnxSdpBindDhcpV6v0Group,
            tmnxSdpBindIpipeV6v0Group,
            tmnxSdpBindTlsL2ptV6v0Group,
            tmnxSdpAutoBindV6v1Group,
            tmnxSdpBindTlsMrpV6v0Group,
            tmnxSdpTlsBgpV6v0Group,
            tmnxSdpNotifyV6v0Group,
            tmnxSdpL2V6v0Group,
            tmnxSdpFCV6v0Group,
            tmnxSdpBindCpipeV6v0Group
        }
    ::= { tmnxSdpCompliances 10 }

tmnxSdp7450V6v1Compliance        MODULE-COMPLIANCE
    STATUS      obsolete
    DESCRIPTION
        "The compliance statement for management of services SDPs on Nokia 7450
         ESS series systems."
    MODULE
        MANDATORY-GROUPS {
            tmnxSdpV6v0Group,
            tmnxSdpBindV6v0Group,
            tmnxSdpBindTlsV6v0Group,
            tmnxSdpBindMeshV6v0Group,
            tmnxSdpBindDhcpV6v0Group,
            tmnxSdpBindIpipeV6v0Group,
            tmnxSdpBindTlsL2ptV6v0Group,
            tmnxSdpAutoBindV6v1Group,
            tmnxSdpBindTlsMrpV6v0Group,
            tmnxSdpTlsBgpV6v0Group,
            tmnxSdpNotifyV6v0Group,
            tmnxSdpL2V6v0Group,
            tmnxSdpFCV6v0Group
        }
    ::= { tmnxSdpCompliances 11 }

tmnxSdp77x0V7v0Compliance        MODULE-COMPLIANCE
    STATUS      obsolete
    DESCRIPTION
        "The compliance statement for management of services SDPs on Nokia 7750
         SR and 7710 SR series systems."
    MODULE
        MANDATORY-GROUPS {
            tmnxSdpV6v0Group,
            tmnxSdpBindV6v0Group,
            tmnxSdpBindTlsV6v0Group,
            tmnxSdpBindMeshV6v0Group,
            tmnxSdpApipeV6v0Group,
            tmnxSdpBindDhcpV6v0Group,
            tmnxSdpBindTlsL2ptV6v0Group,
            tmnxSdpAutoBindV7v0Group,
            tmnxSdpBindTlsMrpV6v0Group,
            tmnxSdpTlsBgpV6v0Group,
            tmnxSdpNotifyV6v0Group,
            tmnxSdpL2V6v0Group,
            tmnxSdpFCV6v0Group,
            tmnxSdpBindCpipeV6v0Group,
            tmnxSdpBindIpipeV7v0Group,
            tmnxSdpL2V7v0Group,
            tmnxSdpEvalPwTempV7v0Group,
            tmnxSdpPbbGroup,
            tmnxSdpBindGenGroup
        }
    ::= { tmnxSdpCompliances 12 }

tmnxSdp7450V7v0Compliance        MODULE-COMPLIANCE
    STATUS      obsolete
    DESCRIPTION
        "The compliance statement for management of services SDPs on Nokia 7450
         ESS series systems."
    MODULE
        MANDATORY-GROUPS {
            tmnxSdpV6v0Group,
            tmnxSdpBindV6v0Group,
            tmnxSdpBindTlsV6v0Group,
            tmnxSdpBindMeshV6v0Group,
            tmnxSdpBindDhcpV6v0Group,
            tmnxSdpBindTlsL2ptV6v0Group,
            tmnxSdpAutoBindV7v0Group,
            tmnxSdpBindTlsMrpV6v0Group,
            tmnxSdpTlsBgpV6v0Group,
            tmnxSdpNotifyV6v0Group,
            tmnxSdpL2V6v0Group,
            tmnxSdpFCV6v0Group,
            tmnxSdpBindIpipeV7v0Group,
            tmnxSdpL2V7v0Group,
            tmnxSdpEvalPwTempV7v0Group,
            tmnxSdpPbbGroup,
            tmnxSdpBindGenGroup
        }
    ::= { tmnxSdpCompliances 13 }

tmnxSdp77x0V8v0Compliance        MODULE-COMPLIANCE
    STATUS      obsolete
    DESCRIPTION
        "The compliance statement for management of services SDPs on Nokia 7750
         SR and 7710 SR series systems."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpBindGenGroup,
            tmnxSdpLdpBackupV8v0Group,
            tmnxSdpV8v0Group,
            tmnxSdpBindV8v0Group,
            tmnxSdpNotifyV8v0Group,
            tmnxSdpAutoBindV8v0Group,
            tmnxSdpBgpVplsV8v0Group,
            tmnxSdpL2V8v0Group,
            tmnxSdpPwV8v0Group,
            tmnxSdpBindCpmProtGroup
        }
    ::= { tmnxSdpCompliances 14 }

tmnxSdp7450V8v0Compliance        MODULE-COMPLIANCE
    STATUS      obsolete
    DESCRIPTION
        "The compliance statement for management of services SDPs on Nokia 7450
         ESS series systems."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpBindGenGroup,
            tmnxSdpLdpBackupV8v0Group,
            tmnxSdpV8v0Group,
            tmnxSdpBindV8v0Group,
            tmnxSdpNotifyV8v0Group,
            tmnxSdpAutoBindV8v0Group,
            tmnxSdpBgpVplsV8v0Group,
            tmnxSdpL2V8v0Group,
            tmnxSdpPwV8v0Group,
            tmnxSdpBindCpmProtGroup
        }
    ::= { tmnxSdpCompliances 15 }

tmnxSdp77x0V9v0Compliance        MODULE-COMPLIANCE
    STATUS      obsolete
    DESCRIPTION
        "The compliance statement for management of services SDPs on Nokia 7750
         SR and 7710 SR series systems release R9.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup
        }
    ::= { tmnxSdpCompliances 16 }

tmnxSdp7450V9v0Compliance        MODULE-COMPLIANCE
    STATUS      obsolete
    DESCRIPTION
        "The compliance statement for management of services SDPs on Nokia 7450
         ESS series systems release R9.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup
        }
    ::= { tmnxSdpCompliances 17 }

tmnxSdp77x0V10v0Compliance       MODULE-COMPLIANCE
    STATUS      obsolete
    DESCRIPTION
        "The compliance statement for management of services SDPs on Nokia 7750
         SR and 7710 SR series systems release R9.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortGroup,
            tmnxSdpSpbGroup,
            tmnxSdpNotifyV10v0Group,
            tmnxSdpBindBlockOnPeerFaultGroup,
            tmnxSdpV10v0Group
        }
    ::= { tmnxSdpCompliances 18 }

tmnxSdp7450V10v0Compliance       MODULE-COMPLIANCE
    STATUS      obsolete
    DESCRIPTION
        "The compliance statement for management of services SDPs on Nokia 7450
         ESS series systems release R9.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpBindDhcpV6v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortGroup,
            tmnxSdpSpbGroup,
            tmnxSdpNotifyV10v0Group,
            tmnxSdpV10v0Group,
            tmnxSdpBindBlockOnPeerFaultGroup,
            tmnxSdpBindQGrpObjsV10v0Group
        }
    ::= { tmnxSdpCompliances 19 }

tmnxSdp77x0V11v0Compliance       MODULE-COMPLIANCE
    STATUS      obsolete
    DESCRIPTION
        "The compliance statement for management of services SDPs on Nokia 7750
         SR and 7710 SR series systems release R11.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpGrpGroup,
            tmnxSdpBindBlockOnPeerFaultGroup,
            tmnxSdpBindPwPortGroup,
            tmnxSdpBindCtrlChanGroup,
            tmnxSdpVllBgpV11v0Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            tmnxSdpBindCtrlChanReqGroup,
            tmnxSdpBindCtrlChanAckGroup
        }
    ::= { tmnxSdpCompliances 20 }

tmnxSdp7450V11v0Compliance       MODULE-COMPLIANCE
    STATUS      obsolete
    DESCRIPTION
        "The compliance statement for management of services SDPs on Nokia 7450
         ESS series systems release R11.0."
    MODULE
        MANDATORY-GROUPS {
            tmnxSdpV6v0Group,
            tmnxSdpBindV6v0Group,
            tmnxSdpBindTlsV6v0Group,
            tmnxSdpBindTlsV8v0Group,
            tmnxSdpBindMeshV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpBindQGrpObjsV10v0Group,
            tmnxSdpGrpGroup,
            tmnxSdpBindBlockOnPeerFaultGroup,
            tmnxSdpBindPwPortGroup,
            tmnxSdpBindCtrlChanGroup,
            tmnxSdpVllBgpV11v0Group,
            tmnxSdpL2tpv3Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            tmnxSdpBindCtrlChanReqGroup,
            tmnxSdpBindCtrlChanAckGroup
        }
    ::= { tmnxSdpCompliances 21 }

tmnxSdp77x0V12v0Compliance       MODULE-COMPLIANCE
    STATUS      obsolete
    DESCRIPTION
        "The compliance statement for management of services SDPs on Nokia 7750
         SR and 7710 SR series systems release R12.0."
    MODULE
        MANDATORY-GROUPS {
            tmnxSdpV12v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpGrpGroup,
            tmnxSdpBindBlockOnPeerFaultGroup,
            tmnxSdpBindPwPortGroup,
            tmnxSdpBindCtrlChanGroup,
            tmnxSdpVllBgpV11v0Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindV11v0Group,
            tmnxSdpBindCtrlChanAckGroup,
            tmnxSdpPBBEpipePWRedV12v0Group,
            tmnxSdpPbbEpipeNotifyObjsGroup,
            tmnxSdpPbbEpipeNotifV12v0Group,
            tmnxSdpBindEthCfmV12v0Group,
            tmnxSdpBfdV12v0Group,
            tmnxSdpL2tpv3CookieGroup,
            tmnxSdpPwTempBindV12v0Group,
            tmnxSdpPwLoopbackGroup,
            tmnxPwTemplateAugGroup,
            tmnxSdpCtrlPwNotifV12v0Group
        }
    ::= { tmnxSdpCompliances 22 }

tmnxSdp7450V12v0Compliance       MODULE-COMPLIANCE
    STATUS      obsolete
    DESCRIPTION
        "The compliance statement for management of services SDPs on Nokia 7450
         ESS series systems release R12.0."
    MODULE
        MANDATORY-GROUPS {
            tmnxSdpV12v0Group,
            tmnxSdpBindV6v0Group,
            tmnxSdpBindTlsV6v0Group,
            tmnxSdpBindTlsV8v0Group,
            tmnxSdpBindMeshV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpV8v0Group,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpBindQGrpObjsV10v0Group,
            tmnxSdpGrpGroup,
            tmnxSdpBindBlockOnPeerFaultGroup,
            tmnxSdpBindPwPortGroup,
            tmnxSdpBindCtrlChanGroup,
            tmnxSdpVllBgpV11v0Group,
            tmnxSdpL2tpv3Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindCtrlChanAckGroup,
            tmnxSdpBindV11v0Group,
            tmnxSdpPBBEpipePWRedV12v0Group,
            tmnxSdpPbbEpipeNotifyObjsGroup,
            tmnxSdpPbbEpipeNotifV12v0Group,
            tmnxSdpL2tpv3CookieGroup,
            tmnxSdpPwTempBindV12v0Group,
            tmnxSdpPwLoopbackGroup,
            tmnxPwTemplateAugGroup,
            tmnxSdpCtrlPwNotifV12v0Group
        }
    ::= { tmnxSdpCompliances 23 }

tmnxSdp77x0V13v0Compliance       MODULE-COMPLIANCE
    STATUS      obsolete
    DESCRIPTION
        "The compliance statement for management of services SDPs on Nokia 7750
         SR and 7710 SR series systems release R13.0."
    MODULE
        MANDATORY-GROUPS {
            tmnxSdpV13v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpGrpGroup,
            tmnxSdpBindBlockOnPeerFaultGroup,
            tmnxSdpBindPwPortGroup,
            tmnxSdpBindCtrlChanGroup,
            tmnxSdpVllBgpV11v0Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindV11v0Group,
            tmnxSdpBindCtrlChanAckGroup,
            tmnxSdpPBBEpipePWRedV12v0Group,
            tmnxSdpPbbEpipeNotifyObjsGroup,
            tmnxSdpPbbEpipeNotifV12v0Group,
            tmnxSdpBindEthCfmV12v0Group,
            tmnxSdpBfdV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpBindV13v0Group,
            tmnxSdpSegRouteGroup,
            tmnxSdpBindDhcpV13v0Group,
            sdpBgpEvpnMplsMhGroup
        }
    ::= { tmnxSdpCompliances 24 }

tmnxSdp7450V13v0Compliance       MODULE-COMPLIANCE
    STATUS      obsolete
    DESCRIPTION
        "The compliance statement for management of services SDPs on Nokia 7450
         ESS series systems release R13.0."
    MODULE
        MANDATORY-GROUPS {
            tmnxSdpV13v0Group,
            tmnxSdpBindV6v0Group,
            tmnxSdpBindTlsV6v0Group,
            tmnxSdpBindTlsV8v0Group,
            tmnxSdpBindMeshV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpBindQGrpObjsV10v0Group,
            tmnxSdpGrpGroup,
            tmnxSdpBindBlockOnPeerFaultGroup,
            tmnxSdpBindPwPortGroup,
            tmnxSdpBindCtrlChanGroup,
            tmnxSdpVllBgpV11v0Group,
            tmnxSdpL2tpv3Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindCtrlChanAckGroup,
            tmnxSdpBindV11v0Group,
            tmnxSdpPBBEpipePWRedV12v0Group,
            tmnxSdpPbbEpipeNotifyObjsGroup,
            tmnxSdpPbbEpipeNotifV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpBindV13v0Group,
            tmnxSdpSegRouteGroup,
            tmnxSdpPwPortOperGrpGroup,
            tmnxSdpBindDhcpV13v0Group,
            sdpBgpEvpnMplsMhGroup,
            sdpGreExtGroup
        }
    ::= { tmnxSdpCompliances 25 }

tmnxSdp7750V14v0Compliance       MODULE-COMPLIANCE
    STATUS      obsolete
    DESCRIPTION
        "The compliance statement for management of services SDPs on Nokia 7750
         ESS series systems release R14.0."
    MODULE
        MANDATORY-GROUPS {
            svcPwTmplExt14v0Group,
            tmnxSdpBindV14v0Group,
            tmnxSdpV13v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpGrpGroup,
            tmnxSdpBindBlockOnPeerFaultGroup,
            tmnxSdpBindPwPortGroup,
            tmnxSdpBindCtrlChanGroup,
            tmnxSdpVllBgpV11v0Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindV11v0Group,
            tmnxSdpBindCtrlChanAckGroup,
            tmnxSdpPBBEpipePWRedV12v0Group,
            tmnxSdpPbbEpipeNotifyObjsGroup,
            tmnxSdpPbbEpipeNotifV12v0Group,
            tmnxSdpBindEthCfmV12v0Group,
            tmnxSdpBfdV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpSegRouteGroup,
            tmnxSdpBindDhcpV13v0Group,
            sdpBgpEvpnMplsMhGroup,
            sdpPwStaticLabelGroup,
            sdpBindV14v0Group,
            sdpFpeV14v0Group,
            sdpBindBgpEvpnAlmpGroup
        }
    ::= { tmnxSdpCompliances 26 }

tmnxSdp7450V14v0Compliance       MODULE-COMPLIANCE
    STATUS      obsolete
    DESCRIPTION
        "The compliance statement for management of services SDPs on Nokia 7450
         ESS series systems release R14.0."
    MODULE
        MANDATORY-GROUPS {
            svcPwTmplExt14v0Group,
            tmnxSdpBindV14v0Group,
            tmnxSdpSegRouteTeGroup,
            tmnxSdpV13v0Group,
            tmnxSdpBindV6v0Group,
            tmnxSdpBindTlsV6v0Group,
            tmnxSdpBindTlsV8v0Group,
            tmnxSdpBindMeshV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpBindQGrpObjsV10v0Group,
            tmnxSdpGrpGroup,
            tmnxSdpBindBlockOnPeerFaultGroup,
            tmnxSdpBindPwPortGroup,
            tmnxSdpBindCtrlChanGroup,
            tmnxSdpVllBgpV11v0Group,
            tmnxSdpL2tpv3Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindCtrlChanAckGroup,
            tmnxSdpBindV11v0Group,
            tmnxSdpPBBEpipePWRedV12v0Group,
            tmnxSdpPbbEpipeNotifyObjsGroup,
            tmnxSdpPbbEpipeNotifV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpSegRouteGroup,
            tmnxSdpPwPortOperGrpGroup,
            tmnxSdpBindDhcpV13v0Group,
            sdpBgpEvpnMplsMhGroup,
            sdpGreExtGroup,
            sdpPwStaticLabelGroup,
            sdpBindV14v0Group,
            sdpBindTlsV14v0Group,
            sdpFpeV14v0Group,
            sdpBindBgpEvpnAlmpGroup
        }
    ::= { tmnxSdpCompliances 27 }

tmnxSdp7750V15v0Compliance       MODULE-COMPLIANCE
    STATUS      current
    DESCRIPTION
        "The compliance statement for management of services SDPs on Nokia 7750
         SROS series systems release 15.0."
    MODULE
        MANDATORY-GROUPS {
            tmnxSdpMplsLspGroup,
            tmnxSdpCfmLmmPerQosV15v0Group,
            svcPwTmplExt14v0Group,
            tmnxSdpBindV14v0Group,
            tmnxSdpBindV6v0Group,
            tmnxSdpBindTlsV6v0Group,
            tmnxSdpBindTlsV8v0Group,
            tmnxSdpBindMeshV6v0Group,
            tmnxSdpApipeV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindCpipeV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpGrpGroup,
            tmnxSdpBindBlockOnPeerFaultGroup,
            tmnxSdpBindPwPortGroup,
            tmnxSdpBindCtrlChanGroup,
            tmnxSdpVllBgpV11v0Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindCtrlChanAckGroup,
            tmnxSdpPBBEpipePWRedV12v0Group,
            tmnxSdpPbbEpipeNotifyObjsGroup,
            tmnxSdpPbbEpipeNotifV12v0Group,
            tmnxSdpBindEthCfmV12v0Group,
            tmnxSdpBfdV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpSegRouteGroup,
            tmnxSdpBindDhcpV13v0Group,
            sdpBgpEvpnMplsMhGroup,
            sdpPwStaticLabelGroup,
            sdpBindV14v0Group,
            sdpFpeV14v0Group,
            sdpBindBgpEvpnAlmpGroup,
            tmnxSdpV15v0Group,
            tmnxSdpWeightedLoadBalanceGroup,
            sdpEvpnMhEthSegV15v0Group,
            tmnxPwTempNameV15v0Group,
            sdpOperTunnelFarEndGroup
        }
    ::= { tmnxSdpCompliances 28 }

tmnxSdp7450V15v0Compliance       MODULE-COMPLIANCE
    STATUS      current
    DESCRIPTION
        "The compliance statement for management of services SDPs on Nokia 7450
         ESS series systems release 15.0."
    MODULE
        MANDATORY-GROUPS {
            tmnxSdpMplsLspGroup,
            tmnxSdpCfmLmmPerQosV15v0Group,
            svcPwTmplExt14v0Group,
            tmnxSdpBindV14v0Group,
            tmnxSdpSegRouteTeGroup,
            tmnxSdpBindV6v0Group,
            tmnxSdpBindTlsV6v0Group,
            tmnxSdpBindTlsV8v0Group,
            tmnxSdpBindMeshV6v0Group,
            tmnxSdpBindDhcpV6v0Group,
            tmnxSdpBindDhcpV11v0Group,
            tmnxSdpBindTlsL2ptV6v0Group,
            tmnxSdpAutoBindV7v0Group,
            tmnxSdpBindTlsMrpV8v0Group,
            tmnxSdpTlsBgpV6v0Group,
            tmnxSdpNotifyV6v0Group,
            tmnxSdpL2V6v0Group,
            tmnxSdpFCV6v0Group,
            tmnxSdpBindIpipeV8v0Group,
            tmnxSdpL2V7v0Group,
            tmnxSdpEvalPwTempV7v0Group,
            tmnxSdpPbbGroup,
            tmnxSdpPbbV12v0Group,
            tmnxSdpBindGenGroup,
            tmnxSdpBindV9v0Group,
            tmnxSdpBindBsxV9v0Group,
            tmnxSdpBindBsxV10v0Group,
            tmnxSdpNotifyV8v0Group,
            tmnxSdpAutoBindV8v0Group,
            tmnxSdpBgpVplsV8v0Group,
            tmnxSdpL2V8v0Group,
            tmnxSdpPwV8v0Group,
            tmnxSdpBindV8v0Group,
            tmnxSdpV9v0Group,
            tmnxSdpBindCpmProtGroup,
            tmnxSdpMixedLspModeV9v0Group,
            tmnxSdpBindEthCfmGroup,
            tmnxSdpBindIpipeNotifyGroup,
            tmnxSdpPwPortV11v0Group,
            tmnxSdpSpbGroup,
            tmnxSdpNotifyV10v0Group,
            tmnxSdpV10v0Group,
            tmnxSdpNotifyV11v0Group,
            tmnxSdpBindQGrpObjsV10v0Group,
            tmnxSdpGrpGroup,
            tmnxSdpBindBlockOnPeerFaultGroup,
            tmnxSdpBindPwPortGroup,
            tmnxSdpBindCtrlChanGroup,
            tmnxSdpVllBgpV11v0Group,
            tmnxSdpL2tpv3Group,
            tmnxSdpBindSpbV11v0Group,
            tmnxSdpBindFlowSpecGroup,
            tmnxSdpPwSecShaperGroup,
            tmnxSdpBindEthLoopbackV11v0Group,
            tmnxSdpBindEthLpbkNtfyV11v0Group,
            sdpBindTlsFdbMacStatsGroup,
            sdpBindTlsEtreeGroup,
            tmnxSdpBindCpmProtV12v0Group,
            tmnxSdpBindCtrlChanReqGroup,
            tmnxSdpBindCtrlChanAckGroup,
            tmnxSdpPBBEpipePWRedV12v0Group,
            tmnxSdpPbbEpipeNotifyObjsGroup,
            tmnxSdpPbbEpipeNotifV12v0Group,
            tmnxSdpL2tpv3CookieGroup,
            tmnxSdpPwTempBindV12v0Group,
            tmnxSdpPwLoopbackGroup,
            tmnxPwTemplateAugGroup,
            tmnxSdpCtrlPwNotifV12v0Group,
            tmnxSdpLdpIpv6Group,
            tmnxSdpSegRouteGroup,
            tmnxSdpPwPortOperGrpGroup,
            tmnxSdpBindDhcpV13v0Group,
            sdpBgpEvpnMplsMhGroup,
            sdpGreExtGroup,
            sdpPwStaticLabelGroup,
            sdpBindV14v0Group,
            sdpBindTlsV14v0Group,
            sdpFpeV14v0Group,
            sdpBindBgpEvpnAlmpGroup,
            tmnxSdpV15v0Group,
            tmnxPwTempNameV15v0Group,
            sdpOperTunnelFarEndGroup
        }
    ::= { tmnxSdpCompliances 29 }

tmnxSdp7750V16v0Compliance       MODULE-COMPLIANCE
    STATUS      current
    DESCRIPTION
        "The compliance statement for management of services SDPs on Nokia 7750
         SROS series systems release 16.0."
    MODULE
        MANDATORY-GROUPS {
            pwTemplateGreGroup,
            pwTemplateQosV16v0Group,
            pwTemplateFilterNameV16v0Group,
            tmnxSdpBindQinqV16v0Group
        }
    ::= { tmnxSdpCompliances 30 }

tmnxSdp7450V16v0Compliance       MODULE-COMPLIANCE
    STATUS      current
    DESCRIPTION
        "The compliance statement for management of services SDPs on Nokia 7450
         SROS series systems release 16.0."
    MODULE
        MANDATORY-GROUPS {
            pwTemplateGreGroup,
            pwTemplateQosV16v0Group,
            pwTemplateFilterNameV16v0Group,
            tmnxSdpBindQinqV16v0Group
        }
    ::= { tmnxSdpCompliances 31 }

tmnxSdpV19v0Compliance           MODULE-COMPLIANCE
    STATUS      current
    DESCRIPTION
        "The compliance statement for management of services SDPs on Nokia SROS
         series systems release 19.0"
    MODULE
        MANDATORY-GROUPS {
            sdpPwPortControlWordGroup,
            pwTemplateNgeAutoBindGroup,
            sdpBindMcastSrcV19v0Group
        }
    ::= { tmnxSdpCompliances 32 }

tmnxSdpGroups                    OBJECT IDENTIFIER ::= { tmnxSdpConformance 2 }

tmnxSdpV6v0Group                 OBJECT-GROUP
    OBJECTS     {
        sdpNumEntries,
        sdpNextFreeId,
        sdpId,
        sdpRowStatus,
        sdpDelivery,
        sdpFarEndIpAddress,
        sdpLspList,
        sdpDescription,
        sdpLabelSignaling,
        sdpAdminStatus,
        sdpOperStatus,
        sdpOperPathMtu,
        sdpKeepAliveAdminStatus,
        sdpKeepAliveOperStatus,
        sdpKeepAliveHelloTime,
        sdpKeepAliveMaxDropCount,
        sdpKeepAliveHoldDownTime,
        sdpLastMgmtChange,
        sdpKeepAliveNumHelloRequestMessages,
        sdpKeepAliveNumHelloResponseMessages,
        sdpKeepAliveNumLateHelloResponseMessages,
        sdpKeepAliveHelloRequestTimeout,
        sdpLdpEnabled,
        sdpVlanVcEtype,
        sdpAdvertisedVllMtuOverride,
        sdpOperFlags,
        sdpLastStatusChange,
        sdpMvplsMgmtService,
        sdpMvplsMgmtSdpBndId,
        sdpCollectAcctStats,
        sdpAccountingPolicyId,
        sdpClassFwdingEnabled,
        sdpClassFwdingDefaultLsp,
        sdpClassFwdingMcLsp,
        sdpMetric,
        sdpAutoSdp,
        sdpSnmpAllowed,
        sdpPBBEtype,
        sdpBandwidthBookingFactor,
        sdpOperBandwidth,
        sdpAvailableBandwidth,
        sdpAdminPathMtu,
        sdpKeepAliveHelloMessageLength
    }
    STATUS      obsolete
    DESCRIPTION
        "The  group  of objects supporting SDP base feature
         on Nokia SROS series systems."
    ::= { tmnxSdpGroups 100 }

tmnxSdpBindV6v0Group             OBJECT-GROUP
    OBJECTS     {
        sdpBindId,
        sdpBindRowStatus,
        sdpBindAdminStatus,
        sdpBindOperStatus,
        sdpBindLastMgmtChange,
        sdpBindType,
        sdpBindIngressMacFilterId,
        sdpBindIngressIpFilterId,
        sdpBindEgressMacFilterId,
        sdpBindEgressIpFilterId,
        sdpBindVpnId,
        sdpBindCustId,
        sdpBindVcType,
        sdpBindVlanVcTag,
        sdpBindSplitHorizonGrp,
        sdpBindOperFlags,
        sdpBindLastStatusChange,
        sdpBindIesIfIndex,
        sdpBindMacPinning,
        sdpBindIngressIpv6FilterId,
        sdpBindEgressIpv6FilterId,
        sdpBindCollectAcctStats,
        sdpBindAccountingPolicyId,
        sdpBindPwPeerStatusBits,
        sdpBindPeerVccvCvBits,
        sdpBindPeerVccvCcBits,
        sdpBindControlWordBit,
        sdpBindOperControlWord,
        sdpBindEndPoint,
        sdpBindEndPointPrecedence,
        sdpBindIsICB,
        sdpBindPwFaultInetAddressType,
        sdpBindClassFwdingOperState,
        sdpBindForceVlanVcForwarding,
        sdpBindAdminBandwidth,
        sdpBindOperBandwidth,
        sdpBindBaseStatsIngressForwardedPackets,
        sdpBindBaseStatsIngressDroppedPackets,
        sdpBindBaseStatsEgressForwardedPackets,
        sdpBindBaseStatsEgressForwardedOctets,
        sdpBindBaseStatsCustId,
        sdpBindBaseStatsIngFwdOctets,
        sdpBindBaseStatsIngDropOctets,
        sdpBindAdminIngressLabel,
        sdpBindAdminEgressLabel,
        sdpBindOperIngressLabel,
        sdpBindOperEgressLabel,
        sdpBindPwFaultInetAddress
    }
    STATUS      current
    DESCRIPTION
        "The  group  of objects supporting SDP Bind feature
         on Nokia SROS series systems."
    ::= { tmnxSdpGroups 101 }

tmnxSdpBindTlsV6v0Group          OBJECT-GROUP
    OBJECTS     {
        sdpBindTlsStpAdminStatus,
        sdpBindTlsStpPriority,
        sdpBindTlsStpPortNum,
        sdpBindTlsStpPathCost,
        sdpBindTlsStpRapidStart,
        sdpBindTlsStpBpduEncap,
        sdpBindTlsStpPortState,
        sdpBindTlsStpDesignatedBridge,
        sdpBindTlsStpDesignatedPort,
        sdpBindTlsStpForwardTransitions,
        sdpBindTlsStpInConfigBpdus,
        sdpBindTlsStpInTcnBpdus,
        sdpBindTlsStpInBadBpdus,
        sdpBindTlsStpOutConfigBpdus,
        sdpBindTlsStpOutTcnBpdus,
        sdpBindTlsStpOperBpduEncap,
        sdpBindTlsStpVpnId,
        sdpBindTlsStpCustId,
        sdpBindTlsMacAddressLimit,
        sdpBindTlsNumMacAddresses,
        sdpBindTlsNumStaticMacAddresses,
        sdpBindTlsMacLearning,
        sdpBindTlsMacAgeing,
        sdpBindTlsStpOperEdge,
        sdpBindTlsStpAdminPointToPoint,
        sdpBindTlsStpPortRole,
        sdpBindTlsStpAutoEdge,
        sdpBindTlsStpOperProtocol,
        sdpBindTlsStpInRstBpdus,
        sdpBindTlsStpOutRstBpdus,
        sdpBindTlsLimitMacMove,
        sdpBindTlsDiscardUnknownSource,
        sdpBindTlsMvplsPruneState,
        sdpBindTlsMvplsMgmtService,
        sdpBindTlsMvplsMgmtSdpBndId,
        sdpBindTlsStpException,
        sdpBindTlsL2ptTermination,
        sdpBindTlsBpduTranslation,
        sdpBindTlsStpRootGuard,
        sdpBindTlsStpInMstBpdus,
        sdpBindTlsStpOutMstBpdus,
        sdpBindTlsStpRxdDesigBridge,
        sdpBindTlsMacMoveNextUpTime,
        sdpBindTlsMacMoveRateExcdLeft,
        sdpBindTlsLimitMacMoveLevel,
        sdpBindTlsBpduTransOper,
        sdpBindTlsL2ptProtocols,
        sdpBindTlsIgnoreStandbySig,
        sdpBindTlsBlockOnMeshFail
    }
    STATUS      current
    DESCRIPTION
        "The  group  of objects supporting SDP Bind TLS feature
         on Nokia SROS series systems."
    ::= { tmnxSdpGroups 102 }

tmnxSdpBindMeshV6v0Group         OBJECT-GROUP
    OBJECTS     {
        sdpBindMeshTlsPortState,
        sdpBindMeshTlsNotInMstRegion,
        sdpBindMeshTlsHoldDownTimer,
        sdpBindMeshTlsTransitionState
    }
    STATUS      current
    DESCRIPTION
        "The  group  of objects supporting mesh SDP bind feature
         on Nokia SROS series systems."
    ::= { tmnxSdpGroups 103 }

tmnxSdpApipeV6v0Group            OBJECT-GROUP
    OBJECTS     {
        sdpBindApipeAdminConcatCellCount,
        sdpBindApipeSigConcatCellCount,
        sdpBindApipeOperConcatCellCount,
        sdpBindApipeConcatMaxDelay,
        sdpBindApipeConcatCellClp,
        sdpBindApipeConcatCellAal5Fr
    }
    STATUS      current
    DESCRIPTION
        "The  group  of objects supporting SDP APipe feature
         on Nokia SROS series systems."
    ::= { tmnxSdpGroups 104 }

tmnxSdpBindDhcpV6v0Group         OBJECT-GROUP
    OBJECTS     {
        sdpBindDhcpDescription,
        sdpBindDhcpSnoop,
        sdpBindDhcpStatsClntSnoopdPckts,
        sdpBindDhcpStatsSrvrSnoopdPckts,
        sdpBindDhcpStatsClntForwdPckts,
        sdpBindDhcpStatsSrvrForwdPckts,
        sdpBindDhcpStatsClntDropdPckts,
        sdpBindDhcpStatsSrvrDropdPckts,
        sdpBindDhcpStatsClntProxRadPckts,
        sdpBindDhcpStatsClntProxLSPckts,
        sdpBindDhcpStatsGenReleasePckts,
        sdpBindDhcpStatsGenForceRenPckts
    }
    STATUS      current
    DESCRIPTION
        "The  group  of objects supporting SDP Bind DHCP feature
         on Nokia SROS series systems."
    ::= { tmnxSdpGroups 105 }

tmnxSdpBindIpipeV6v0Group        OBJECT-GROUP
    OBJECTS     {
        sdpBindIpipeCeInetAddressType,
        sdpBindIpipeCeInetAddress
    }
    STATUS      obsolete
    DESCRIPTION
        "The  group  of objects supporting SDP Bind Ipipe Service
         on Nokia SROS series systems."
    ::= { tmnxSdpGroups 106 }

tmnxSdpFCV6v0Group               OBJECT-GROUP
    OBJECTS     {
        sdpFCMappingRowStatus,
        sdpFCMappingLspId
    }
    STATUS      current
    DESCRIPTION
        "The  group  of objects supporting SDP FC feature
         on Nokia SROS series systems."
    ::= { tmnxSdpGroups 107 }

tmnxSdpBindCpipeV6v0Group        OBJECT-GROUP
    OBJECTS     {
        sdpBindCpipeLocalPayloadSize,
        sdpBindCpipePeerPayloadSize,
        sdpBindCpipeLocalBitrate,
        sdpBindCpipePeerBitrate,
        sdpBindCpipeLocalSigPkts,
        sdpBindCpipePeerSigPkts,
        sdpBindCpipeLocalCasTrunkFraming,
        sdpBindCpipePeerCasTrunkFraming,
        sdpBindCpipeLocalUseRtpHeader,
        sdpBindCpipePeerUseRtpHeader,
        sdpBindCpipeLocalDifferential,
        sdpBindCpipePeerDifferential,
        sdpBindCpipeLocalTimestampFreq,
        sdpBindCpipePeerTimestampFreq
    }
    STATUS      current
    DESCRIPTION
        "The  group  of objects supporting SDP bind CPipe feature
         on Nokia SROS series systems."
    ::= { tmnxSdpGroups 108 }

tmnxSdpBindTlsL2ptV6v0Group      OBJECT-GROUP
    OBJECTS     {
        sdpBindTlsMfibMdaRowStatus,
        sdpBindTlsL2ptStatsLastClearedTime,
        sdpBindTlsL2ptStatsL2ptEncapStpConfigBpdusRx,
        sdpBindTlsL2ptStatsL2ptEncapStpConfigBpdusTx,
        sdpBindTlsL2ptStatsL2ptEncapStpRstBpdusRx,
        sdpBindTlsL2ptStatsL2ptEncapStpRstBpdusTx,
        sdpBindTlsL2ptStatsL2ptEncapStpTcnBpdusRx,
        sdpBindTlsL2ptStatsL2ptEncapStpTcnBpdusTx,
        sdpBindTlsL2ptStatsL2ptEncapPvstConfigBpdusRx,
        sdpBindTlsL2ptStatsL2ptEncapPvstConfigBpdusTx,
        sdpBindTlsL2ptStatsL2ptEncapPvstRstBpdusRx,
        sdpBindTlsL2ptStatsL2ptEncapPvstRstBpdusTx,
        sdpBindTlsL2ptStatsL2ptEncapPvstTcnBpdusRx,
        sdpBindTlsL2ptStatsL2ptEncapPvstTcnBpdusTx,
        sdpBindTlsL2ptStatsStpConfigBpdusRx,
        sdpBindTlsL2ptStatsStpConfigBpdusTx,
        sdpBindTlsL2ptStatsStpRstBpdusRx,
        sdpBindTlsL2ptStatsStpRstBpdusTx,
        sdpBindTlsL2ptStatsStpTcnBpdusRx,
        sdpBindTlsL2ptStatsStpTcnBpdusTx,
        sdpBindTlsL2ptStatsPvstConfigBpdusRx,
        sdpBindTlsL2ptStatsPvstConfigBpdusTx,
        sdpBindTlsL2ptStatsPvstRstBpdusRx,
        sdpBindTlsL2ptStatsPvstRstBpdusTx,
        sdpBindTlsL2ptStatsPvstTcnBpdusRx,
        sdpBindTlsL2ptStatsPvstTcnBpdusTx,
        sdpBindTlsL2ptStatsOtherBpdusRx,
        sdpBindTlsL2ptStatsOtherBpdusTx,
        sdpBindTlsL2ptStatsOtherL2ptBpdusRx,
        sdpBindTlsL2ptStatsOtherL2ptBpdusTx,
        sdpBindTlsL2ptStatsOtherInvalidBpdusRx,
        sdpBindTlsL2ptStatsOtherInvalidBpdusTx,
        sdpBindTlsL2ptStatsL2ptEncapCdpBpdusRx,
        sdpBindTlsL2ptStatsL2ptEncapCdpBpdusTx,
        sdpBindTlsL2ptStatsL2ptEncapVtpBpdusRx,
        sdpBindTlsL2ptStatsL2ptEncapVtpBpdusTx,
        sdpBindTlsL2ptStatsL2ptEncapDtpBpdusRx,
        sdpBindTlsL2ptStatsL2ptEncapDtpBpdusTx,
        sdpBindTlsL2ptStatsL2ptEncapPagpBpdusRx,
        sdpBindTlsL2ptStatsL2ptEncapPagpBpdusTx,
        sdpBindTlsL2ptStatsL2ptEncapUdldBpdusRx,
        sdpBindTlsL2ptStatsL2ptEncapUdldBpdusTx,
        sdpBindTlsL2ptStatsCdpBpdusRx,
        sdpBindTlsL2ptStatsCdpBpdusTx,
        sdpBindTlsL2ptStatsVtpBpdusRx,
        sdpBindTlsL2ptStatsVtpBpdusTx,
        sdpBindTlsL2ptStatsDtpBpdusRx,
        sdpBindTlsL2ptStatsDtpBpdusTx,
        sdpBindTlsL2ptStatsPagpBpdusRx,
        sdpBindTlsL2ptStatsPagpBpdusTx,
        sdpBindTlsL2ptStatsUdldBpdusRx,
        sdpBindTlsL2ptStatsUdldBpdusTx
    }
    STATUS      current
    DESCRIPTION
        "The  group  of objects supporting SDP bind L2pt feature
         on Nokia SROS series systems."
    ::= { tmnxSdpGroups 109 }

tmnxSdpAutoBindV6v0Group         OBJECT-GROUP
    OBJECTS     {
        pwTemplateTableLastChanged,
        pwTemplateRowStatus,
        pwTemplateLastChanged,
        pwTemplateVcType,
        pwTemplateAccountingPolicyId,
        pwTemplateCollectAcctStats,
        pwTemplateMacLearning,
        pwTemplateMacAgeing,
        pwTemplateDiscardUnknownSource,
        pwTemplateLimitMacMove,
        pwTemplateMacPinning,
        pwTemplateMacAddressLimit,
        pwTemplateShgName,
        pwTemplateShgDescription,
        pwTemplateShgRestProtSrcMac,
        pwTemplateShgRestUnprotDstMac,
        pwTemplateEgressMacFilterId,
        pwTemplateEgressIpFilterId,
        pwTemplateEgressIpv6FilterId,
        pwTemplateIngressMacFilterId,
        pwTemplateIngressIpFilterId,
        pwTemplateIngressIpv6FilterId,
        pwTemplateIgmpFastLeave,
        pwTemplateIgmpImportPlcy,
        pwTemplateIgmpLastMembIntvl,
        pwTemplateIgmpMaxNbrGrps,
        pwTemplateIgmpGenQueryIntvl,
        pwTemplateIgmpQueryRespIntvl,
        pwTemplateIgmpRobustCount,
        pwTemplateIgmpSendQueries,
        pwTemplateIgmpMcacPolicyName,
        pwTemplateIgmpMcacPrRsvMndBW,
        pwTemplateIgmpMcacUnconstBW,
        pwTemplateIgmpVersion,
        pwTemplateIgmpSnpgGrpSrcTblLC,
        pwTemplateIgmpSnpgRowStatus,
        pwTemplateIgmpSnpgLastChngd,
        pwTemplateMfibAllowedMdaTblLC,
        pwTemplateMfibMdaRowStatus,
        pwTemplateUseProvisionedSdp,
        pwTemplateVlanVcTag,
        sdpAutoBindBgpInfoTableLC,
        sdpAutoBindBgpInfoTemplateId,
        sdpAutoBindBgpInfoAGI,
        sdpAutoBindBgpInfoSAII,
        sdpAutoBindBgpInfoTAII
    }
    STATUS      obsolete
    DESCRIPTION
        "The  group  of objects supporting SDP auto-bind feature
         on Nokia SROS series systems."
    ::= { tmnxSdpGroups 112 }

tmnxSdpBindTlsMrpV6v0Group       OBJECT-GROUP
    OBJECTS     {
        sdpBindTlsMrpTableLastChanged,
        sdpBindTlsMrpLastChngd,
        sdpBindTlsMrpJoinTime,
        sdpBindTlsMrpLeaveTime,
        sdpBindTlsMrpLeaveAllTime,
        sdpBindTlsMrpPeriodicTime,
        sdpBindTlsMrpPeriodicEnabled,
        sdpBindTlsMrpRxPdus,
        sdpBindTlsMrpDroppedPdus,
        sdpBindTlsMrpTxPdus,
        sdpBindTlsMrpRxNewEvent,
        sdpBindTlsMrpRxJoinInEvent,
        sdpBindTlsMrpRxInEvent,
        sdpBindTlsMrpRxJoinEmptyEvent,
        sdpBindTlsMrpRxEmptyEvent,
        sdpBindTlsMrpRxLeaveEvent,
        sdpBindTlsMrpTxNewEvent,
        sdpBindTlsMrpTxJoinInEvent,
        sdpBindTlsMrpTxInEvent,
        sdpBindTlsMrpTxJoinEmptyEvent,
        sdpBindTlsMrpTxEmptyEvent,
        sdpBindTlsMrpTxLeaveEvent,
        sdpBindTlsMmrpDeclared,
        sdpBindTlsMmrpRegistered
    }
    STATUS      obsolete
    DESCRIPTION
        "The  group  of objects supporting SDP MRP feature
         on Nokia SROS series systems."
    ::= { tmnxSdpGroups 113 }

tmnxSdpTlsBgpV6v0Group           OBJECT-GROUP
    OBJECTS     {
        svcTlsBgpADPWTempBindTblLC,
        svcTlsBgpADPWTempBindRowStatus,
        svcTlsBgpADPWTempBindLastChngd,
        svcTlsBgpADPWTempBindSHG,
        svcTlsBgpADPWTempBindRTTblLC,
        svcTlsBgpADPWTempBindRTRowStat
    }
    STATUS      current
    DESCRIPTION
        "The  group  of objects supporting SDP BGP feature
         on Nokia SROS series systems."
    ::= { tmnxSdpGroups 114 }

tmnxSdpL2V6v0Group               OBJECT-GROUP
    OBJECTS     {
        sdpCreationOrigin,
        sdpBindCreationOrigin,
        svcL2RteTableLastChanged,
        svcL2RteSdpBindId,
        svcL2RtePwTemplateId,
        svcL2RteError,
        svcL2RteLastErrorTime
    }
    STATUS      current
    DESCRIPTION
        "The  group  of objects supporting SDP L2 Route feature
         on Nokia SROS series systems."
    ::= { tmnxSdpGroups 115 }

tmnxSdpAutoBindV6v1Group         OBJECT-GROUP
    OBJECTS     {
        pwTemplateTableLastChanged,
        pwTemplateRowStatus,
        pwTemplateLastChanged,
        pwTemplateVcType,
        pwTemplateAccountingPolicyId,
        pwTemplateCollectAcctStats,
        pwTemplateMacLearning,
        pwTemplateMacAgeing,
        pwTemplateDiscardUnknownSource,
        pwTemplateLimitMacMove,
        pwTemplateMacPinning,
        pwTemplateMacAddressLimit,
        pwTemplateShgName,
        pwTemplateShgDescription,
        pwTemplateShgRestProtSrcMac,
        pwTemplateShgRestUnprotDstMac,
        pwTemplateEgressMacFilterId,
        pwTemplateEgressIpFilterId,
        pwTemplateEgressIpv6FilterId,
        pwTemplateIngressMacFilterId,
        pwTemplateIngressIpFilterId,
        pwTemplateIngressIpv6FilterId,
        pwTemplateIgmpFastLeave,
        pwTemplateIgmpImportPlcy,
        pwTemplateIgmpLastMembIntvl,
        pwTemplateIgmpMaxNbrGrps,
        pwTemplateIgmpGenQueryIntvl,
        pwTemplateIgmpQueryRespIntvl,
        pwTemplateIgmpRobustCount,
        pwTemplateIgmpSendQueries,
        pwTemplateIgmpVersion,
        pwTemplateIgmpSnpgGrpSrcTblLC,
        pwTemplateIgmpSnpgRowStatus,
        pwTemplateIgmpSnpgLastChngd,
        pwTemplateMfibAllowedMdaTblLC,
        pwTemplateMfibMdaRowStatus,
        pwTemplateUseProvisionedSdp,
        pwTemplateVlanVcTag,
        sdpAutoBindBgpInfoTableLC,
        sdpAutoBindBgpInfoTemplateId,
        sdpAutoBindBgpInfoAGI,
        sdpAutoBindBgpInfoSAII,
        sdpAutoBindBgpInfoTAII
    }
    STATUS      obsolete
    DESCRIPTION
        "The  group  of objects supporting SDP auto-bind feature
         on Nokia SROS series systems."
    ::= { tmnxSdpGroups 116 }

tmnxSdpAutoBindV7v0Group         OBJECT-GROUP
    OBJECTS     {
        pwTemplateTableLastChanged,
        pwTemplateRowStatus,
        pwTemplateLastChanged,
        pwTemplateVcType,
        pwTemplateAccountingPolicyId,
        pwTemplateCollectAcctStats,
        pwTemplateMacLearning,
        pwTemplateMacAgeing,
        pwTemplateDiscardUnknownSource,
        pwTemplateLimitMacMove,
        pwTemplateMacPinning,
        pwTemplateMacAddressLimit,
        pwTemplateShgName,
        pwTemplateShgDescription,
        pwTemplateShgRestProtSrcMac,
        pwTemplateShgRestUnprotDstMac,
        pwTemplateEgressMacFilterId,
        pwTemplateEgressIpFilterId,
        pwTemplateEgressIpv6FilterId,
        pwTemplateIngressMacFilterId,
        pwTemplateIngressIpFilterId,
        pwTemplateIngressIpv6FilterId,
        pwTemplateIgmpFastLeave,
        pwTemplateIgmpImportPlcy,
        pwTemplateIgmpLastMembIntvl,
        pwTemplateIgmpMaxNbrGrps,
        pwTemplateIgmpGenQueryIntvl,
        pwTemplateIgmpQueryRespIntvl,
        pwTemplateIgmpRobustCount,
        pwTemplateIgmpSendQueries,
        pwTemplateIgmpVersion,
        pwTemplateForceVlanVcForwarding,
        pwTemplateIgmpSnpgGrpSrcTblLC,
        pwTemplateIgmpSnpgRowStatus,
        pwTemplateIgmpSnpgLastChngd,
        pwTemplateMfibAllowedMdaTblLC,
        pwTemplateMfibMdaRowStatus,
        pwTemplateUseProvisionedSdp,
        pwTemplateVlanVcTag,
        sdpAutoBindBgpInfoTableLC,
        sdpAutoBindBgpInfoTemplateId,
        sdpAutoBindBgpInfoAGI,
        sdpAutoBindBgpInfoSAII,
        sdpAutoBindBgpInfoTAII
    }
    STATUS      current
    DESCRIPTION
        "The  group  of objects supporting SDP auto-bind feature
         on Nokia SROS series systems."
    ::= { tmnxSdpGroups 117 }

tmnxSdpBindIpipeV7v0Group        OBJECT-GROUP
    OBJECTS     {
        sdpBindIpipeCeInetAddressType,
        sdpBindIpipeCeInetAddress,
        sdpBindIpipePeerCeInetAddrType,
        sdpBindIpipePeerCeInetAddr
    }
    STATUS      obsolete
    DESCRIPTION
        "The  group  of objects supporting SDP Bind Ipipe feature
         on Nokia SROS series systems."
    ::= { tmnxSdpGroups 118 }

tmnxSdpL2V7v0Group               OBJECT-GROUP
    OBJECTS     {
        sdpEnforceDiffServLspFc
    }
    STATUS      current
    DESCRIPTION
        "The  group  of objects supporting 'DiffServ' TE feature for SDP
         on Nokia SROS series systems."
    ::= { tmnxSdpGroups 119 }

tmnxSdpEvalPwTempV7v0Group       OBJECT-GROUP
    OBJECTS     {
        svcApplyEvalPwTemplateAction,
        svcApplyEvalPwTemplateErrorMsg,
        svcApplyEvalPwTemplateId,
        svcApplyEvalPwTemplateSuccess,
        svcApplyEvalPwTemplateSvcId,
        svcApplyEvalPwTemplateTime
    }
    STATUS      current
    DESCRIPTION
        "The  group  of objects supporting evaluating pseudowite template
         on Nokia SROS series systems in release 7.0."
    ::= { tmnxSdpGroups 120 }

tmnxSdpLdpBackupV8v0Group        OBJECT-GROUP
    OBJECTS     {
        sdpMixedLspModeEnabled,
        sdpLspRevertTime,
        sdpLspRevertTimeCountDown,
        sdpLdpLspId,
        sdpLdpActive
    }
    STATUS      obsolete
    DESCRIPTION
        "The  group  of objects supporting LDP backup feature for SDP
         on Nokia SROS series systems."
    ::= { tmnxSdpGroups 121 }

tmnxSdpPbbGroup                  OBJECT-GROUP
    OBJECTS     {
        sdpBindPbbRowStatus,
        sdpBindPbbLastMgmtChange,
        sdpBindPbbIgmpSnpgMRouter
    }
    STATUS      current
    DESCRIPTION
        "The  group  of objects supporting
         Provider Backbone Bridging (PBB/IEEE 802.1ah) feature for SDP
         on Nokia SROS series systems."
    ::= { tmnxSdpGroups 122 }

tmnxSdpBindGenGroup              OBJECT-GROUP
    OBJECTS     {
        sdpBindDescription
    }
    STATUS      current
    DESCRIPTION
        "The  group  of objects supporting additional SDP bind features
         on Nokia SROS series systems."
    ::= { tmnxSdpGroups 123 }

tmnxSdpBindTlsMrpV8v0Group       OBJECT-GROUP
    OBJECTS     {
        sdpBindTlsMrpTableLastChanged,
        sdpBindTlsMrpLastChngd,
        sdpBindTlsMrpJoinTime,
        sdpBindTlsMrpLeaveTime,
        sdpBindTlsMrpLeaveAllTime,
        sdpBindTlsMrpPeriodicTime,
        sdpBindTlsMrpPeriodicEnabled,
        sdpBindTlsMrpRxPdus,
        sdpBindTlsMrpDroppedPdus,
        sdpBindTlsMrpTxPdus,
        sdpBindTlsMrpRxNewEvent,
        sdpBindTlsMrpRxJoinInEvent,
        sdpBindTlsMrpRxInEvent,
        sdpBindTlsMrpRxJoinEmptyEvent,
        sdpBindTlsMrpRxEmptyEvent,
        sdpBindTlsMrpRxLeaveEvent,
        sdpBindTlsMrpTxNewEvent,
        sdpBindTlsMrpTxJoinInEvent,
        sdpBindTlsMrpTxInEvent,
        sdpBindTlsMrpTxJoinEmptyEvent,
        sdpBindTlsMrpTxEmptyEvent,
        sdpBindTlsMrpTxLeaveEvent,
        sdpBindTlsMmrpDeclared,
        sdpBindTlsMmrpRegistered,
        sdpBindTlsMmrpEndStation,
        sdpBindTlsMrpPolicy
    }
    STATUS      current
    DESCRIPTION
        "The  group  of objects supporting SDP MRP feature
         on Nokia SROS series systems."
    ::= { tmnxSdpGroups 124 }

tmnxSdpV8v0Group                 OBJECT-GROUP
    OBJECTS     {
        sdpNetDomainName,
        sdpEgressIfsNetDomainConsistent,
        sdpBgpTunnelEnabled,
        sdpBgpTunnelLspId,
        sdpTunnelFarEndIpAddress
    }
    STATUS      obsolete
    DESCRIPTION
        "The  group  of objects supporting SDP feature on Nokia SROS
         series systems in the 8.0 release."
    ::= { tmnxSdpGroups 125 }

tmnxSdpBindV8v0Group             OBJECT-GROUP
    OBJECTS     {
        sdpBindSiteName,
        sdpBindHashLabel,
        sdpBindHashLabelSignalCapability,
        sdpBindIsaAaApplicationProfile,
        sdpBindFPropBMacAddrTblLastChgd,
        sdpBindFPropBMacAddrRowStatus,
        sdpBindPwStatusSignaling
    }
    STATUS      current
    DESCRIPTION
        "The  group  of objects supporting SDP Bind feature on Nokia
         SROS series systems in the 8.0 release."
    ::= { tmnxSdpGroups 126 }

tmnxSdpAutoBindV8v0Group         OBJECT-GROUP
    OBJECTS     {
        pwTemplateHashLabel,
        pwTemplateControlWord,
        pwTemplateHashLabelSignalCap,
        sdpAutoBindBgpVplsTableLC,
        sdpAutoBindBgpVplsTemplateId
    }
    STATUS      current
    DESCRIPTION
        "The  group  of objects supporting SDP auto-bind feature
         on Nokia SROS series systems in the 8.0 release."
    ::= { tmnxSdpGroups 127 }

tmnxSdpBindIpipeV8v0Group        OBJECT-GROUP
    OBJECTS     {
        sdpBindIpipeCeInetAddressType,
        sdpBindIpipeCeInetAddress,
        sdpBindIpipePeerCeInetAddrType,
        sdpBindIpipePeerCeInetAddr,
        sdpBindIpipePeerIpv6Capability,
        sdpBindIpipePeerLLCeInetAddr,
        sdpBindIpipePeerGlobalCeInetAddr
    }
    STATUS      current
    DESCRIPTION
        "The  group  of objects supporting SDP Bind Ipipe feature
         on Nokia SROS series systems."
    ::= { tmnxSdpGroups 128 }

tmnxSdpBindV9v0Group             OBJECT-GROUP
    OBJECTS     {
        sdpBindIngressFlowspec
    }
    STATUS      current
    DESCRIPTION
        "The group of objects supporting SDP Bind feature on Nokia SROS series
         systems in the 9.0 release."
    ::= { tmnxSdpGroups 129 }

tmnxSdpBindCpmProtGroup          OBJECT-GROUP
    OBJECTS     {
        sdpBindCpmProtPolicyId,
        sdpBindCpmProtMonitorMac,
        sdpBindCpmProtEthCfmMonitorFlags
    }
    STATUS      current
    DESCRIPTION
        "The group of objects supporting management of SDP binding CPM
         protection capabilities on release 8.0 R5 of Nokia SROS series
         systems."
    ::= { tmnxSdpGroups 130 }

tmnxSdpBindBsxV9v0Group          OBJECT-GROUP
    OBJECTS     {
        sdpBindTransitIpPolicyId,
        sdpBindTransitPrefixPolicyId
    }
    STATUS      current
    DESCRIPTION
        "The  group  of objects supporting SDP Bind BSX capabilities on
         Nokia SROS series systems in the 9.0 release."
    ::= { tmnxSdpGroups 131 }

tmnxSdpBindTlsV8v0Group          OBJECT-GROUP
    OBJECTS     {
        sdpBindTlsInTcBitBpdus,
        sdpBindTlsOutTcBitBpdus
    }
    STATUS      current
    DESCRIPTION
        "The  group  of objects on Nokia SROS series systems
         supporting SDP Bind TLS feature, added in release 8.0."
    ::= { tmnxSdpGroups 132 }

tmnxSdpV9v0Group                 OBJECT-GROUP
    OBJECTS     {
        sdpAtBndBgp129Type2SaiiAcId,
        sdpAtBndBgp129Type2SaiiGlobalId,
        sdpAtBndBgp129Type2SaiiPrefix,
        sdpAtBndBgp129Type2TableLC,
        sdpAtBndBgp129Type2TaiiAcId,
        sdpAtBndBgp129Type2TaiiGlobalId,
        sdpAtBndBgp129Type2TaiiPrefix,
        sdpAtBndBgp129Type2TemplateId,
        svcTlsBgpADPWTempBindOperGrp,
        sdpBindOperGrp,
        sdpBindMonitorOperGrp,
        sdpBindOperHashLabel
    }
    STATUS      current
    DESCRIPTION
        "The  group  of objects on Nokia SROS series systems
         supporting SDP feature, added in release 9.0."
    ::= { tmnxSdpGroups 133 }

tmnxSdpMixedLspModeV9v0Group     OBJECT-GROUP
    OBJECTS     {
        sdpMixedLspModeEnabled,
        sdpLspRevertTime,
        sdpLspRevertTimeCountDown,
        sdpLdpLspId,
        sdpActiveLspType
    }
    STATUS      current
    DESCRIPTION
        "The  group  of objects supporting Mixed LSP Mode feature for SDP
         on Nokia SROS series systems."
    ::= { tmnxSdpGroups 134 }

tmnxSdpSpbGroup                  OBJECT-GROUP
    OBJECTS     {
        sdpBindTlsSpbAdminState,
        sdpBindTlsSpbIfIndex,
        sdpBindTlsSpbLastChgd,
        sdpBindTlsSpbRowStatus,
        sdpBindTlsSpbTblLastChanged
    }
    STATUS      current
    DESCRIPTION
        "The  group  of objects supporting Shortest Path Bridging feature for
         SDP on Nokia SROS series systems."
    ::= { tmnxSdpGroups 135 }

tmnxSdpBindBsxV10v0Group         OBJECT-GROUP
    OBJECTS     {
        sdpBindAarpId,
        sdpBindAarpServRefType
    }
    STATUS      current
    DESCRIPTION
        "The  group  of objects supporting SDP Bind BSX capabilities on
         Nokia SROS series systems in the 10.0 release."
    ::= { tmnxSdpGroups 136 }

tmnxSdpPwPortGroup               OBJECT-GROUP
    OBJECTS     {
        sdpPwPortAdminStatus,
        sdpPwPortEncapType,
        sdpPwPortLastChgd,
        sdpPwPortRowStatus,
        sdpPwPortTblLastChanged,
        sdpPwPortVcId,
        sdpPwPortOperStatus,
        sdpPwPortOperFlags,
        sdpPwPortVcType,
        sdpPwPortVlanVcTag,
        sdpPwPortEgrShapDefIntDestId,
        sdpPwPortEgrShapVPort,
        sdpBindingPort
    }
    STATUS      obsolete
    DESCRIPTION
        "The group of objects supporting SDP MPLS pseudo-wire port support on
         Nokia SROS series systems in the 10.0 release."
    ::= { tmnxSdpGroups 137 }

tmnxSdpV10v0Group                OBJECT-GROUP
    OBJECTS     {
        sdpBindPwLocalStatusBits,
        pwTemplateAutoLearnMacProtect,
        pwTemplateRestProtSrcMac,
        pwTemplateRestProtSrcMacAction,
        pwTemplateShgAutoLearnMacProtect,
        pwTemplateShgRestProtSrcMacAct,
        sdpBindTlsAutoLearnMacProtect,
        sdpBindTlsRestProtSrcMac,
        sdpBindTlsRestProtSrcMacAction,
        sdpBindMeshTlsAutoLearnMacProt,
        sdpBindMeshTlsRestProtSrcMac,
        sdpBindMeshTlsRestProtSrcMacAct
    }
    STATUS      current
    DESCRIPTION
        "The  group  of objects supporting SDP general capabilities on
         Nokia SROS series systems in the 10.0 release."
    ::= { tmnxSdpGroups 138 }

tmnxSdpBindDhcpV11v0Group        OBJECT-GROUP
    OBJECTS     {
        sdpBindDhcp6Description,
        sdpBindDhcp6Snoop,
        sdpBindDhcpStatsClntProxUDBPckts
    }
    STATUS      current
    DESCRIPTION
        "The  group  of objects supporting SDP Bind DHCP feature
         on Nokia SROS series systems added in 11.0 release."
    ::= { tmnxSdpGroups 139 }

tmnxSdpBindDhcpV13v0Group        OBJECT-GROUP
    OBJECTS     {
        sdpBindDhcpStatsClntProxNqPckts
    }
    STATUS      current
    DESCRIPTION
        "The  group  of objects supporting SDP Bind DHCP feature
         added in 13.0 release of Nokia SROS series systems."
    ::= { tmnxSdpGroups 140 }

tmnxSdpNotifyObjsV6v0Group       OBJECT-GROUP
    OBJECTS     {
        sdpNotifySdpId,
        sdpMaxBookableBandwidth,
        sdpBookedBandwidth,
        dynamicSdpStatus,
        dynamicSdpOrigin,
        dynamicSdpCreationError,
        dynamicSdpBindCreationError
    }
    STATUS      obsolete
    DESCRIPTION
        "The  group  of objects supporting SDP notification objects
         on Nokia SROS series systems."
    ::= { tmnxSdpGroups 200 }

tmnxSdpNotifyObjsV7v0Group       OBJECT-GROUP
    OBJECTS     {
        sdpNotifySdpId,
        sdpMaxBookableBandwidth,
        sdpBookedBandwidth,
        dynamicSdpStatus,
        dynamicSdpOrigin,
        dynamicSdpCreationError,
        dynamicSdpBindCreationError,
        sdpBindNotifyMacAddr
    }
    STATUS      current
    DESCRIPTION
        "The group of objects supporting SDP notification objects on Nokia SROS
         series systems."
    ::= { tmnxSdpGroups 201 }

tmnxSdpNotifyObjsV8v0Group       OBJECT-GROUP
    OBJECTS     {
        sdpEgIfNetDomainInconsCount
    }
    STATUS      current
    DESCRIPTION
        "The group of objects supporting SDP notification objects on Nokia SROS
         series systems 8.0 release."
    ::= { tmnxSdpGroups 202 }

tmnxSdpBgpVplsV8v0Group          OBJECT-GROUP
    OBJECTS     {
        svcL2BgpVplsRteControlWord,
        svcL2BgpVplsRteError,
        svcL2BgpVplsRteLastErrorTime,
        svcL2BgpVplsRtePathMtu,
        svcL2BgpVplsRtePwTemplateId,
        svcL2BgpVplsRteSdpBindId,
        svcL2BgpVplsRteSeqDelivery,
        svcL2BgpVplsRteState,
        svcL2BgpVplsRteDF
    }
    STATUS      current
    DESCRIPTION
        "The group of objects supporting SDP specific BGP VPLS feature on Nokia
         SROS series systems."
    ::= { tmnxSdpGroups 203 }

tmnxSdpL2V8v0Group               OBJECT-GROUP
    OBJECTS     {
        svcL2RteStatus,
        svcL2BgpVplsRteStatus
    }
    STATUS      current
    DESCRIPTION
        "The group of objects supporting SDP specific L2 feature in 8.0 on
         Nokia SROS series systems."
    ::= { tmnxSdpGroups 204 }

tmnxSdpPwV8v0Group               OBJECT-GROUP
    OBJECTS     {
        sdpBindStandbySigSlave
    }
    STATUS      current
    DESCRIPTION
        "The group of objects supporting SDP specific pseudo-wire feature in
         8.0 on Nokia SROS series systems."
    ::= { tmnxSdpGroups 205 }

tmnxSdpBindEthCfmGroup           OBJECT-GROUP
    OBJECTS     {
        sdpBindEthCfmTableLastChanged,
        sdpBindEthCfmRowLastChanged,
        sdpBindEthCfmVMepFilter
    }
    STATUS      current
    DESCRIPTION
        "The group of objects supporting Ethernet Connectivity Fault Management
         (CFM) for the SDP-BIND feature on Nokia SROS series systems for
         Release 9.0."
    ::= { tmnxSdpGroups 206 }

tmnxSdpNotifyObjsV9v0Group       OBJECT-GROUP
    OBJECTS     {
        sdpMSPwPeId
    }
    STATUS      current
    DESCRIPTION
        "The group of objects supporting SDP notification objects on Nokia SROS
         series systems 9.0 release."
    ::= { tmnxSdpGroups 207 }

tmnxSdpBindIpipeNotifyObjsGroup  OBJECT-GROUP
    OBJECTS     {
        sdpBindIpipeCeIpAddrType,
        sdpBindIpipeCeIpAddress
    }
    STATUS      current
    DESCRIPTION
        "The group of objects supporting Ipipe SDP notification objects on
         Nokia SROS series systems."
    ::= { tmnxSdpGroups 208 }

tmnxSdpObsoletedObjsV6v1Group    OBJECT-GROUP
    OBJECTS     {
        pwTemplateIgmpMcacPolicyName,
        pwTemplateIgmpMcacPrRsvMndBW,
        pwTemplateIgmpMcacUnconstBW
    }
    STATUS      current
    DESCRIPTION
        "The group of obsolete objects for the service SDPs on Nokia SROS
         series systems."
    ::= { tmnxSdpGroups 300 }

tmnxSdpObsoletedObjsV9v0Group    OBJECT-GROUP
    OBJECTS     {
        sdpLdpActive
    }
    STATUS      current
    DESCRIPTION
        "The group of obsolete objects for the service SDPs on Nokia SROS
         series systems."
    ::= { tmnxSdpGroups 301 }

tmnxSdpBindQGrpObjsV10v0Group    OBJECT-GROUP
    OBJECTS     {
        sdpBindIngressQoSNetworkPlcyId,
        sdpBindEgressQoSNetworkPlcyId,
        sdpBindIngressQoSFpRedirectQGrp,
        sdpBindEgressQoSPortRedirectQGrp,
        sdpBindIngressQoSInstanceId,
        sdpBindEgressQoSInstanceId,
        pwTemplateIngQoSNetworkPlcyId,
        pwTemplateEgrQoSNetworkPlcyId,
        pwTemplateIngQoSFpRedirectQGrp,
        pwTemplateEgrQoSPortRedirectQGrp,
        pwTemplateIngQoSInstanceId,
        pwTemplateEgrQoSInstanceId
    }
    STATUS      current
    DESCRIPTION
        "The group of objects supporting SDP binding queue group objects on
         Nokia SROS series systems 10.0 release."
    ::= { tmnxSdpGroups 302 }

tmnxSdpNotifyV6v0Group           NOTIFICATION-GROUP
    NOTIFICATIONS {
        unacknowledgedTCN,
        tmnxSvcTopoChgSdpBindMajorState,
        tmnxSvcNewRootSdpBind,
        tmnxSvcTopoChgSdpBindState,
        tmnxSvcSdpBindRcvdTCN,
        tmnxSvcSdpBindRcvdHigherBriPrio,
        tmnxSvcSdpBindEncapPVST,
        tmnxSvcSdpBindEncapDot1d,
        tmnxSvcSdpActiveProtocolChange,
        tmnxStpMeshNotInMstRegion,
        tmnxSdpBndStpExcepCondStateChng,
        sdpStatusChanged,
        sdpBindStatusChanged,
        sdpTlsMacAddrLimitAlarmRaised,
        sdpTlsMacAddrLimitAlarmCleared,
        sdpBindDHCPLeaseEntriesExceeded,
        sdpBindDHCPLseStateOverride,
        sdpBindDHCPLseStatePopulateErr,
        sdpBindDHCPSuspiciousPcktRcvd,
        sdpBindPwPeerStatusBitsChanged,
        sdpBindTlsMacMoveExceeded,
        sdpBindPwPeerFaultAddrChanged,
        sdpBindDHCPProxyServerError,
        sdpBindSdpStateChangeProcessed,
        sdpBindDHCPLseStateMobilityErr,
        sdpBandwidthOverbooked,
        sdpBindInsufficientBandwidth,
        dynamicSdpConfigChanged,
        dynamicSdpBindConfigChanged,
        dynamicSdpCreationFailed,
        dynamicSdpBindCreationFailed
    }
    STATUS      current
    DESCRIPTION
        "The group of SDP notifications on Nokia SROS series systems."
    ::= { tmnxSdpGroups 400 }

tmnxSdpObsoletedNotifyV6v0Group  NOTIFICATION-GROUP
    NOTIFICATIONS {
        sdpCreated,
        sdpDeleted,
        sdpBindCreated,
        sdpBindDeleted,
        sdpTlsDHCPSuspiciousPcktRcvd,
        sdpBindDHCPCoAError,
        sdpBindDHCPSubAuthError
    }
    STATUS      current
    DESCRIPTION
        "The  group  of obsoleted SDP objects on Nokia SROS series
         systems."
    ::= { tmnxSdpGroups 401 }

tmnxSdpNotifyV8v0Group           NOTIFICATION-GROUP
    NOTIFICATIONS {
        sdpEgrIfsNetDomInconsCntChanged
    }
    STATUS      current
    DESCRIPTION
        "The group of SDP notifications on Nokia SROS series systems 8.0
         release."
    ::= { tmnxSdpGroups 402 }

tmnxSdpBindIpipeNotifyGroup      NOTIFICATION-GROUP
    NOTIFICATIONS {
        sdpBindIpipeCeIpAddressChange
    }
    STATUS      current
    DESCRIPTION
        "The group of Ipipe SDP notifications on Nokia SROS series systems."
    ::= { tmnxSdpGroups 403 }

tmnxSdpNotifyV10v0Group          NOTIFICATION-GROUP
    NOTIFICATIONS {
        sdpBindPwLocalStatusBitsChanged,
        sdpBindReceivedProtSrcMac
    }
    STATUS      current
    DESCRIPTION
        "The group of SDP notifications on Nokia SROS series systems 10.0
         release."
    ::= { tmnxSdpGroups 404 }

tmnxSdpNotifyV11v0Group          NOTIFICATION-GROUP
    NOTIFICATIONS {
        sdpBindTlsMacMoveExceedNonBlock
    }
    STATUS      current
    DESCRIPTION
        "The group of SDP notifications on Nokia SROS series systems 11.0
         release."
    ::= { tmnxSdpGroups 405 }

tmnxSdpGrpGroup                  OBJECT-GROUP
    OBJECTS     {
        pwTempExcSdpGrpLastChanged,
        pwTempExcSdpGrpRowStatus,
        pwTempExcSdpGrpTableLastChanged,
        pwTempIncSdpGrpLastChanged,
        pwTempIncSdpGrpRowStatus,
        pwTempIncSdpGrpTableLastChanged,
        sdpGrpLastChange,
        sdpGrpRowStatus,
        sdpGrpTblLastChanged,
        sdpGrpValue,
        sdpSdpGrpLastChange,
        sdpSdpGrpRowStatus,
        sdpSdpGrpTblLastChanged
    }
    STATUS      current
    DESCRIPTION
        "The group of objects supporting SDP supporting SDP group on Nokia SROS
         series systems."
    ::= { tmnxSdpGroups 500 }

tmnxSdpBindBlockOnPeerFaultGroup OBJECT-GROUP
    OBJECTS     {
        pwTemplateBlockOnPeerFault,
        sdpBindBlockOnPeerFault
    }
    STATUS      current
    DESCRIPTION
        "The group of objects supporting specific SDP feature on Nokia SROS
         series systems."
    ::= { tmnxSdpGroups 501 }

tmnxSdpBindFlowSpecGroup         OBJECT-GROUP
    OBJECTS     {
        sdpBindIngressFlowspec,
        sdpBindIngressIPv6Flowspec
    }
    STATUS      current
    DESCRIPTION
        "The group of objects supporting specific SDP feature on Nokia SROS
         series systems."
    ::= { tmnxSdpGroups 502 }

tmnxSdpBindPwPortGroup           OBJECT-GROUP
    OBJECTS     {
        sdpFarEndNodeId,
        sdpFarEndGlobalId,
        sdpBindPwPathRowStatus,
        sdpBindPwPathAgi,
        sdpBindPwPathLastChanged,
        sdpBindPwPathSaiiAcId,
        sdpBindPwPathSaiiGlobalId,
        sdpBindPwPathSaiiNodeId,
        sdpBindPwPathTableLastChanged,
        sdpBindPwPathTaiiAcId,
        sdpBindPwPathTaiiGlobalId,
        sdpBindPwPathTaiiNodeId
    }
    STATUS      current
    DESCRIPTION
        "The group of objects supporting specific SDP feature on Nokia SROS
         series systems."
    ::= { tmnxSdpGroups 503 }

tmnxSdpVllBgpV11v0Group          OBJECT-GROUP
    OBJECTS     {
        sdpAutoBindBgpVpwsTemplateId,
        svcL2BgpVpwsRteSdpBindId,
        svcL2BgpVpwsRtePwTemplateId,
        svcL2BgpVpwsRteError,
        svcL2BgpVpwsRteLastErrorTime,
        svcL2BgpVpwsRteControlWord,
        svcL2BgpVpwsRtePathMtu,
        svcL2BgpVpwsRteState,
        svcL2BgpVpwsRteSeqDelivery,
        svcL2BgpVpwsRteStatus,
        svcL2BgpVpwsRteCsv,
        svcL2BgpVpwsRtePreference,
        svcL2BgpVpwsRteTxStatus,
        svcVllBgpADPWTempBindRTTblLC,
        svcVllBgpADPWTempBindRTRowStat,
        svcVllBgpADPWTempBindTblLC,
        svcVllBgpADPWTempBindRowStatus,
        svcVllBgpADPWTempBindLastChngd,
        svcVllBgpADPWTempBindEndPt
    }
    STATUS      current
    DESCRIPTION
        "The  group  of objects supporting SDP BGP feature
         on Nokia SROS series systems."
    ::= { tmnxSdpGroups 504 }

tmnxSdpL2tpv3Group               OBJECT-GROUP
    OBJECTS     {
        sdpBindMirrorRemoteSource,
        sdpFarEndInetAddressType,
        sdpFarEndInetAddress,
        sdpLocalEndInetAddressType,
        sdpLocalEndInetAddress,
        sdpBindL2tpv3SessMismatch,
        sdpBindL2tpv3SessMismatchLstClrd,
        sdpBindL2tpv3IngressCookie,
        sdpBindL2tpv3EgressCookie
    }
    STATUS      current
    DESCRIPTION
        "The  group of objects supporting SDP L2TPV3 feature
         on Nokia SROS series systems."
    ::= { tmnxSdpGroups 505 }

tmnxSdpBindSpbV11v0Group         OBJECT-GROUP
    OBJECTS     {
        sdpBindTlsStaticIsidStatus,
        sdpBindTlsStaticIsidRngRowStatus,
        sdpBindTlsStaticIsidRngLastChgd,
        sdpBindTlsStaticIsidRngLow,
        sdpBindTlsStaticIsidRngHigh
    }
    STATUS      current
    DESCRIPTION
        "The  group of objects supporting SDP SPB feature
         on Nokia SROS series systems in 11.0 release."
    ::= { tmnxSdpGroups 506 }

tmnxSdpBindEthLoopbackV11v0Group OBJECT-GROUP
    OBJECTS     {
        sdpBindEthLoopbackRowStatus,
        sdpBindEthLoopbackMode,
        sdpBindEthLoopbackMacSwap,
        sdpBindEthLoopbackMacSwapAddr,
        sdpBindEthLoopbackMacSwapAddrAll
    }
    STATUS      current
    DESCRIPTION
        "The group of objects supporting management of the SDP Binding Ethernet
         Loopback feature on Nokia SROS series systems in release 11.0."
    ::= { tmnxSdpGroups 507 }

tmnxSdpBindEthLpbkNtfyV11v0Group NOTIFICATION-GROUP
    NOTIFICATIONS {
        sdpBindEthLoopbackStarted,
        sdpBindEthLoopbackStopped
    }
    STATUS      current
    DESCRIPTION
        "The group of notifications supporting management of the SDP Binding
         Ethernet Loopback feature on Nokia SROS series systems in release
         11.0."
    ::= { tmnxSdpGroups 508 }

tmnxSdpPwSecShaperGroup          OBJECT-GROUP
    OBJECTS     {
        sdpPwPortEgrShapSapSecShaper
    }
    STATUS      current
    DESCRIPTION
        "The  group of objects supporting SDP PW port feature
         on Nokia SROS series systems in release 11.0."
    ::= { tmnxSdpGroups 509 }

tmnxSdpPwPortV11v0Group          OBJECT-GROUP
    OBJECTS     {
        sdpPwPortAdminStatus,
        sdpPwPortLastChgd,
        sdpPwPortRowStatus,
        sdpPwPortTblLastChanged,
        sdpPwPortVcId,
        sdpPwPortOperStatus,
        sdpPwPortOperFlags,
        sdpPwPortVcType,
        sdpPwPortVlanVcTag,
        sdpPwPortEgrShapDefIntDestId,
        sdpPwPortEgrShapVPort,
        sdpBindingPort
    }
    STATUS      current
    DESCRIPTION
        "The group of objects supporting SDP MPLS pseudo-wire port support on
         Nokia SROS series systems in the 10.0 release."
    ::= { tmnxSdpGroups 510 }

tmnxSdpObsoletedObjsV11v0Group   OBJECT-GROUP
    OBJECTS     {
        sdpPwPortEncapType
    }
    STATUS      current
    DESCRIPTION
        "The group of obsoleted objects for the service SDPs on Nokia SROS
         series systems in the 11.0 release."
    ::= { tmnxSdpGroups 511 }

tmnxSdpBindCtrlChanGroup         OBJECT-GROUP
    OBJECTS     {
        sdpBindCtrlChanPwStatus,
        sdpBindCtrlChanPwLastChanged,
        sdpBindCtrlChanPwRefreshTimer,
        sdpBindCtrlChanPwPeerExpired,
        sdpBindCtrlChanPwTableLastChgd
    }
    STATUS      current
    DESCRIPTION
        "The group of objects supporting specific SDP pseudo-wire control
         channel feature on Nokia SROS series systems."
    ::= { tmnxSdpGroups 512 }

sdpBindTlsFdbMacStatsGroup       OBJECT-GROUP
    OBJECTS     {
        sdpBindTlsFdbMacStatsNumEntries
    }
    STATUS      current
    DESCRIPTION
        "The group of additional objects for the management of MAC statistics
         per FDB type on SDP Bindings for release 11.0 of the SROS series
         systems."
    ::= { tmnxSdpGroups 514 }

sdpBindTlsEtreeGroup             OBJECT-GROUP
    OBJECTS     {
        sdpBindEtreeRootLeafTag,
        sdpBindEtreeLeafAc
    }
    STATUS      current
    DESCRIPTION
        "The group of objects supporting ETree feature for SDPs on Nokia SROS
         series systems."
    ::= { tmnxSdpGroups 515 }

tmnxSdpBindCpmProtV12v0Group     OBJECT-GROUP
    OBJECTS     {
        sdpBindCpmProtMonitorIP
    }
    STATUS      current
    DESCRIPTION
        "The group of objects supporting management of CPM Protection on SDP
         Bindings for release 12.0 of the SROS series systems."
    ::= { tmnxSdpGroups 516 }

tmnxSdpBindCtrlChanReqGroup      OBJECT-GROUP
    OBJECTS     {
        sdpBindCtrlChanPwRequestTimer,
        sdpBindCtrlChanPwRetryTimer,
        sdpBindCtrlChanPwTimeoutMult
    }
    STATUS      current
    DESCRIPTION
        "The group of objects supporting specific SDP pseudo-wire control
         channel request-timer feature on Nokia SROS series systems."
    ::= { tmnxSdpGroups 517 }

tmnxSdpBindCtrlChanAckGroup      OBJECT-GROUP
    OBJECTS     {
        sdpBindCtrlChanPwAck
    }
    STATUS      current
    DESCRIPTION
        "The group of objects supporting specific SDP pseudo-wire control
         channel acknowledgement feature on Nokia SROS series systems."
    ::= { tmnxSdpGroups 518 }

tmnxSdpPBBEpipePWRedV12v0Group   OBJECT-GROUP
    OBJECTS     {
        sdpSourceBMacLSB,
        sdpControlPWVCId,
        sdpBindUseSdpBMac,
        sdpControlPWIsActive
    }
    STATUS      current
    DESCRIPTION
        "The group of objects supporting PBB epipe pseudo-wire redundancy
         feature on Nokia SROS series systems for release 12.0."
    ::= { tmnxSdpGroups 519 }

tmnxSdpPbbEpipeNotifyObjsGroup   OBJECT-GROUP
    OBJECTS     {
        sdpPbbActvPwWithNonActvCtrlPw
    }
    STATUS      current
    DESCRIPTION
        "The  group  of objects supporting PBB epipe pseudo-wire redundancy
         SDP notification objects on Nokia SROS series systems."
    ::= { tmnxSdpGroups 520 }

tmnxSdpPbbEpipeNotifV12v0Group   NOTIFICATION-GROUP
    NOTIFICATIONS {
        sdpPbbActvPwWithNonActvCtrlPwChg
    }
    STATUS      current
    DESCRIPTION
        "The group of notifications supporting management of the SDP Binding
         SDP feature on Nokia SROS series systems in release 12.0."
    ::= { tmnxSdpGroups 521 }

tmnxSdpBindEthCfmV12v0Group      OBJECT-GROUP
    OBJECTS     {
        sdpBindEthCfmSquelchIngress,
        sdpBindEthCfmCollectLmmStats
    }
    STATUS      current
    DESCRIPTION
        "The group of additional objects supporting Ethernet Connectivity Fault
         Management (ETH-CFM) for the SDP-BIND feature on Nokia SROS series
         systems for Release 12.0."
    ::= { tmnxSdpGroups 522 }

tmnxSdpV12v0Group                OBJECT-GROUP
    OBJECTS     {
        svcTlsBgpADPWTempBindCreatOrigin,
        sdpNumEntries,
        sdpNextFreeId,
        sdpId,
        sdpRowStatus,
        sdpDelivery,
        sdpFarEndIpAddress,
        sdpLspList,
        sdpDescription,
        sdpLabelSignaling,
        sdpAdminStatus,
        sdpOperStatus,
        sdpOperPathMtu,
        sdpKeepAliveAdminStatus,
        sdpKeepAliveOperStatus,
        sdpKeepAliveHelloTime,
        sdpKeepAliveMaxDropCount,
        sdpKeepAliveHoldDownTime,
        sdpLastMgmtChange,
        sdpKeepAliveNumHelloRequestMessages,
        sdpKeepAliveNumHelloResponseMessages,
        sdpKeepAliveNumLateHelloResponseMessages,
        sdpKeepAliveHelloRequestTimeout,
        sdpLdpEnabled,
        sdpVlanVcEtype,
        sdpAdvertisedVllMtuOverride,
        sdpOperFlags,
        sdpLastStatusChange,
        sdpMvplsMgmtService,
        sdpMvplsMgmtSdpBndId,
        sdpCollectAcctStats,
        sdpAccountingPolicyId,
        sdpClassFwdingEnabled,
        sdpClassFwdingDefaultLsp,
        sdpClassFwdingMcLsp,
        sdpMetric,
        sdpAutoSdp,
        sdpPBBEtype,
        sdpBandwidthBookingFactor,
        sdpOperBandwidth,
        sdpAvailableBandwidth,
        sdpAdminPathMtu,
        sdpKeepAliveHelloMessageLength
    }
    STATUS      obsolete
    DESCRIPTION
        "The  group  of objects supporting SDP base feature
         on Nokia SROS series systems."
    ::= { tmnxSdpGroups 523 }

tmnxSdpObsoletedObjsV12v0Group   OBJECT-GROUP
    OBJECTS     {
        sdpSnmpAllowed
    }
    STATUS      current
    DESCRIPTION
        "The group of obsoleted objects for the service SDPs on Nokia SROS
         series systems in the 12.0 release."
    ::= { tmnxSdpGroups 524 }

tmnxSdpBfdV12v0Group             OBJECT-GROUP
    OBJECTS     {
        svcVllBgpADPWTempBindBfdTemplate,
        svcVllBgpADPWTempBindBfdEnable,
        svcVllBgpADPWTempBindBfdEncap,
        svcTlsBgpADPWTempBindBfdTemplate,
        svcTlsBgpADPWTempBindBfdEnable,
        svcTlsBgpADPWTempBindBfdEncap,
        sdpBindBfdTemplateName,
        sdpBindBfdEnable,
        sdpBindBfdEncap
    }
    STATUS      current
    DESCRIPTION
        "The group of objects for BFD feature for service SDPs on Nokia SROS
         series systems in 12.0 release."
    ::= { tmnxSdpGroups 525 }

tmnxSdpL2tpv3CookieGroup         OBJECT-GROUP
    OBJECTS     {
        sdpBindL2tpv3IngressCookie2
    }
    STATUS      current
    DESCRIPTION
        "The group of objects for L2TP-V3 cookies feature for service SDPs on
         Nokia SROS series systems in 12.0 release."
    ::= { tmnxSdpGroups 526 }

tmnxSdpPwTempBindV12v0Group      OBJECT-GROUP
    OBJECTS     {
        svcTlsBgpADPWTempBindMonOperGrp
    }
    STATUS      current
    DESCRIPTION
        "The group of objects for BFD feature for service SDPs on Nokia SROS
         series systems in 12.0 release."
    ::= { tmnxSdpGroups 527 }

tmnxSdpPbbV12v0Group             OBJECT-GROUP
    OBJECTS     {
        sdpBindPbbMldSnpgMRouter
    }
    STATUS      current
    DESCRIPTION
        "The  group  of objects supporting
         Provider Backbone Bridging (PBB/IEEE 802.1ah) feature for SDP
         on Nokia SROS series systems in 12.0 release."
    ::= { tmnxSdpGroups 528 }

tmnxSdpPwLoopbackGroup           OBJECT-GROUP
    OBJECTS     {
        sdpBindPwLoopbackRowStatus,
        sdpBindPwAdminLockRowStatus,
        sdpBindPwAdminLockTestSvc
    }
    STATUS      current
    DESCRIPTION
        "The group of objects for pseudo-wire feature for service SDPs on Nokia
         SROS series systems."
    ::= { tmnxSdpGroups 529 }

tmnxPwTemplateAugGroup           OBJECT-GROUP
    OBJECTS     {
        pwTemplateAugTableLastChgd,
        pwTemplateAugLastChgd,
        pwTemplateAugStpAutoEdge,
        pwTemplateAugStpRapidStart,
        pwTemplateAugStpAdminPtToPt,
        pwTemplateAugStpPathCost,
        pwTemplateAugStpPriority,
        pwTemplateAugStpRootGuard,
        pwTemplateAugStpAdminStatus,
        pwTemplateAugL2ptTermination,
        pwTemplateAugL2ptProtocols
    }
    STATUS      current
    DESCRIPTION
        "The group of objects for pseudo-wire template feature for services on
         Nokia SROS series systems."
    ::= { tmnxSdpGroups 530 }

tmnxSdpCtrlPwNotifV12v0Group     NOTIFICATION-GROUP
    NOTIFICATIONS {
        sdpControlPwActiveStateChg
    }
    STATUS      current
    DESCRIPTION
        "The group of notifications supporting management of the SDP feature on
         Nokia SROS series systems in release 12.0."
    ::= { tmnxSdpGroups 531 }

tmnxSdpLdpIpv6Group              OBJECT-GROUP
    OBJECTS     {
        sdpTunnelFarEndInetAddressType,
        sdpTunnelFarEndInetAddress
    }
    STATUS      current
    DESCRIPTION
        "The group of objects supporting management of the LDP IPv6 feature for
         SDP on Nokia SROS series systems in release 13.0."
    ::= { tmnxSdpGroups 532 }

tmnxSdpBindV13v0Group            OBJECT-GROUP
    OBJECTS     {
        sdpBindIngressVlanTranslation,
        sdpBindIngressVlanTranslationId
    }
    STATUS      obsolete
    DESCRIPTION
        "The group of objects supporting management of the SDP feature on Nokia
         SROS series systems in release 13.0."
    ::= { tmnxSdpGroups 533 }

tmnxSdpSegRouteGroup             OBJECT-GROUP
    OBJECTS     {
        sdpSegRouteIsIs,
        sdpSegRouteIsIsOperInstId,
        sdpSegRouteIsIsLspId,
        sdpSegRouteOspf,
        sdpSegRouteOspfOperInstId,
        sdpSegRouteOspfLspId,
        sdpSegRouteTableLastChgd
    }
    STATUS      current
    DESCRIPTION
        "The group of objects supporting management of the SDP segment routing
         feature on Nokia SROS series systems in release 13.0."
    ::= { tmnxSdpGroups 534 }

tmnxSdpBindV11v0Group            OBJECT-GROUP
    OBJECTS     {
        sdpBindForceQinqVcForwarding,
        pwTemplateForceQinqVcForwarding
    }
    STATUS      obsolete
    DESCRIPTION
        "The group of objects supporting management of the SDP feature on Nokia
         SROS series systems in release 11.0."
    ::= { tmnxSdpGroups 535 }

tmnxSdpPwPortOperGrpGroup        OBJECT-GROUP
    OBJECTS     {
        sdpPwPortMonOperGrp
    }
    STATUS      current
    DESCRIPTION
        "The group of objects supporting management of the pseudo-wire port
         operational group feature on Nokia SROS series systems in release
         13.0."
    ::= { tmnxSdpGroups 536 }

tmnxSdpV13v0Group                OBJECT-GROUP
    OBJECTS     {
        svcTlsBgpADPWTempBindCreatOrigin,
        sdpNumEntries,
        sdpNextFreeId,
        sdpId,
        sdpRowStatus,
        sdpDelivery,
        sdpLspList,
        sdpDescription,
        sdpLabelSignaling,
        sdpAdminStatus,
        sdpOperStatus,
        sdpOperPathMtu,
        sdpKeepAliveAdminStatus,
        sdpKeepAliveOperStatus,
        sdpKeepAliveHelloTime,
        sdpKeepAliveMaxDropCount,
        sdpKeepAliveHoldDownTime,
        sdpLastMgmtChange,
        sdpKeepAliveNumHelloRequestMessages,
        sdpKeepAliveNumHelloResponseMessages,
        sdpKeepAliveNumLateHelloResponseMessages,
        sdpKeepAliveHelloRequestTimeout,
        sdpLdpEnabled,
        sdpVlanVcEtype,
        sdpAdvertisedVllMtuOverride,
        sdpOperFlags,
        sdpLastStatusChange,
        sdpMvplsMgmtService,
        sdpMvplsMgmtSdpBndId,
        sdpCollectAcctStats,
        sdpAccountingPolicyId,
        sdpClassFwdingEnabled,
        sdpClassFwdingDefaultLsp,
        sdpClassFwdingMcLsp,
        sdpMetric,
        sdpAutoSdp,
        sdpPBBEtype,
        sdpBandwidthBookingFactor,
        sdpOperBandwidth,
        sdpAvailableBandwidth,
        sdpAdminPathMtu,
        sdpKeepAliveHelloMessageLength,
        sdpNetDomainName,
        sdpEgressIfsNetDomainConsistent,
        sdpBgpTunnelEnabled,
        sdpBgpTunnelLspId
    }
    STATUS      obsolete
    DESCRIPTION
        "The  group  of objects supporting SDP base feature
         on Nokia SROS series systems."
    ::= { tmnxSdpGroups 537 }

tmnxSdpObsoletedObjsV13v0Group   OBJECT-GROUP
    OBJECTS     {
        sdpFarEndIpAddress,
        sdpTunnelFarEndIpAddress
    }
    STATUS      current
    DESCRIPTION
        "The group of obsoleted objects for the service SDPs on Nokia SROS
         series systems in the 12.0 release."
    ::= { tmnxSdpGroups 538 }

sdpBgpEvpnMplsMhGroup            OBJECT-GROUP
    OBJECTS     {
        sdpEvpnMHEthSegName
    }
    STATUS      current
    DESCRIPTION
        "The group of objects supporting SDP BGP EVPN (Ethernet - VPN) MPLS
         Multi Home feature on Nokia SROS series systems release 13.0."
    ::= { tmnxSdpGroups 539 }

sdpGreExtGroup                   OBJECT-GROUP
    OBJECTS     {
        sdpGreAllowFragmentation
    }
    STATUS      current
    DESCRIPTION
        "The group of objects supporting SDP GRE extension feature on Nokia
         SROS series systems release 13.0."
    ::= { tmnxSdpGroups 540 }

svcPwTmplExt14v0Group            OBJECT-GROUP
    OBJECTS     {
        pwTemplatePreferProvSdp
    }
    STATUS      current
    DESCRIPTION
        "The group of objects supporting PW Template extension feature on Nokia
         SROS series systems release 14.0."
    ::= { tmnxSdpGroups 541 }

tmnxSdpBindV14v0Group            OBJECT-GROUP
    OBJECTS     {
        sdpBindExtTableLastChanged,
        sdpBindExtEntropyLabel,
        sdpBindExtLastMgmtChange,
        pwTemplateEntropyLabel
    }
    STATUS      current
    DESCRIPTION
        "The  group  of objects supporting SDP Bind feature on Nokia
         SROS series systems in release 14.0."
    ::= { tmnxSdpGroups 543 }

tmnxSdpSegRouteTeGroup           OBJECT-GROUP
    OBJECTS     {
        sdpSegRouteTeOperInstId,
        sdpSegRouteTeLspRowStatus,
        sdpSegRouteTeLspLastChanged,
        sdpSegRouteTeLspTableLastChgd
    }
    STATUS      current
    DESCRIPTION
        "The group of objects supporting management of the SDP segment routing
         feature on Nokia SROS series systems in release 13.0."
    ::= { tmnxSdpGroups 544 }

tmnxSdpFlowSPecObsoletedV14v0Grp OBJECT-GROUP
    OBJECTS     {
        sdpBindIngressFlowspec,
        sdpBindIngressIPv6Flowspec
    }
    STATUS      current
    DESCRIPTION
        "The group of obsoleted objects supporting SDP BGP Flow-Spec feature on
         Nokia SROS series systems release 14.0."
    ::= { tmnxSdpGroups 545 }

tmnxSdpBindObsoletedV13v0Group   OBJECT-GROUP
    OBJECTS     {
        sdpBindIngressVlanTranslation,
        sdpBindIngressVlanTranslationId
    }
    STATUS      current
    DESCRIPTION
        "The group of obsoleted objects supporting management of the SDP
         feature on Nokia SROS series systems in release 14.0."
    ::= { tmnxSdpGroups 546 }

sdpPwStaticLabelGroup            OBJECT-GROUP
    OBJECTS     {
        sdpPwPortIngVcLabel,
        sdpPwPortEgrVcLabel
    }
    STATUS      current
    DESCRIPTION
        "The group of objects supporting management of the SDP PW static label
         feature on Nokia SROS series systems in release 14.0."
    ::= { tmnxSdpGroups 547 }

sdpBindV14v0Group                OBJECT-GROUP
    OBJECTS     {
        sdpBindMinReqdSdpOperMtu
    }
    STATUS      current
    DESCRIPTION
        "The group of additional objects supporting management of the SDP BIND
         feature on Nokia SROS series systems in release 14.0."
    ::= { tmnxSdpGroups 548 }

sdpBindTlsV14v0Group             OBJECT-GROUP
    OBJECTS     {
        sdpBindDisableSendBvplsEvpnFlush
    }
    STATUS      current
    DESCRIPTION
        "The group of additional objects supporting management of the SDP BIND
         for vpls services feature on Nokia SROS series systems in release
         14.0."
    ::= { tmnxSdpGroups 549 }

sdpFpeV14v0Group                 OBJECT-GROUP
    OBJECTS     {
        sdpFpeLspId
    }
    STATUS      current
    DESCRIPTION
        "The group of additional objects supporting management of the SDP for
         forward-path-extension feature on Nokia SROS series systems in release
         14.0."
    ::= { tmnxSdpGroups 550 }

sdpBindBgpEvpnAlmpGroup          OBJECT-GROUP
    OBJECTS     {
        sdpBindTlsRestProtSrcMacOper,
        sdpBindTlsRestProtSrcMacOperAct,
        sdpBindMeshTlsRPSMacOper,
        sdpBindMeshTlsRPSMacOperAct
    }
    STATUS      current
    DESCRIPTION
        "The group of additional objects supporting management of the SDP for
         BGP EVPN on Nokia SROS series systems in release 14.0."
    ::= { tmnxSdpGroups 551 }

tmnxSdpMplsLspGroup              OBJECT-GROUP
    OBJECTS     {
        sdpMplsLspRowStatus,
        sdpMplsLspLastChanged,
        sdpMplsLspTableLastChgd
    }
    STATUS      current
    DESCRIPTION
        "The group of objects supporting management of the SDP segment routing
         feature on Nokia SROS series systems in release 15.0."
    ::= { tmnxSdpGroups 552 }

tmnxSdpCfmLmmPerQosV15v0Group    OBJECT-GROUP
    OBJECTS     {
        sdpBindEthCfmCollLmmFcSts,
        sdpBindEthCfmCollLmmFcStsInP
    }
    STATUS      current
    DESCRIPTION
        "The group of objects supporting the ETH-LMM per QoS Class feature on
         Nokia SROS series systems."
    ::= { tmnxSdpGroups 553 }

tmnxObsoletedSdpV15v0Group       OBJECT-GROUP
    OBJECTS     {
        sdpLspList
    }
    STATUS      current
    DESCRIPTION
        "The  group  of obsoleted objects supporting SDP base feature
         on Nokia SROS series systems in release 15.0."
    ::= { tmnxSdpGroups 554 }

tmnxSdpV15v0Group                OBJECT-GROUP
    OBJECTS     {
        svcTlsBgpADPWTempBindCreatOrigin,
        sdpNumEntries,
        sdpNextFreeId,
        sdpId,
        sdpRowStatus,
        sdpDelivery,
        sdpDescription,
        sdpLabelSignaling,
        sdpAdminStatus,
        sdpOperStatus,
        sdpOperPathMtu,
        sdpKeepAliveAdminStatus,
        sdpKeepAliveOperStatus,
        sdpKeepAliveHelloTime,
        sdpKeepAliveMaxDropCount,
        sdpKeepAliveHoldDownTime,
        sdpLastMgmtChange,
        sdpKeepAliveNumHelloRequestMessages,
        sdpKeepAliveNumHelloResponseMessages,
        sdpKeepAliveNumLateHelloResponseMessages,
        sdpKeepAliveHelloRequestTimeout,
        sdpLdpEnabled,
        sdpVlanVcEtype,
        sdpAdvertisedVllMtuOverride,
        sdpOperFlags,
        sdpLastStatusChange,
        sdpMvplsMgmtService,
        sdpMvplsMgmtSdpBndId,
        sdpCollectAcctStats,
        sdpAccountingPolicyId,
        sdpClassFwdingEnabled,
        sdpClassFwdingDefaultLsp,
        sdpClassFwdingMcLsp,
        sdpMetric,
        sdpAutoSdp,
        sdpPBBEtype,
        sdpBandwidthBookingFactor,
        sdpOperBandwidth,
        sdpAvailableBandwidth,
        sdpAdminPathMtu,
        sdpKeepAliveHelloMessageLength,
        sdpNetDomainName,
        sdpEgressIfsNetDomainConsistent,
        sdpBgpTunnelEnabled,
        sdpBgpTunnelLspId
    }
    STATUS      current
    DESCRIPTION
        "The  group  of objects supporting SDP base feature
         on Nokia SROS series systems in release 15.0."
    ::= { tmnxSdpGroups 555 }

tmnxSdpWeightedLoadBalanceGroup  OBJECT-GROUP
    OBJECTS     {
        sdpWeightedEcmpEnabled
    }
    STATUS      current
    DESCRIPTION
        "The  group  of objects supporting SDP weighted load
         balancing feature on Nokia SROS series systems in release
         15.0."
    ::= { tmnxSdpGroups 556 }

sdpEvpnMhEthSegV15v0Group        OBJECT-GROUP
    OBJECTS     {
        sdpEvpnMHEthSegStatus
    }
    STATUS      current
    DESCRIPTION
        "The group of objects supporting VXLAN MH feature on Nokia SROS series
         systems release 15.0."
    ::= { tmnxSdpGroups 557 }

tmnxPwTempNameV15v0Group         OBJECT-GROUP
    OBJECTS     {
        pwTemplateName
    }
    STATUS      current
    DESCRIPTION
        "The group of objects supporting names for PW templates on Nokia series
         systems release 15.0."
    ::= { tmnxSdpGroups 558 }

sdpOperTunnelFarEndGroup         OBJECT-GROUP
    OBJECTS     {
        sdpOperTunnelFarEndInetAddrType,
        sdpOperTunnelFarEndInetAddr
    }
    STATUS      current
    DESCRIPTION
        "The group of objects supporting management of tunnel far-end for SDP
         on Nokia SROS series systems in release 15.0."
    ::= { tmnxSdpGroups 559 }

pwTemplateGreGroup               OBJECT-GROUP
    OBJECTS     {
        pwTemplateGreDelivery,
        pwTemplateAugGreAllowFrag
    }
    STATUS      current
    DESCRIPTION
        "The group of objects supporting management of PW template GRE feature
         on Nokia SROS series systems in release 16.0."
    ::= { tmnxSdpGroups 560 }

pwTemplateQosV16v0Group          OBJECT-GROUP
    OBJECTS     {
        pwTemplateIngQoSNetworkPlcyName,
        pwTemplateEgrQoSNetworkPlcyName
    }
    STATUS      current
    DESCRIPTION
        "The group of objects supporting management of PW template QoS feature
         on Nokia SROS series systems in release 16.0."
    ::= { tmnxSdpGroups 561 }

pwTemplateFilterNameV16v0Group   OBJECT-GROUP
    OBJECTS     {
        pwTemplateIngressIpFilterName,
        pwTemplateIngressIpv6FilterName,
        pwTemplateIngressMacFilterName,
        pwTemplateEgressIpFilterName,
        pwTemplateEgressIpv6FilterName,
        pwTemplateEgressMacFilterName
    }
    STATUS      current
    DESCRIPTION
        "The group of objects supporting management of SAP templates Filter
         feature on Nokia SROS series systems in release 16.0."
    ::= { tmnxSdpGroups 562 }

tmnxSdpBindQinqV16v0Group        OBJECT-GROUP
    OBJECTS     {
        sdpBindForceQinqVcFwding,
        pwTemplateForceQinqVcFwding
    }
    STATUS      current
    DESCRIPTION
        "The group of objects supporting management of Qinq preserve and
         translation feature on Nokia SROS series systems in release 16.0."
    ::= { tmnxSdpGroups 564 }

tmnxSdpBindV16v0ObsoletedGroup   OBJECT-GROUP
    OBJECTS     {
        sdpBindForceQinqVcForwarding,
        pwTemplateForceQinqVcForwarding
    }
    STATUS      current
    DESCRIPTION
        "The group of objects supporting management of the SDP feature on Nokia
         SROS series systems in release 16.0."
    ::= { tmnxSdpGroups 565 }

sdpPwPortControlWordGroup        OBJECT-GROUP
    OBJECTS     {
        sdpPwPortControlWord
    }
    STATUS      current
    DESCRIPTION
        "The group of objects supporting management of the SDP pseudo-wire port
         with control-word feature on Nokia SROS series systems in release
         19.10."
    ::= { tmnxSdpGroups 566 }

pwTemplateNgeAutoBindGroup       OBJECT-GROUP
    OBJECTS     {
        pwTemplateAugAluNgeKeyGroupIn,
        pwTemplateAugAluNgeKeyGroupOut
    }
    STATUS      current
    DESCRIPTION
        "The group of objects supporting management of the SDP pseudo-wire port
         with control-word feature on Nokia SROS series systems in release
         19.10."
    ::= { tmnxSdpGroups 567 }

sdpBindMcastSrcV19v0Group        OBJECT-GROUP
    OBJECTS     {
        sdpBindMulticastSource
    }
    STATUS      current
    DESCRIPTION
        "The group of additional objects supporting management of the SDP
         feature on Nokia SROS series systems in release 19.0."
    ::= { tmnxSdpGroups 568 }

sdpTrapsPrefix                   OBJECT IDENTIFIER ::= { tmnxServNotifications 4 }

sdpTraps                         OBJECT IDENTIFIER ::= { sdpTrapsPrefix 0 }

sdpCreated                       NOTIFICATION-TYPE
    OBJECTS     {
        sdpId
    }
    STATUS      obsolete
    DESCRIPTION
        "The sdpCreated notification is sent when a new row is created in the
         sdpInfoTable."
    ::= { sdpTraps 1 }

sdpDeleted                       NOTIFICATION-TYPE
    OBJECTS     {
        sdpId
    }
    STATUS      obsolete
    DESCRIPTION
        "The sdpDeleted notification is sent when an existing row is deleted
         from the sdpInfoTable."
    ::= { sdpTraps 2 }

sdpStatusChanged                 NOTIFICATION-TYPE
    OBJECTS     {
        sdpId,
        sdpAdminStatus,
        sdpOperStatus
    }
    STATUS      current
    DESCRIPTION
        "The sdpStatusChanged notification is generated when there is a change
         in the administrative or operating status of an SDP."
    ::= { sdpTraps 3 }

sdpBindCreated                   NOTIFICATION-TYPE
    OBJECTS     {
        custId,
        svcId,
        svcVpnId,
        sdpBindId
    }
    STATUS      obsolete
    DESCRIPTION
        "The sdpBindCreated notification is sent when a new row is created in
         the sdpBindTable."
    ::= { sdpTraps 4 }

sdpBindDeleted                   NOTIFICATION-TYPE
    OBJECTS     {
        custId,
        svcId,
        svcVpnId,
        sdpBindId
    }
    STATUS      obsolete
    DESCRIPTION
        "The sdpBindDeleted notification is sent when an existing row is
         deleted from the sdpBindTable."
    ::= { sdpTraps 5 }

sdpBindStatusChanged             NOTIFICATION-TYPE
    OBJECTS     {
        custId,
        svcId,
        svcVpnId,
        sdpBindId,
        sdpBindAdminStatus,
        sdpBindOperStatus,
        sdpBindOperFlags
    }
    STATUS      current
    DESCRIPTION
        "The sdpBindStatusChanged notification is generated when there is a
         change in the administrative or operating status of an SDP Binding.

         Notice that this trap is not generated whenever the SDP Binding
         operating status change is caused by an operating status change on the
         associated SDP."
    ::= { sdpTraps 6 }

sdpTlsMacAddrLimitAlarmRaised    NOTIFICATION-TYPE
    OBJECTS     {
        custId,
        svcId,
        svcVpnId,
        sdpId,
        sdpBindId
    }
    STATUS      current
    DESCRIPTION
        "The sdpTlsMacAddrLimitAlarmRaised notification is sent whenever the
         number of MAC addresses stored in the FDB for this spoke sdp-bind
         increases to reach the watermark specified by the object
         svcTlsFdbTableFullHighWatermark."
    ::= { sdpTraps 7 }

sdpTlsMacAddrLimitAlarmCleared   NOTIFICATION-TYPE
    OBJECTS     {
        custId,
        svcId,
        svcVpnId,
        sdpId,
        sdpBindId
    }
    STATUS      current
    DESCRIPTION
        "The sdpTlsMacAddrLimitAlarmCleared notification is sent whenever the
         number of MAC addresses stored in the FDB for this spoke sdp-bind
         drops to the watermark specified by the object
         svcTlsFdbTableFullLowWatermark."
    ::= { sdpTraps 8 }

sdpTlsDHCPSuspiciousPcktRcvd     NOTIFICATION-TYPE
    OBJECTS     {
        custId,
        svcId,
        svcVpnId,
        sdpId,
        tlsDhcpPacketProblem
    }
    STATUS      obsolete
    DESCRIPTION
        "The sdpTlsDHCPSuspiciousPcktRcvd notification is generated when a DHCP
         packet is received with suspicious content."
    ::= { sdpTraps 9 }

sdpBindDHCPLeaseEntriesExceeded  NOTIFICATION-TYPE
    OBJECTS     {
        custId,
        svcId,
        svcVpnId,
        sdpBindId,
        svcDhcpLseStateNewCiAddr,
        svcDhcpLseStateNewChAddr,
        svcDhcpClientLease
    }
    STATUS      current
    DESCRIPTION
        "The sdpBindDHCPLeaseEntriesExceeded notification is generated when the
         number of DHCP lease state entries on a given IES or VRPN spoke-SDP
         reaches the user configurable upper limit given by
         TIMETRA-VRTR-MIB::vRtrIfDHCPLeasePopulate."
    ::= { sdpTraps 10 }

sdpBindDHCPLseStateOverride      NOTIFICATION-TYPE
    OBJECTS     {
        custId,
        svcId,
        svcVpnId,
        sdpBindId,
        svcDhcpLseStateNewCiAddr,
        svcDhcpLseStateNewChAddr,
        svcDhcpLseStateOldCiAddr,
        svcDhcpLseStateOldChAddr
    }
    STATUS      current
    DESCRIPTION
        "The sdpBindDHCPLseStateOverride notification is generated when an
         existing DHCP lease state is overridden by a new lease state which has
         the same IP address but a different MAC address. This trap is only
         applicable for IES and VPRN spoke-SDPs."
    ::= { sdpTraps 11 }

sdpBindDHCPSuspiciousPcktRcvd    NOTIFICATION-TYPE
    OBJECTS     {
        custId,
        svcId,
        svcVpnId,
        sdpBindId,
        svcDhcpPacketProblem
    }
    STATUS      current
    DESCRIPTION
        "The sdpBindDHCPSuspiciousPcktRcvd notification is generated when a
         DHCP packet is received with suspicious content."
    ::= { sdpTraps 12 }

sdpBindDHCPLseStatePopulateErr   NOTIFICATION-TYPE
    OBJECTS     {
        custId,
        svcId,
        svcVpnId,
        sdpBindId,
        svcDhcpLseStatePopulateError
    }
    STATUS      current
    DESCRIPTION
        "The sdpBindDHCPLseStatePopulateErr notification indicates that the
         system was unable to update the DHCP Lease State table with the
         information contained in the DHCP ACK message. The DHCP ACK message
         has been discarded. This trap is only applicable for IES and VPRN
         spoke-SDPs."
    ::= { sdpTraps 13 }

sdpBindPwPeerStatusBitsChanged   NOTIFICATION-TYPE
    OBJECTS     {
        custId,
        svcId,
        svcVpnId,
        sdpBindId,
        sdpBindPwPeerStatusBits
    }
    STATUS      current
    DESCRIPTION
        "The sdpBindPwPeerStatusBitsChanged notification is generated when
         there is a change in the PW status bits received from the peer."
    ::= { sdpTraps 14 }

sdpBindTlsMacMoveExceeded        NOTIFICATION-TYPE
    OBJECTS     {
        custId,
        svcId,
        svcVpnId,
        sdpBindId,
        sdpBindAdminStatus,
        sdpBindOperStatus,
        sdpBindTlsMacMoveRateExcdLeft,
        sdpBindTlsMacMoveNextUpTime,
        svcTlsMacMoveMaxRate,
        sdpBindNotifyMacAddr
    }
    STATUS      current
    DESCRIPTION
        "The sdpBindTlsMacMoveExceeded notification is generated when the SDP
         exceeds the TLS svcTlsMacMoveMaxRate."
    ::= { sdpTraps 15 }

sdpBindPwPeerFaultAddrChanged    NOTIFICATION-TYPE
    OBJECTS     {
        custId,
        svcId,
        svcVpnId,
        sdpBindId,
        sdpBindPwFaultInetAddressType,
        sdpBindPwFaultInetAddress
    }
    STATUS      current
    DESCRIPTION
        "The sdpBindPwPeerFaultAddrChanged notification is
         generated when there is a change in the IP address
         included in the PW status message sent by the peer.
         This notification is only generated if the IP address
         is the only information in the notification that
         changed.  If the status bits changed as well, then
         the sdpBindPwPeerStatusBitsChanged notification will
         be generated instead."
    ::= { sdpTraps 16 }

sdpBindDHCPProxyServerError      NOTIFICATION-TYPE
    OBJECTS     {
        custId,
        svcId,
        svcVpnId,
        sdpBindId,
        svcDhcpProxyError
    }
    STATUS      current
    DESCRIPTION
        "The sdpBindDHCPProxyServerError notification indicates that the system
         was unable to proxy DHCP requests."
    ::= { sdpTraps 17 }

sdpBindDHCPCoAError              NOTIFICATION-TYPE
    OBJECTS     {
        custId,
        svcId,
        svcVpnId,
        sdpBindId,
        svcDhcpCoAError
    }
    STATUS      obsolete
    DESCRIPTION
        "The sdpBindDHCPCoAError notification indicates that the system was
         unable to process a Change of Authorization (CoA) request from a
         Radius server."
    ::= { sdpTraps 18 }

sdpBindDHCPSubAuthError          NOTIFICATION-TYPE
    OBJECTS     {
        custId,
        svcId,
        svcVpnId,
        sdpBindId,
        svcDhcpSubAuthError
    }
    STATUS      obsolete
    DESCRIPTION
        "The sdpBindDHCPSubAuthError notification indicates that the system
         encountered a problem while trying to authenticate a subscriber."
    ::= { sdpTraps 19 }

sdpBindSdpStateChangeProcessed   NOTIFICATION-TYPE
    OBJECTS     {
        sdpNotifySdpId
    }
    STATUS      current
    DESCRIPTION
        "The sdpBindSdpStateChangeProcessed notification indicates that the
         agent has finished processing an SDP state change event, and that the
         operating status of all the affected SDP Bindings has been updated
         accordingly. The value of the sdpNotifySdpId object indicates the SDP
         that experienced the state change."
    ::= { sdpTraps 20 }

sdpBindDHCPLseStateMobilityErr   NOTIFICATION-TYPE
    OBJECTS     {
        custId,
        svcId,
        svcVpnId,
        sdpBindId,
        svcDhcpLseStatePopulateError
    }
    STATUS      current
    DESCRIPTION
        "The sdpBindDHCPLseStateMobilityErr notification indicates that the
         system was unable to perform a mobility check for this lease state."
    ::= { sdpTraps 21 }

sdpBandwidthOverbooked           NOTIFICATION-TYPE
    OBJECTS     {
        sdpId,
        sdpMaxBookableBandwidth,
        sdpBookedBandwidth
    }
    STATUS      current
    DESCRIPTION
        "The sdpBandwidthOverbooked notification indicates that the bandwidth
         that has been allocated to the SDP bindings indicated by
         sdpBookedBandwidth exceeds sdpMaxBookableBandwidth."
    ::= { sdpTraps 22 }

sdpBindInsufficientBandwidth     NOTIFICATION-TYPE
    OBJECTS     {
        svcId,
        sdpId,
        sdpBindId,
        sdpAvailableBandwidth,
        sdpBindAdminBandwidth
    }
    STATUS      current
    DESCRIPTION
        "The sdpBindInsufficientBandwidth notification indicates that the
         available bandwidth of the SDP is insufficient to satisfy the
         bandwidth requirement specified by sdpBindAdminBandwidth of this SDP
         binding."
    ::= { sdpTraps 23 }

dynamicSdpConfigChanged          NOTIFICATION-TYPE
    OBJECTS     {
        dynamicSdpOrigin,
        sdpId,
        svcL2RteSdpBindId,
        dynamicSdpStatus
    }
    STATUS      current
    DESCRIPTION
        "The dynamicSdpConfigChanged notification is generated when a dynamic
         SDP is 'created', 'modified', or 'deleted', with the value of
         dynamicSdpStatus indicated which state it has entered."
    ::= { sdpTraps 24 }

dynamicSdpBindConfigChanged      NOTIFICATION-TYPE
    OBJECTS     {
        dynamicSdpOrigin,
        sdpId,
        svcL2RteSdpBindId,
        dynamicSdpStatus,
        sdpMSPwPeId
    }
    STATUS      current
    DESCRIPTION
        "The dynamicSdpBindConfigChanged notification is generated when a
         dynamic SDP Bind is 'created', 'modified', or 'deleted'.  New state
         of the SDP Bind is indicated by the value of dynamicSdpStatus. The
         affected SDP is indicated by the value of 'sdpId' or by Spoke-SDP FEC
         identifier 'sdpMSPwPeId'.

         [EFFECT] This is an informational notification. Depending on the type
         of change, new layer-2 route may have been created, modified or
         deleted.

         [RECOVERY] No recovery action is required."
    ::= { sdpTraps 25 }

dynamicSdpCreationFailed         NOTIFICATION-TYPE
    OBJECTS     {
        svcL2RteSdpBindId,
        dynamicSdpOrigin,
        dynamicSdpCreationError
    }
    STATUS      current
    DESCRIPTION
        "The dynamicSdpCreationFailed notification is generated when the system
         fails to create a dynamic SDP."
    ::= { sdpTraps 26 }

dynamicSdpBindCreationFailed     NOTIFICATION-TYPE
    OBJECTS     {
        svcL2RteSdpBindId,
        dynamicSdpOrigin,
        sdpId,
        pwTemplateLastChanged,
        dynamicSdpBindCreationError
    }
    STATUS      current
    DESCRIPTION
        "The dynamicSdpBindCreationFailed notification is generated when the
         system fails to create a dynamic SDP Bind."
    ::= { sdpTraps 27 }

sdpEgrIfsNetDomInconsCntChanged  NOTIFICATION-TYPE
    OBJECTS     {
        sdpEgIfNetDomainInconsCount
    }
    STATUS      current
    DESCRIPTION
        "The sdpEgrIfsNetDomInconsCntChanged notification is generated when the
         value of sdpEgIfNetDomainInconsCount changes."
    ::= { sdpTraps 28 }

sdpBindIpipeCeIpAddressChange    NOTIFICATION-TYPE
    OBJECTS     {
        svcId,
        sdpBindId,
        sdpBindIpipeCeIpAddrType,
        sdpBindIpipeCeIpAddress
    }
    STATUS      current
    DESCRIPTION
        "[CAUSE] The sdpBindIpipeCeIpAddressChange notification indicates an IP
         address has been discovered for the far end CE device on a specified
         IPIPE SDP. The type of IP address is specified by
         sdpBindIpipeCeIpAddrType. The IP address is specified by
         sdpBindIpipeCeIpAddress.

         [EFFECT] The IP address specified by sdpBindIpipeCeIpAddress and of
         type sdpBindIpipeCeIpAddrType has been discovered on the remote CE
         device.

         [RECOVERY] No action is required."
    ::= { sdpTraps 29 }

sdpBindReceivedProtSrcMac        NOTIFICATION-TYPE
    OBJECTS     {
        svcId,
        sdpBindId,
        protectedMacForNotify,
        sdpBindTlsRestProtSrcMacAction
    }
    STATUS      current
    DESCRIPTION
        "[CAUSE] The sdpBindReceivedProtSrcMac notification is generated when a
         protected source MAC is received on a TLS SDP-BIND with
         sdpBindTlsRestProtSrcMac 'true', or if the TLS SDP-BIND belongs to an
         SHG with tlsShgRestProtSrcMac set to 'true'.

         [EFFECT] If the sdpBindTlsRestProtSrcMacAction is set to
         'discardFrame', the frame will be discarded.

         [RECOVERY] No action is required."
    ::= { sdpTraps 30 }

sdpBindPwLocalStatusBitsChanged  NOTIFICATION-TYPE
    OBJECTS     {
        custId,
        svcId,
        svcVpnId,
        sdpBindId,
        sdpBindPwLocalStatusBits
    }
    STATUS      current
    DESCRIPTION
        "[CAUSE] The sdpBindPwLocalStatusBitsChanged notification is generated
         when there is a change in the local PW status bits.

         [EFFECT] Based on the change in the sdpBindPwLocalStatusBits traffic
         on the SDP-BIND may be impacted.

         [RECOVERY] Based on the change in the sdpBindPwLocalStatusBits
         appropriate configuration changes may be required."
    ::= { sdpTraps 31 }

sdpBindTlsMacMoveExceedNonBlock  NOTIFICATION-TYPE
    OBJECTS     {
        custId,
        svcId,
        svcVpnId,
        sdpBindId,
        svcTlsMacMoveMaxRate,
        sdpBindNotifyMacAddr
    }
    STATUS      current
    DESCRIPTION
        "[CAUSE] The sdpBindTlsMacMoveExceedNonBlock notification is generated
         when the SDP exceeds the TLS svcTlsMacMoveMaxRate even when
         sdpBindTlsLimitMacMove is set to 'nonBlocking'.In case of Provider
         Backbone Bridging (PBB), if the MAC address that exceeds the rate is
         in ISID-VPLS(iVpls) FDB and sdp binding that detects the move is in
         Backbone-VPLS(bVpls), the notification will be generated with svcId,
         custId of I-VPLS and B-VPLS sdpBindId.

         [EFFECT] This notification is informational only.

         [RECOVERY] User can adjust the value of svcTlsMacMoveMaxRate to reduce
         the frequency of this notification."
    ::= { sdpTraps 32 }

sdpBindEthLoopbackStarted        NOTIFICATION-TYPE
    OBJECTS     {
        sdpBindEthLoopbackMode,
        sdpBindEthLoopbackMacSwap,
        sdpBindEthLoopbackMacSwapAddr,
        sdpBindEthLoopbackMacSwapAddrAll
    }
    STATUS      current
    DESCRIPTION
        "[CAUSE] The sdpBindEthLoopbackStarted notification is generated when
         the SDP binding is placed into loopback.

         [EFFECT] This notification is informational only."
    ::= { sdpTraps 33 }

sdpBindEthLoopbackStopped        NOTIFICATION-TYPE
    OBJECTS     {
        sdpBindEthLoopbackMode
    }
    STATUS      current
    DESCRIPTION
        "[CAUSE] The sdpBindEthLoopbackStopped notification is generated when
         the SDP binding is removed from loopback.

         [EFFECT] This notification is informational only."
    ::= { sdpTraps 34 }

sdpPbbActvPwWithNonActvCtrlPwChg NOTIFICATION-TYPE
    OBJECTS     {
        sdpId,
        sdpPbbActvPwWithNonActvCtrlPw
    }
    STATUS      current
    DESCRIPTION
        "[CAUSE] The sdpPbbActvPwWithNonActvCtrlPwChg notification is generated
         when last pseudo-wire (PW) goes standby or down and when first PW
         becomes active on the Backbone Edge Bridge (BEB) where control PW is
         standby or down on that SDP.

         [EFFECT] There is a change which caused last active PW to become
         standby or down and when first PW becomes active.

         [RECOVERY] sdpPbbActvPwWithNonActvCtrlPwChg event with
         sdpPbbActvPwWithNonActvCtrlPw set to 'false' indicate clearing of
         sdpPbbActvPwWithNonActvCtrlPwChg with sdpPbbActvPwWithNonActvCtrlPw
         set to 'true'."
    ::= { sdpTraps 35 }

sdpControlPwActiveStateChg       NOTIFICATION-TYPE
    OBJECTS     {
        sdpControlPWIsActive
    }
    STATUS      current
    DESCRIPTION
        "[CAUSE] The sdpControlPwActiveStateChg notification is generated when
         the SDP control PW Active value changes on that SDP.

         [EFFECT] Control pseudo-wire state change could affect related SDP
         bindings.

         [RECOVERY] A change in the configuration may be required."
    ::= { sdpTraps 36 }

unacknowledgedTCN                NOTIFICATION-TYPE
    OBJECTS     {
        custId,
        svcId,
        sdpId
    }
    STATUS      current
    DESCRIPTION
        "The unacknowledgedTCN notification is generated when a
         TCN sent towards the root bridge on the root port (SAP
         or  SDP  binding) has not been acknowledged within the
         allowed  time. A portion of the spanning tree topology
         may  not have been notified that a topology change has
         taken  place.  FDB  tables  on  some  devices may take
         significantly longer to represent the new distribution
         of  layer-2 addresses. Examine this device and devices
         towards the root bridge for STP issues."
    ::= { tstpTraps 8 }

tmnxSvcTopoChgSdpBindMajorState  NOTIFICATION-TYPE
    OBJECTS     {
        custId,
        svcId,
        sdpBindId,
        sdpBindTlsStpPortState,
        tmnxOldSdpBindTlsStpPortState
    }
    STATUS      current
    DESCRIPTION
        "The tmnxSvcTopoChgSdpBindMajorState  notification   is
         generated  when  a  SDP  binding  has transitioned its
         state  from  learning to forwarding or from forwarding
         to  blocking or broken. The spanning tree topology has
         been  modified.  It may denote loss of customer access
         or  redundancy.  Check  the  new  topology against the
         provisioned  topology  to  determine  the  severity of
         connectivity loss."
    ::= { tstpTraps 14 }

tmnxSvcNewRootSdpBind            NOTIFICATION-TYPE
    OBJECTS     {
        custId,
        svcId,
        sdpBindId,
        svcTlsStpDesignatedRoot
    }
    STATUS      current
    DESCRIPTION
        "The  tmnxSvcNewRootSdpBind notification  is  generated
         when  the previous root bridge has been aged out and a
         new  root bridge has been elected. The new root bridge
         creates  a  new  spanning tree topology. It may denote
         loss  of  customer access or redundancy. Check the new
         topology against the provisioned topology to determine
         the severity of connectivity loss."
    ::= { tstpTraps 15 }

tmnxSvcTopoChgSdpBindState       NOTIFICATION-TYPE
    OBJECTS     {
        custId,
        svcId,
        sdpBindId,
        sdpBindTlsStpPortState,
        tmnxOldSdpBindTlsStpPortState
    }
    STATUS      current
    DESCRIPTION
        "The    tmnxSvcTopoChgSdpBindState    notification   is
         generated when a SDP binding has transitioned state to
         blocking  or  broken  from  learning state. This event
         complements     what     is     not     covered     by
         tmnxSvcTopoChgSdpBindMajorState.   The  spanning  tree
         topology  has  been  modified.  It  may denote loss of
         customer  access or redundancy. Check the new topology
         against  the  provisioned  topology  to  determine the
         severity of connectivity loss."
    ::= { tstpTraps 16 }

tmnxSvcSdpBindRcvdTCN            NOTIFICATION-TYPE
    OBJECTS     {
        custId,
        svcId,
        sdpBindId
    }
    STATUS      current
    DESCRIPTION
        "The tmnxSvcSdpBindRcvdTCN  notification  is  generated
         when  a  SDP  binding  has  received  TCN from another
         bridge.  This  bridge  will either have its configured
         BPDU with the topology change flag set if it is a root
         bridge,  or  it  will  pass  TCN  to  its root bridge.
         Eventually  the address aging timer for the forwarding
         database  will  be  made shorter for a short period of
         time. No recovery is needed."
    ::= { tstpTraps 17 }

tmnxSvcSdpBindRcvdHigherBriPrio  NOTIFICATION-TYPE
    OBJECTS     {
        custId,
        svcId,
        sdpBindId,
        tmnxCustomerBridgeId,
        tmnxCustomerRootBridgeId
    }
    STATUS      current
    DESCRIPTION
        "The tmnxSvcSdpBindRcvdHigherBriPrio  notification   is
         generated when a customer's device has been configured
         with  a bridge priority equal to zero. The SDP binding
         that  the  customer's device is connected through will
         be   blocked.   Remove   the   customer's   device  or
         reconfigure  the customer's bridge priority with value
         greater than zero."
    ::= { tstpTraps 18 }

tmnxSvcSdpBindEncapPVST          NOTIFICATION-TYPE
    OBJECTS     {
        custId,
        svcId,
        sdpBindId,
        tmnxOtherBridgeId
    }
    STATUS      current
    DESCRIPTION
        "The tmnxSvcSdpBindEncapPVST notification is  generated
         when an SDP bindings STP received a BPDU that was PVST
         encapsulated. The SDP binding STP's BPDUs will be PVST
         encapsulated. No recovery is needed."
    ::= { tstpTraps 19 }

tmnxSvcSdpBindEncapDot1d         NOTIFICATION-TYPE
    OBJECTS     {
        custId,
        svcId,
        sdpBindId,
        tmnxOtherBridgeId
    }
    STATUS      current
    DESCRIPTION
        "The tmnxSvcSdpBindEncapDot1d notification is generated
         when  a  SDP  binding  received a BPDU that was 802.1d
         encapsulated.  The  SDP  binding  BPDUs  will  also be
         802.1d encapsulated. No recovery is needed."
    ::= { tstpTraps 20 }

tmnxSvcSdpActiveProtocolChange   NOTIFICATION-TYPE
    OBJECTS     {
        custId,
        svcId,
        sdpBindId,
        sdpBindTlsStpOperProtocol
    }
    STATUS      current
    DESCRIPTION
        "The tmnxSvcSdpActiveProtocolChange  notification    is
         generated  when the spanning tree protocol on this SDP
         changes from rstp to stp or vise versa. No recovery is
         needed."
    ::= { tstpTraps 31 }

svcTlsBgpADPWTempBindTblLC       OBJECT-TYPE
    SYNTAX      TimeStamp
    MAX-ACCESS  read-only
    STATUS      current
    DESCRIPTION
        "The value of svcTlsBgpADPWTempBindTblLC indicates the sysUpTime at the
         time of the last modification of svcTlsBgpADPWTempBindTable.

         If no changes were made to the entry since the last re-initialization
         of the local network management subsystem, then this object contains a
         zero value."
    ::= { tmnxSvcObjs 32 }

svcTlsBgpADPWTempBindTable       OBJECT-TYPE
    SYNTAX      SEQUENCE OF SvcTlsBgpADPWTempBindEntry
    MAX-ACCESS  not-accessible
    STATUS      current
    DESCRIPTION
        "svcTlsBgpADPWTempBindTable contains entries for the associations
         between SDP Auto-Bind policies and a BGP Auto-Discovery context for a
         VPLS service."
    ::= { tmnxSvcObjs 33 }

svcTlsBgpADPWTempBindEntry       OBJECT-TYPE
    SYNTAX      SvcTlsBgpADPWTempBindEntry
    MAX-ACCESS  not-accessible
    STATUS      current
    DESCRIPTION
        "A SDP Auto-Bind Policy entry in the svcTlsBgpADPWTempBindTable."
    INDEX       {
        svcId,
        pwTemplateId
    }
    ::= { svcTlsBgpADPWTempBindTable 1 }

SvcTlsBgpADPWTempBindEntry       ::= SEQUENCE
{
    svcTlsBgpADPWTempBindRowStatus   RowStatus,
    svcTlsBgpADPWTempBindLastChngd   TimeStamp,
    svcTlsBgpADPWTempBindSHG         TNamedItemOrEmpty,
    svcTlsBgpADPWTempBindOperGrp     TNamedItemOrEmpty,
    svcTlsBgpADPWTempBindCreatOrigin TmnxCreateOrigin,
    svcTlsBgpADPWTempBindBfdTemplate TNamedItemOrEmpty,
    svcTlsBgpADPWTempBindBfdEnable   TruthValue,
    svcTlsBgpADPWTempBindBfdEncap    TmnxBfdEncap,
    svcTlsBgpADPWTempBindMonOperGrp  TNamedItemOrEmpty
}

svcTlsBgpADPWTempBindRowStatus   OBJECT-TYPE
    SYNTAX      RowStatus
    MAX-ACCESS  read-create
    STATUS      current
    DESCRIPTION
        "The value of svcTlsBgpADPWTempBindRowStatus is used for the creation
         and deletion of associations between SDP Auto-Bind policies and a BGP
         Auto-Discovery context for a VPLS service."
    ::= { svcTlsBgpADPWTempBindEntry 1 }

svcTlsBgpADPWTempBindLastChngd   OBJECT-TYPE
    SYNTAX      TimeStamp
    MAX-ACCESS  read-only
    STATUS      current
    DESCRIPTION
        "The value of svcTlsBgpADPWTempBindLastChngd indicates the sysUpTime at
         the time of the last modification of this entry.

         If no changes were made to the entry since the last re-initialization
         of the local network management subsystem, then this object contains a
         zero value."
    ::= { svcTlsBgpADPWTempBindEntry 2 }

svcTlsBgpADPWTempBindSHG         OBJECT-TYPE
    SYNTAX      TNamedItemOrEmpty
    MAX-ACCESS  read-create
    STATUS      current
    DESCRIPTION
        "The value of svcTlsBgpADPWTempBindSHG specifies the split-horizon
         group to associate with the SDP Auto-Bind policy in this BGP
         Auto-Discovery context in a VPLS service.

         When this Auto-Bind policy is used to create an SDP, this
         split-horizon group will be associated with the SDP.

         The name specified must correspond to an existing split-horizon group
         in the VPLS service, otherwise an 'inconsistentValue' error will be
         returned."
    DEFVAL      { "" }
    ::= { svcTlsBgpADPWTempBindEntry 3 }

svcTlsBgpADPWTempBindOperGrp     OBJECT-TYPE
    SYNTAX      TNamedItemOrEmpty
    MAX-ACCESS  read-create
    STATUS      current
    DESCRIPTION
        "The value of the svcTlsBgpADPWTempBindOperGrp specifies the
         Operational-Group identifier associated with this pseudo-wire template
         binding."
    DEFVAL      { "" }
    ::= { svcTlsBgpADPWTempBindEntry 4 }

svcTlsBgpADPWTempBindCreatOrigin OBJECT-TYPE
    SYNTAX      TmnxCreateOrigin
    MAX-ACCESS  read-only
    STATUS      current
    DESCRIPTION
        "The value of svcTlsBgpADPWTempBindCreatOrigin indicates the mechanism
         used to create this entry."
    DEFVAL      { manual }
    ::= { svcTlsBgpADPWTempBindEntry 5 }

svcTlsBgpADPWTempBindBfdTemplate OBJECT-TYPE
    SYNTAX      TNamedItemOrEmpty
    MAX-ACCESS  read-create
    STATUS      current
    DESCRIPTION
        "The value of the svcTlsBgpADPWTempBindBfdTemplate specifies the BFD
         template name associated with this pseudo-wire template binding."
    DEFVAL      { "" }
    ::= { svcTlsBgpADPWTempBindEntry 6 }

svcTlsBgpADPWTempBindBfdEnable   OBJECT-TYPE
    SYNTAX      TruthValue
    MAX-ACCESS  read-create
    STATUS      current
    DESCRIPTION
        "The value of svcTlsBgpADPWTempBindBfdEnable specifies whether BFD is
         enabled on this pseudo-wire template binding."
    DEFVAL      { false }
    ::= { svcTlsBgpADPWTempBindEntry 7 }

svcTlsBgpADPWTempBindBfdEncap    OBJECT-TYPE
    SYNTAX      TmnxBfdEncap
    MAX-ACCESS  read-create
    STATUS      current
    DESCRIPTION
        "The value of svcTlsBgpADPWTempBindBfdEncap specifies the BFD
         encapsulation used on this pseudo-wire template binding."
    DEFVAL      { ipv4 }
    ::= { svcTlsBgpADPWTempBindEntry 8 }

svcTlsBgpADPWTempBindMonOperGrp  OBJECT-TYPE
    SYNTAX      TNamedItemOrEmpty
    MAX-ACCESS  read-create
    STATUS      current
    DESCRIPTION
        "The value of the svcTlsBgpADPWTempBindMonOperGrp specifies the
         monitoring operational-group identifier associated with this
         pseudo-wire template binding."
    DEFVAL      { "" }
    ::= { svcTlsBgpADPWTempBindEntry 9 }

svcTlsBgpADPWTempBindRTTblLC     OBJECT-TYPE
    SYNTAX      TimeStamp
    MAX-ACCESS  read-only
    STATUS      current
    DESCRIPTION
        "The value of svcTlsBgpADPWTempBindRTTblLC indicates the sysUpTime at
         the time of the last modification of svcTlsBgpADPWTempBindRTTable.

         If no changes were made to the entry since the last re-initialization
         of the local network management subsystem, then this object contains a
         zero value."
    ::= { tmnxSvcObjs 34 }

svcTlsBgpADPWTempBindRTTable     OBJECT-TYPE
    SYNTAX      SEQUENCE OF SvcTlsBgpADPWTempBindRTEntry
    MAX-ACCESS  not-accessible
    STATUS      current
    DESCRIPTION
        "svcTlsBgpADPWTempBindTable contains entries for Route Targets
         associated with a SDP Auto-Bind policy and a BGP Auto-Discovery
         context for a VPLS service."
    ::= { tmnxSvcObjs 35 }

svcTlsBgpADPWTempBindRTEntry     OBJECT-TYPE
    SYNTAX      SvcTlsBgpADPWTempBindRTEntry
    MAX-ACCESS  not-accessible
    STATUS      current
    DESCRIPTION
        "A SDP Auto-Bind Policy Route Target entry in the
         svcTlsBgpADPWTempBindRTTable."
    INDEX       {
        svcId,
        pwTemplateId,
        IMPLIED svcTlsBgpADPWTempBindRT
    }
    ::= { svcTlsBgpADPWTempBindRTTable 1 }

SvcTlsBgpADPWTempBindRTEntry     ::= SEQUENCE
{
    svcTlsBgpADPWTempBindRT          TNamedItem,
    svcTlsBgpADPWTempBindRTRowStat   RowStatus
}

svcTlsBgpADPWTempBindRT          OBJECT-TYPE
    SYNTAX      TNamedItem
    MAX-ACCESS  not-accessible
    STATUS      current
    DESCRIPTION
        "The value of svcTlsBgpADPWTempBindRT is the Route Target associated
         with a PW template and a BGP Auto-Discovery context for a VPLS
         service.

         When advertisements are received with this Route Target, the PW
         template specified by the index, pwTemplateId, will be used to create
         the SDP."
    ::= { svcTlsBgpADPWTempBindRTEntry 1 }

svcTlsBgpADPWTempBindRTRowStat   OBJECT-TYPE
    SYNTAX      RowStatus
    MAX-ACCESS  read-create
    STATUS      current
    DESCRIPTION
        "The value of svcTlsBgpADPWTempBindRTRowStat is used for the
         association of Route Targets with a SDP Auto-Bind policy and a BGP
         Auto-Discovery context for a VPLS service."
    ::= { svcTlsBgpADPWTempBindRTEntry 2 }

tmnxStpMeshNotInMstRegion        NOTIFICATION-TYPE
    OBJECTS     {
        svcId,
        sdpBindId
    }
    STATUS      current
    DESCRIPTION
        "The tmnxStpMeshNotInMstRegion notification is generated when a MSTP
         BPDU from outside the MST region is received on the indicated mesh
         SDP.

         It is up to the operator to make sure bridges connected via mesh SDPs
         are in the same MST-region. If not the mesh will NOT become
         operational."
    ::= { tstpTraps 36 }

svcL2RteTableLastChanged         OBJECT-TYPE
    SYNTAX      TimeStamp
    MAX-ACCESS  read-only
    STATUS      current
    DESCRIPTION
        "The value of svcL2RteTableLastChanged indicates the sysUpTime at the
         time of the last modification of svcL2RteTable.

         If no changes were made to the entry since the last re-initialization
         of the local network management subsystem, then this object contains a
         zero value."
    ::= { tmnxSvcObjs 38 }

tmnxSdpBndStpExcepCondStateChng  NOTIFICATION-TYPE
    OBJECTS     {
        custId,
        svcId,
        sdpBindId,
        sdpBindTlsStpException
    }
    STATUS      current
    DESCRIPTION
        "The tmnxSdpBndStpExcepCondStateChng notification is generated when the
         value of the object sdpBindTlsStpException has changed, i.e. when the
         exception condition changes on the indicated SDP Bind."
    ::= { tstpTraps 38 }

svcL2RteTable                    OBJECT-TYPE
    SYNTAX      SEQUENCE OF SvcL2RteEntry
    MAX-ACCESS  not-accessible
    STATUS      current
    DESCRIPTION
        "svcL2RteTable contains entries for L2 routes."
    ::= { tmnxSvcObjs 39 }

svcL2RteEntry                    OBJECT-TYPE
    SYNTAX      SvcL2RteEntry
    MAX-ACCESS  not-accessible
    STATUS      current
    DESCRIPTION
        "An L2 route entry in the svcL2RteTable."
    INDEX       {
        svcId,
        svcL2RteVsiPrefix,
        svcL2RteRouteDistinguisher,
        svcL2RteNextHopType,
        svcL2RteNextHop
    }
    ::= { svcL2RteTable 1 }

SvcL2RteEntry                    ::= SEQUENCE
{
    svcL2RteVsiPrefix                Unsigned32,
    svcL2RteRouteDistinguisher       TmnxVPNRouteDistinguisher,
    svcL2RteNextHopType              InetAddressType,
    svcL2RteNextHop                  InetAddress,
    svcL2RteSdpBindId                SdpBindId,
    svcL2RtePwTemplateId             PWTemplateId,
    svcL2RteError                    DisplayString,
    svcL2RteLastErrorTime            TimeStamp,
    svcL2RteStatus                   INTEGER
}

svcL2RteVsiPrefix                OBJECT-TYPE
    SYNTAX      Unsigned32
    MAX-ACCESS  not-accessible
    STATUS      current
    DESCRIPTION
        "The value of svcL2RteVsiPrefix is the low-order 4 bytes
            of the Virtual Switch Instance identifier (VSI-id) of the
         remote VSI for this L2 route."
    ::= { svcL2RteEntry 1 }

svcL2RteRouteDistinguisher       OBJECT-TYPE
    SYNTAX      TmnxVPNRouteDistinguisher
    MAX-ACCESS  not-accessible
    STATUS      current
    DESCRIPTION
        "The value of svcL2RteRouteDistinguisher is the high-order
            6 bytes of the Virtual Switch Instance identifier (VSI-id)
         of the remote VSI for this L2 route."
    ::= { svcL2RteEntry 2 }

svcL2RteNextHopType              OBJECT-TYPE
    SYNTAX      InetAddressType
    MAX-ACCESS  not-accessible
    STATUS      current
    DESCRIPTION
        "The value of svcL2RteNextHopType indicates the address type of
         svcL2RteNextHop."
    ::= { svcL2RteEntry 3 }

svcL2RteNextHop                  OBJECT-TYPE
    SYNTAX      InetAddress
    MAX-ACCESS  not-accessible
    STATUS      current
    DESCRIPTION
        "The value of svcL2RteNextHop indicates the IP next hop
            for this L2 route. This value is equivalent to the
         IP address of the Far End of this L2 route."
    ::= { svcL2RteEntry 4 }

svcL2RteSdpBindId                OBJECT-TYPE
    SYNTAX      SdpBindId
    MAX-ACCESS  read-only
    STATUS      current
    DESCRIPTION
        "The value of svcL2RteSdpBindId indicates the SDP bind ID of the SDP
         bind that binds this VPLS context to the VSI indicated by
         svcL2RteRouteDistinguisher, svcL2RteVsiPrefix, and svcL2RteNextHop.

         The value of svcL2RteSdpBindId will be '0000000000000000'H if there
         was an error in creating the L2 route and the svcL2RteError will
         contain a string describing the error."
    ::= { svcL2RteEntry 5 }

svcL2RtePwTemplateId             OBJECT-TYPE
    SYNTAX      PWTemplateId
    MAX-ACCESS  read-only
    STATUS      current
    DESCRIPTION
        "The value of svcL2RtePwTemplateId indicates the PW template associated
         with the SDP bind that binds this VPLS context to the VSI indicated by
         svcL2RteRouteDistinguisher, svcL2RteVsiPrefix, and svcL2RteNextHop."
    ::= { svcL2RteEntry 6 }

svcL2RteError                    OBJECT-TYPE
    SYNTAX      DisplayString
    MAX-ACCESS  read-only
    STATUS      current
    DESCRIPTION
        "The value of svcL2RteError indicates an error message describing an
         error encountered when establishing this L2 route entry. The value of
         svcL2RteError will be a zero-length string when the L2 route is
         successfully established."
    DEFVAL      { "" }
    ::= { svcL2RteEntry 7 }

svcL2RteLastErrorTime            OBJECT-TYPE
    SYNTAX      TimeStamp
    MAX-ACCESS  read-only
    STATUS      current
    DESCRIPTION
        "The value of svcL2RteLastErrorTime indicates the sysUpTime at the time
         of the last error for this L2 route entry.

         If no errors were encountered for this entry since the last
         re-initialization of the local network management subsystem, then this
         object contains a zero value."
    DEFVAL      { 0 }
    ::= { svcL2RteEntry 8 }

svcL2RteStatus                   OBJECT-TYPE
    SYNTAX      INTEGER {
        active   (1),
        inactive (2)
    }
    MAX-ACCESS  read-only
    STATUS      current
    DESCRIPTION
        "The value of svcL2RteStatus indicates the status of the this L2 Route."
    ::= { svcL2RteEntry 9 }

svcL2BgpVplsRteTable             OBJECT-TYPE
    SYNTAX      SEQUENCE OF SvcL2BgpVplsRteEntry
    MAX-ACCESS  not-accessible
    STATUS      current
    DESCRIPTION
        "svcL2BgpVplsRteTable contains entries for L2 routes."
    ::= { tmnxSvcObjs 84 }

svcL2BgpVplsRteEntry             OBJECT-TYPE
    SYNTAX      SvcL2BgpVplsRteEntry
    MAX-ACCESS  not-accessible
    STATUS      current
    DESCRIPTION
        "An L2 route entry in the svcL2BgpVplsRteTable."
    INDEX       {
        svcId,
        svcL2BgpVplsRteVeId,
        svcL2BgpVplsRteRD,
        svcL2BgpVplsRteNextHopType,
        svcL2BgpVplsRteNextHop
    }
    ::= { svcL2BgpVplsRteTable 1 }

SvcL2BgpVplsRteEntry             ::= SEQUENCE
{
    svcL2BgpVplsRteVeId              TmnxSiteId,
    svcL2BgpVplsRteRD                TmnxVPNRouteDistinguisher,
    svcL2BgpVplsRteNextHopType       InetAddressType,
    svcL2BgpVplsRteNextHop           InetAddress,
    svcL2BgpVplsRteSdpBindId         SdpBindId,
    svcL2BgpVplsRtePwTemplateId      PWTemplateId,
    svcL2BgpVplsRteError             DisplayString,
    svcL2BgpVplsRteLastErrorTime     TimeStamp,
    svcL2BgpVplsRteControlWord       Unsigned32,
    svcL2BgpVplsRtePathMtu           Integer32,
    svcL2BgpVplsRteState             INTEGER,
    svcL2BgpVplsRteSeqDelivery       Unsigned32,
    svcL2BgpVplsRteDF                TruthValue,
    svcL2BgpVplsRteStatus            INTEGER
}

svcL2BgpVplsRteVeId              OBJECT-TYPE
    SYNTAX      TmnxSiteId
    MAX-ACCESS  not-accessible
    STATUS      current
    DESCRIPTION
        "The value of svcL2BgpVplsRteVeId is the low-order 4 bytes
            of the Virtual Switch Instance identifier (VSI-id) of the
         remote VSI for this L2 route."
    ::= { svcL2BgpVplsRteEntry 1 }

svcL2BgpVplsRteRD                OBJECT-TYPE
    SYNTAX      TmnxVPNRouteDistinguisher
    MAX-ACCESS  not-accessible
    STATUS      current
    DESCRIPTION
        "The value of svcL2BgpVplsRteRD is the high-order
            6 bytes of the Virtual Switch Instance identifier (VSI-id)
         of the remote VSI for this L2 route."
    ::= { svcL2BgpVplsRteEntry 2 }

svcL2BgpVplsRteNextHopType       OBJECT-TYPE
    SYNTAX      InetAddressType
    MAX-ACCESS  not-accessible
    STATUS      current
    DESCRIPTION
        "The value of svcL2BgpVplsRteNextHopType indicates the address type of
         svcL2BgpVplsRteNextHop."
    ::= { svcL2BgpVplsRteEntry 3 }

svcL2BgpVplsRteNextHop           OBJECT-TYPE
    SYNTAX      InetAddress
    MAX-ACCESS  not-accessible
    STATUS      current
    DESCRIPTION
        "The value of svcL2BgpVplsRteNextHop indicates the IP next hop
            for this L2 route. This value is equivalent to the
         IP address of the Far End of this L2 route."
    ::= { svcL2BgpVplsRteEntry 4 }

svcL2BgpVplsRteSdpBindId         OBJECT-TYPE
    SYNTAX      SdpBindId
    MAX-ACCESS  read-only
    STATUS      current
    DESCRIPTION
        "The value of svcL2BgpVplsRteSdpBindId indicates the SDP bind ID of the
         SDP bind that binds this VPLS context to the VSI indicated by
         svcL2BgpVplsRteRD, svcL2BgpVplsRteVeId, and svcL2BgpVplsRteNextHop.

         The value of svcL2BgpVplsRteSdpBindId will be '0000000000000000'H if
         there was an error in creating the L2 route and the
         svcL2BgpVplsRteError will contain a string describing the error."
    ::= { svcL2BgpVplsRteEntry 5 }

svcL2BgpVplsRtePwTemplateId      OBJECT-TYPE
    SYNTAX      PWTemplateId
    MAX-ACCESS  read-only
    STATUS      current
    DESCRIPTION
        "The value of svcL2BgpVplsRtePwTemplateId indicates the PW template
         associated with the SDP bind that binds this VPLS context to the VSI
         indicated by svcL2BgpVplsRteRD, svcL2BgpVplsRteVeId, and
         svcL2BgpVplsRteNextHop."
    ::= { svcL2BgpVplsRteEntry 6 }

svcL2BgpVplsRteError             OBJECT-TYPE
    SYNTAX      DisplayString
    MAX-ACCESS  read-only
    STATUS      current
    DESCRIPTION
        "The value of svcL2BgpVplsRteError indicates an error message
         describing an error encountered when establishing this L2 route entry.
         The value of svcL2BgpVplsRteError will be a zero-length string when
         the L2 route is successfully established."
    DEFVAL      { "" }
    ::= { svcL2BgpVplsRteEntry 7 }

svcL2BgpVplsRteLastErrorTime     OBJECT-TYPE
    SYNTAX      TimeStamp
    MAX-ACCESS  read-only
    STATUS      current
    DESCRIPTION
        "The value of svcL2BgpVplsRteLastErrorTime indicates the sysUpTime at
         the time of the last error for this L2 route entry.

         If no errors were encountered for this entry since the last
         re-initialization of the local network management subsystem, then this
         object contains a zero value."
    DEFVAL      { 0 }
    ::= { svcL2BgpVplsRteEntry 8 }

svcL2BgpVplsRteControlWord       OBJECT-TYPE
    SYNTAX      Unsigned32
    MAX-ACCESS  read-only
    STATUS      current
    DESCRIPTION
        "The value of svcL2BgpVplsRteControlWord indicates the control word
         advertised for this route."
    ::= { svcL2BgpVplsRteEntry 9 }

svcL2BgpVplsRtePathMtu           OBJECT-TYPE
    SYNTAX      Integer32
    MAX-ACCESS  read-only
    STATUS      current
    DESCRIPTION
        "The value of svcL2BgpVplsRtePathMtu indicates the layer-2 path MTU for
         the pseudo-wire to the PE for this route."
    ::= { svcL2BgpVplsRteEntry 10 }

svcL2BgpVplsRteState             OBJECT-TYPE
    SYNTAX      INTEGER {
        up   (1),
        down (2)
    }
    MAX-ACCESS  read-only
    STATUS      current
    DESCRIPTION
        "The value of svcL2BgpVplsRteState indicates state of the object for
         this route."
    ::= { svcL2BgpVplsRteEntry 11 }

svcL2BgpVplsRteSeqDelivery       OBJECT-TYPE
    SYNTAX      Unsigned32
    MAX-ACCESS  read-only
    STATUS      current
    DESCRIPTION
        "The value of svcL2BgpVplsRteSeqDelivery indicates the
            sequenced delivery flag advertised for this route."
    ::= { svcL2BgpVplsRteEntry 12 }

svcL2BgpVplsRteDF                OBJECT-TYPE
    SYNTAX      TruthValue
    MAX-ACCESS  read-only
    STATUS      current
    DESCRIPTION
        "The value of svcL2BgpVplsRteDF indicates the value of DF bit
         associated with this BGP VPLS L2 route entry."
    ::= { svcL2BgpVplsRteEntry 13 }

svcL2BgpVplsRteStatus            OBJECT-TYPE
    SYNTAX      INTEGER {
        active   (1),
        inactive (2)
    }
    MAX-ACCESS  read-only
    STATUS      current
    DESCRIPTION
        "The value of svcL2BgpVplsRteStatus indicates the status of the this
         BGP VPLS L2 Route."
    ::= { svcL2BgpVplsRteEntry 14 }

svcVllBgpADPWTempBindTblLC       OBJECT-TYPE
    SYNTAX      TimeStamp
    MAX-ACCESS  read-only
    STATUS      current
    DESCRIPTION
        "The value of svcVllBgpADPWTempBindTblLC indicates the sysUpTime at the
         time of the last modification of svcVllBgpADPWTempBindTable.

         If no changes were made to the entry since the last re-initialization
         of the local network management subsystem, then this object contains a
         zero value."
    ::= { tmnxSvcObjs 143 }

svcVllBgpADPWTempBindTable       OBJECT-TYPE
    SYNTAX      SEQUENCE OF SvcVllBgpADPWTempBindEntry
    MAX-ACCESS  not-accessible
    STATUS      current
    DESCRIPTION
        "svcVllBgpADPWTempBindTable contains entries for the associations
         between SDP Auto-Bind policies and a BGP Auto-Discovery context for a
         VLL service."
    ::= { tmnxSvcObjs 144 }

svcVllBgpADPWTempBindEntry       OBJECT-TYPE
    SYNTAX      SvcVllBgpADPWTempBindEntry
    MAX-ACCESS  not-accessible
    STATUS      current
    DESCRIPTION
        "A SDP Auto-Bind Policy entry in the svcVllBgpADPWTempBindTable."
    INDEX       {
        svcId,
        pwTemplateId
    }
    ::= { svcVllBgpADPWTempBindTable 1 }

SvcVllBgpADPWTempBindEntry       ::= SEQUENCE
{
    svcVllBgpADPWTempBindRowStatus   RowStatus,
    svcVllBgpADPWTempBindLastChngd   TimeStamp,
    svcVllBgpADPWTempBindEndPt       TNamedItemOrEmpty,
    svcVllBgpADPWTempBindBfdTemplate TNamedItemOrEmpty,
    svcVllBgpADPWTempBindBfdEnable   TruthValue,
    svcVllBgpADPWTempBindBfdEncap    TmnxBfdEncap
}

svcVllBgpADPWTempBindRowStatus   OBJECT-TYPE
    SYNTAX      RowStatus
    MAX-ACCESS  read-create
    STATUS      current
    DESCRIPTION
        "The value of svcVllBgpADPWTempBindRowStatus is used for the creation
         and deletion of associations between SDP Auto-Bind policies and a BGP
         Auto-Discovery context for a VLL service."
    ::= { svcVllBgpADPWTempBindEntry 1 }

svcVllBgpADPWTempBindLastChngd   OBJECT-TYPE
    SYNTAX      TimeStamp
    MAX-ACCESS  read-only
    STATUS      current
    DESCRIPTION
        "The value of svcVllBgpADPWTempBindLastChngd indicates the sysUpTime at
         the time of the last modification of this entry.

         If no changes were made to the entry since the last re-initialization
         of the local network management subsystem, then this object contains a
         zero value."
    ::= { svcVllBgpADPWTempBindEntry 2 }

svcVllBgpADPWTempBindEndPt       OBJECT-TYPE
    SYNTAX      TNamedItemOrEmpty
    MAX-ACCESS  read-create
    STATUS      current
    DESCRIPTION
        "The value of the svcVllBgpADPWTempBindEndPt specifies the endpoint
         associated with this pseudo-wire template binding."
    DEFVAL      { "" }
    ::= { svcVllBgpADPWTempBindEntry 3 }

svcVllBgpADPWTempBindBfdTemplate OBJECT-TYPE
    SYNTAX      TNamedItemOrEmpty
    MAX-ACCESS  read-create
    STATUS      current
    DESCRIPTION
        "The value of the svcVllBgpADPWTempBindBfdTemplate specifies the BFD
         template name associated with this pseudo-wire template binding."
    DEFVAL      { "" }
    ::= { svcVllBgpADPWTempBindEntry 4 }

svcVllBgpADPWTempBindBfdEnable   OBJECT-TYPE
    SYNTAX      TruthValue
    MAX-ACCESS  read-create
    STATUS      current
    DESCRIPTION
        "The value of svcVllBgpADPWTempBindBfdEnable specifies whether BFD is
         enabled on this pseudo-wire template binding."
    DEFVAL      { false }
    ::= { svcVllBgpADPWTempBindEntry 5 }

svcVllBgpADPWTempBindBfdEncap    OBJECT-TYPE
    SYNTAX      TmnxBfdEncap
    MAX-ACCESS  read-create
    STATUS      current
    DESCRIPTION
        "The value of svcVllBgpADPWTempBindBfdEncap specifies the BFD
         encapsulation used on this pseudo-wire template binding."
    DEFVAL      { ipv4 }
    ::= { svcVllBgpADPWTempBindEntry 6 }

svcVllBgpADPWTempBindRTTblLC     OBJECT-TYPE
    SYNTAX      TimeStamp
    MAX-ACCESS  read-only
    STATUS      current
    DESCRIPTION
        "The value of svcVllBgpADPWTempBindRTTblLC indicates the sysUpTime at
         the time of the last modification of svcVllBgpADPWTempBindRTTable.

         If no changes were made to the entry since the last re-initialization
         of the local network management subsystem, then this object contains a
         zero value."
    ::= { tmnxSvcObjs 145 }

svcVllBgpADPWTempBindRTTable     OBJECT-TYPE
    SYNTAX      SEQUENCE OF SvcVllBgpADPWTempBindRTEntry
    MAX-ACCESS  not-accessible
    STATUS      current
    DESCRIPTION
        "svcVllBgpADPWTempBindTable contains entries for Route Targets
         associated with a SDP Auto-Bind policy and a BGP Auto-Discovery
         context for a VLL service."
    ::= { tmnxSvcObjs 146 }

svcVllBgpADPWTempBindRTEntry     OBJECT-TYPE
    SYNTAX      SvcVllBgpADPWTempBindRTEntry
    MAX-ACCESS  not-accessible
    STATUS      current
    DESCRIPTION
        "A SDP Auto-Bind Policy Route Target entry in the
         svcVllBgpADPWTempBindRTTable."
    INDEX       {
        svcId,
        pwTemplateId,
        IMPLIED svcVllBgpADPWTempBindRT
    }
    ::= { svcVllBgpADPWTempBindRTTable 1 }

SvcVllBgpADPWTempBindRTEntry     ::= SEQUENCE
{
    svcVllBgpADPWTempBindRT          TNamedItem,
    svcVllBgpADPWTempBindRTRowStat   RowStatus
}

svcVllBgpADPWTempBindRT          OBJECT-TYPE
    SYNTAX      TNamedItem
    MAX-ACCESS  not-accessible
    STATUS      current
    DESCRIPTION
        "The value of svcVllBgpADPWTempBindRT is the Route Target associated
         with a PW template and a BGP Auto-Discovery context for a VLL service.

         When advertisements are received with this Route Target, the PW
         template specified by the index, pwTemplateId, will be used to create
         the SDP."
    ::= { svcVllBgpADPWTempBindRTEntry 1 }

svcVllBgpADPWTempBindRTRowStat   OBJECT-TYPE
    SYNTAX      RowStatus
    MAX-ACCESS  read-create
    STATUS      current
    DESCRIPTION
        "The value of svcVllBgpADPWTempBindRTRowStat is used for the
         association of Route Targets with a SDP Auto-Bind policy and a BGP
         Auto-Discovery context for a VLL service."
    ::= { svcVllBgpADPWTempBindRTEntry 2 }

svcL2BgpVpwsRteTable             OBJECT-TYPE
    SYNTAX      SEQUENCE OF SvcL2BgpVpwsRteEntry
    MAX-ACCESS  not-accessible
    STATUS      current
    DESCRIPTION
        "The svcL2BgpVpwsRteTable contains entries for BGP VPWS (Virtual
         Private Wire Service) L2 routes."
    ::= { tmnxSvcObjs 147 }

svcL2BgpVpwsRteEntry             OBJECT-TYPE
    SYNTAX      SvcL2BgpVpwsRteEntry
    MAX-ACCESS  not-accessible
    STATUS      current
    DESCRIPTION
        "The svcL2BgpVpwsRteEntry is an BGP VPWS L2 route entry in the
         svcL2BgpVpwsRteTable."
    INDEX       {
        svcId,
        svcL2BgpVpwsRteVeId,
        svcL2BgpVpwsRteRD,
        svcL2BgpVpwsRteNextHopType,
        svcL2BgpVpwsRteNextHop
    }
    ::= { svcL2BgpVpwsRteTable 1 }

SvcL2BgpVpwsRteEntry             ::= SEQUENCE
{
    svcL2BgpVpwsRteVeId              TmnxSiteId,
    svcL2BgpVpwsRteRD                TmnxVPNRouteDistinguisher,
    svcL2BgpVpwsRteNextHopType       InetAddressType,
    svcL2BgpVpwsRteNextHop           InetAddress,
    svcL2BgpVpwsRteSdpBindId         SdpBindId,
    svcL2BgpVpwsRtePwTemplateId      PWTemplateId,
    svcL2BgpVpwsRteError             DisplayString,
    svcL2BgpVpwsRteLastErrorTime     TimeStamp,
    svcL2BgpVpwsRteControlWord       Unsigned32,
    svcL2BgpVpwsRtePathMtu           Integer32,
    svcL2BgpVpwsRteState             INTEGER,
    svcL2BgpVpwsRteSeqDelivery       Unsigned32,
    svcL2BgpVpwsRteStatus            INTEGER,
    svcL2BgpVpwsRteCsv               Unsigned32,
    svcL2BgpVpwsRteTxStatus          INTEGER,
    svcL2BgpVpwsRtePreference        Unsigned32
}

svcL2BgpVpwsRteVeId              OBJECT-TYPE
    SYNTAX      TmnxSiteId
    MAX-ACCESS  not-accessible
    STATUS      current
    DESCRIPTION
        "The value of svcL2BgpVpwsRteVeId is the low-order 4 bytes of the
         Virtual Switch Instance identifier (VSI-id) of the remote VSI for this
         L2 route."
    ::= { svcL2BgpVpwsRteEntry 1 }

svcL2BgpVpwsRteRD                OBJECT-TYPE
    SYNTAX      TmnxVPNRouteDistinguisher
    MAX-ACCESS  not-accessible
    STATUS      current
    DESCRIPTION
        "The value of svcL2BgpVpwsRteRD is the high-order 6 bytes of the
         Virtual Switch Instance identifier (VSI-id) of the remote VSI for this
         L2 route."
    ::= { svcL2BgpVpwsRteEntry 2 }

svcL2BgpVpwsRteNextHopType       OBJECT-TYPE
    SYNTAX      InetAddressType
    MAX-ACCESS  not-accessible
    STATUS      current
    DESCRIPTION
        "The value of svcL2BgpVpwsRteNextHopType indicates the address type of
         svcL2BgpVpwsRteNextHop."
    ::= { svcL2BgpVpwsRteEntry 3 }

svcL2BgpVpwsRteNextHop           OBJECT-TYPE
    SYNTAX      InetAddress
    MAX-ACCESS  not-accessible
    STATUS      current
    DESCRIPTION
        "The value of svcL2BgpVpwsRteNextHop indicates the IP next hop for this
         L2 route. This value is equivalent to the IP address of the Far End of
         this L2 route."
    ::= { svcL2BgpVpwsRteEntry 4 }

svcL2BgpVpwsRteSdpBindId         OBJECT-TYPE
    SYNTAX      SdpBindId
    MAX-ACCESS  read-only
    STATUS      current
    DESCRIPTION
        "The value of svcL2BgpVpwsRteSdpBindId indicates the SDP bind ID of the
         SDP bind that binds this VPWS context to the VSI indicated by
         svcL2BgpVpwsRteRD, svcL2BgpVpwsRteVeId, and svcL2BgpVpwsRteNextHop.

         The value of svcL2BgpVpwsRteSdpBindId will be '0000000000000000'H if
         there was an error in creating the L2 route and the
         svcL2BgpVpwsRteError will contain a string describing the error."
    ::= { svcL2BgpVpwsRteEntry 5 }

svcL2BgpVpwsRtePwTemplateId      OBJECT-TYPE
    SYNTAX      PWTemplateId
    MAX-ACCESS  read-only
    STATUS      current
    DESCRIPTION
        "The value of svcL2BgpVpwsRtePwTemplateId indicates the PW template
         associated with the SDP bind that binds this VPWS context to the VSI
         indicated by svcL2BgpVpwsRteRD, svcL2BgpVpwsRteVeId, and
         svcL2BgpVpwsRteNextHop."
    ::= { svcL2BgpVpwsRteEntry 6 }

svcL2BgpVpwsRteError             OBJECT-TYPE
    SYNTAX      DisplayString
    MAX-ACCESS  read-only
    STATUS      current
    DESCRIPTION
        "The value of svcL2BgpVpwsRteError indicates an error message
         describing an error encountered when establishing this L2 route entry.
         The value of svcL2BgpVpwsRteError will be a zero-length string when
         the L2 route is successfully established."
    DEFVAL      { "" }
    ::= { svcL2BgpVpwsRteEntry 7 }

svcL2BgpVpwsRteLastErrorTime     OBJECT-TYPE
    SYNTAX      TimeStamp
    MAX-ACCESS  read-only
    STATUS      current
    DESCRIPTION
        "The value of svcL2BgpVpwsRteLastErrorTime indicates the sysUpTime at
         the time of the last error for this L2 route entry.

         If no errors were encountered for this entry since the last
         re-initialization of the local network management subsystem, then this
         object contains a zero value."
    DEFVAL      { 0 }
    ::= { svcL2BgpVpwsRteEntry 8 }

svcL2BgpVpwsRteControlWord       OBJECT-TYPE
    SYNTAX      Unsigned32
    MAX-ACCESS  read-only
    STATUS      current
    DESCRIPTION
        "The value of svcL2BgpVpwsRteControlWord indicates the control word
         advertised for this route."
    ::= { svcL2BgpVpwsRteEntry 9 }

svcL2BgpVpwsRtePathMtu           OBJECT-TYPE
    SYNTAX      Integer32
    MAX-ACCESS  read-only
    STATUS      current
    DESCRIPTION
        "The value of svcL2BgpVpwsRtePathMtu indicates the layer-2 path MTU for
         the pseudo-wire to the PE for this route."
    ::= { svcL2BgpVpwsRteEntry 10 }

svcL2BgpVpwsRteState             OBJECT-TYPE
    SYNTAX      INTEGER {
        up   (1),
        down (2)
    }
    MAX-ACCESS  read-only
    STATUS      current
    DESCRIPTION
        "The value of svcL2BgpVpwsRteState indicates state of the object for
         this route."
    ::= { svcL2BgpVpwsRteEntry 11 }

svcL2BgpVpwsRteSeqDelivery       OBJECT-TYPE
    SYNTAX      Unsigned32
    MAX-ACCESS  read-only
    STATUS      current
    DESCRIPTION
        "The value of svcL2BgpVpwsRteSeqDelivery indicates the sequenced
         delivery flag advertised for this route."
    ::= { svcL2BgpVpwsRteEntry 12 }

svcL2BgpVpwsRteStatus            OBJECT-TYPE
    SYNTAX      INTEGER {
        active   (1),
        inactive (2)
    }
    MAX-ACCESS  read-only
    STATUS      current
    DESCRIPTION
        "The value of svcL2BgpVpwsRteStatus indicates the status of the this
         BGP VPWS L2 Route."
    ::= { svcL2BgpVpwsRteEntry 13 }

svcL2BgpVpwsRteCsv               OBJECT-TYPE
    SYNTAX      Unsigned32
    MAX-ACCESS  read-only
    STATUS      current
    DESCRIPTION
        "The value of svcL2BgpVpwsRteCsv indicates the circuit status vector
         for this route."
    ::= { svcL2BgpVpwsRteEntry 14 }

svcL2BgpVpwsRteTxStatus          OBJECT-TYPE
    SYNTAX      INTEGER {
        active   (1),
        inactive (2)
    }
    MAX-ACCESS  read-only
    STATUS      current
    DESCRIPTION
        "The value of svcL2BgpVpwsRteTxStatus indicates the transmit side
         status of the this BGP VPWS L2 Route."
    ::= { svcL2BgpVpwsRteEntry 15 }

svcL2BgpVpwsRtePreference        OBJECT-TYPE
    SYNTAX      Unsigned32
    MAX-ACCESS  read-only
    STATUS      current
    DESCRIPTION
        "The value of svcL2BgpVpwsRtePreference indicates the preference value
         for this route."
    ::= { svcL2BgpVpwsRteEntry 16 }

END
