LLDP-EXT-DOT3-V2-MIB DEFINITIONS ::= BEGIN

IMPORTS
    MODULE-IDENTITY,
    OBJECT-TYPE,
    Unsigned32
        FROM SNMPv2-SMI
    TruthValue
        FROM SNMPv2-TC
    MODULE-COMPLIANCE,
    OBJECT-GROUP
        FROM SNMPv2-CONF
    ifGeneralInformationGroup
        FROM IF-MIB
    lldpV2Extensions,
    lldpV2LocPortIfIndex,
    lldpV2RemTimeMark, 
    lldpV2RemLocalIfIndex,
    lldpV2RemLocalDestMACAddress,
    lldpV2RemIndex,
    lldpV2PortConfigEntry
        FROM LLDP-V2-MIB
    LldpV2PowerPortClass
        FROM LLDP-V2-TC-MIB;

lldpV2Xdot3MIB MODULE-IDENTITY
    LAST-UPDATED "201305241753Z"  -- Fri May 24 17:53 UTC 2013
    ORGANIZATION "IEEE 802.1 Working Group"
    CONTACT-INFO 
            "WG-URL: http://grouper.ieee.org/groups/802/1/index.html
            WG-EMail: STDS-802-1-L@LISTSERV.IEEE.ORG

            Contact: Tony Jeffree
            Postal:  11a Poplar Grove
                     Sale 
                     Cheshire M33 3AX
                     UK
            Tel:     +44-161-973-4278
            E-mail:  tony@jeffree.co.uk"
    DESCRIPTION
            "The LLDP Management Information Base extension module for
            IEEE 802.3 organizationally defined discovery information.

            In order to assure the uniqueness of the LLDP-MIB,
            lldpV2Xdot3MIB is branched from lldpV2Extensions using OUI value
            as the node.  An OUI/'company_id' is a 24 bit globally unique
            assigned number referenced by various standards.

            Unless otherwise indicated, the references in this
            MIB module are to IEEE 802.1AB-2009.

            Copyright (C) IEEE (2009).  This version of this MIB module
            is published as Annex F.6.5 of IEEE Std 802.1AB-2009;
            see the standard itself for full legal notices."

    REVISION "201305241753Z"  -- Fri May 24 17:53 UTC 2013
    DESCRIPTION
            "Enterasys Networks:
             Added a p8021 prefix to all leaves to avoid naming conflicts
             with IEEE8023-DOT3-LLDP-EXT-V2-MIB."

    REVISION "200906080000Z" -- June 08, 2009

    DESCRIPTION
            "Published as part of IEEE Std 802.1AB-2009 revision.
            This revision incorporated changes to the MIB to
            support the use of LLDP with multiple destination MAC
            addresses, and to deprecate the Link Aggregation TLV
            (now moved to the 802.1 extension MIB)."

-- OUI for IEEE 802.3 is 4623 (00-12-0F)
   ::= { lldpV2Extensions 4623 } 

------------------------------------------------------------------------------
------------------------------------------------------------------------------
--
-- Organizationally Defined Information Extension - IEEE 802.3
--
------------------------------------------------------------------------------
------------------------------------------------------------------------------

p8021lldpV2Xdot3Objects    OBJECT IDENTIFIER ::= { lldpV2Xdot3MIB 1 }

-- LLDP IEEE 802.3 extension MIB groups
p8021lldpV2Xdot3Config     OBJECT IDENTIFIER ::= { p8021lldpV2Xdot3Objects 1 }
p8021lldpV2Xdot3LocalData  OBJECT IDENTIFIER ::= { p8021lldpV2Xdot3Objects 2 }
p8021lldpV2Xdot3RemoteData OBJECT IDENTIFIER ::= { p8021lldpV2Xdot3Objects 3 }



------------------------------------------------------------------------------
-- IEEE 802.3 - Configuration
------------------------------------------------------------------------------


--
-- Version 2 of lldpV2Xdot3PortConfigTable
-- supports use of multiple destination MAC addresses
--


p8021lldpV2Xdot3PortConfigTable OBJECT-TYPE
    SYNTAX      SEQUENCE OF LldpV2Xdot3PortConfigEntry
    MAX-ACCESS  not-accessible
    STATUS      current
    DESCRIPTION
            "A table that controls selection of LLDP TLVs to be transmitted 
            on individual ports."
    ::= { p8021lldpV2Xdot3Config 1 }

p8021lldpV2Xdot3PortConfigEntry  OBJECT-TYPE
    SYNTAX      LldpV2Xdot3PortConfigEntry
    MAX-ACCESS  not-accessible
    STATUS      current
    DESCRIPTION
            "LLDP configuration information that controls the
            transmission of IEEE 802.3 organizationally defined TLVs on
            LLDP transmission capable ports.

            This configuration object augments the lldpV2PortConfigEntry of
            the LLDP-MIB, therefore it is only present along with the port
            configuration defined by the associated lldpV2PortConfigEntry
            entry.

            Each active lldpV2Xdot3PortConfigEntry is restored from non-volatile
            storage (along with the corresponding lldpV2PortConfigEntry)
            after a re-initialization of the management system."
    AUGMENTS { lldpV2PortConfigEntry }
    ::= { p8021lldpV2Xdot3PortConfigTable 1 }

LldpV2Xdot3PortConfigEntry ::= SEQUENCE {
      p8021lldpV2Xdot3PortConfigTLVsTxEnable  BITS
}

p8021lldpV2Xdot3PortConfigTLVsTxEnable  OBJECT-TYPE
    SYNTAX      BITS {
            macPhyConfigStatus(0),
            powerViaMDI(1),
            unused(2), --avoids re-use of the old link agg bit number 
            maxFrameSize(3)
    }
    MAX-ACCESS  read-write
    STATUS      current
    DESCRIPTION
            "The lldpV2Xdot3PortConfigTLVsTxEnable, defined as a bitmap,
            includes the IEEE 802.3 organizationally defined set of LLDP
            TLVs whose transmission is allowed on the local LLDP agent by
            the network management.  Each bit in the bitmap corresponds
            to an IEEE 802.3 subtype associated with a specific IEEE
            802.3 optional TLV.  The bit 0 is not used since there is
            no corresponding subtype.

            The bit 'macPhyConfigStatus(0)' indicates that LLDP agent
            should transmit 'MAC/PHY configuration/status TLV'.

            The bit 'powerViaMDI(1)' indicates that LLDP agent should
            transmit 'Power via MDI TLV'.

            The bit 'unused(2)' is no longer used; this was used for
            the 'Link Aggregation TLV' in the previous version.

            The bit 'maxFrameSize(3)' indicates that LLDP agent should
            transmit 'Maximum-frame-size TLV'.

            The default value for lldpV2Xdot3PortConfigTLVsTxEnable object
            is an empty set, which means no enumerated values are set.

            The value of this object is restored from non-volatile
            storage after a re-initialization of the management system."
    REFERENCE 
            "9.1.2.1"
    DEFVAL  { { } }
    ::= { p8021lldpV2Xdot3PortConfigEntry  1 }



------------------------------------------------------------------------------
-- IEEE 802.3 - Local Device Information 
------------------------------------------------------------------------------

---
--- lldpV2Xdot3LocPortTable: Ethernet Port AutoNeg/Speed/Duplex
---                        Information Table
--- V2 modified to be indexed by ifIndex.
---

p8021lldpV2Xdot3LocPortTable OBJECT-TYPE
    SYNTAX      SEQUENCE OF P8021LldpV2Xdot3LocPortEntry
    MAX-ACCESS  not-accessible
    STATUS      current
    DESCRIPTION
            "This table contains one row per port of Ethernet port
            information (as a part of the LLDP 802.3 organizational
            extension) on the local system known to this agent."
    ::= { p8021lldpV2Xdot3LocalData 1 }

p8021lldpV2Xdot3LocPortEntry OBJECT-TYPE
    SYNTAX      P8021LldpV2Xdot3LocPortEntry
    MAX-ACCESS  not-accessible
    STATUS      current
    DESCRIPTION
            "Information about a particular port component."
    INDEX   { lldpV2LocPortIfIndex }
    ::= { p8021lldpV2Xdot3LocPortTable 1 }

P8021LldpV2Xdot3LocPortEntry ::= SEQUENCE {
         p8021lldpV2Xdot3LocPortAutoNegSupported     TruthValue,
         p8021lldpV2Xdot3LocPortAutoNegEnabled       TruthValue,
         p8021lldpV2Xdot3LocPortAutoNegAdvertisedCap OCTET STRING,
         p8021lldpV2Xdot3LocPortOperMauType          Unsigned32
}

p8021lldpV2Xdot3LocPortAutoNegSupported OBJECT-TYPE
    SYNTAX      TruthValue
    MAX-ACCESS  read-only
    STATUS      current
    DESCRIPTION
            "The truth value used to indicate whether the given port
            (associated with the local system) supports Auto-negotiation."
    REFERENCE 
            "F.2.1"
    ::= { p8021lldpV2Xdot3LocPortEntry 1 }

p8021lldpV2Xdot3LocPortAutoNegEnabled  OBJECT-TYPE
    SYNTAX      TruthValue
    MAX-ACCESS  read-only
    STATUS      current
    DESCRIPTION
            "The truth value used to indicate whether port
            Auto-negotiation is enabled on the given port associated
            with the local system."
    REFERENCE 
            "F.2.1"
    ::= { p8021lldpV2Xdot3LocPortEntry 2 }

p8021lldpV2Xdot3LocPortAutoNegAdvertisedCap OBJECT-TYPE
    SYNTAX      OCTET STRING(SIZE(2))
    MAX-ACCESS  read-only
    STATUS      current
    DESCRIPTION
            "This object contains the value (bitmap) of the
            ifMauAutoNegCapAdvertisedBits object (defined in IETF RFC
            3636) which is associated with the given port on the
            local system."
    REFERENCE 
            "F.2.2"
    ::= { p8021lldpV2Xdot3LocPortEntry 3 }

p8021lldpV2Xdot3LocPortOperMauType  OBJECT-TYPE
    SYNTAX      Unsigned32(0..2147483647)
    MAX-ACCESS  read-only
    STATUS      current
    DESCRIPTION
            "An integer value that indicates the operational MAU type
            of the given port on the local system.

            This object contains the integer value derived from the
            list position of the corresponding dot3MauType as listed 
            in IETF RFC 4836 (or subsequent revisions) and is equal
            to the last number in the respective dot3MauType OID.
           
            For example, if the ifMauType object is dot3MauType1000BaseTHD
            which corresponds to {dot3MauType 29}, the numerical value of
            this field is 29. For MAU types not listed in RFC 4836
            (or subsequent revisions), the value of this field shall be
            set to zero."
    REFERENCE 
            "F.2.3"
    ::= { p8021lldpV2Xdot3LocPortEntry 4 }



---
---
--- lldpV2Xdot3LocPowerTable: Power Ethernet Information Table
--- V2 modified to be indexed by ifIndex.
---
---

p8021lldpV2Xdot3LocPowerTable OBJECT-TYPE
    SYNTAX      SEQUENCE OF LldpV2Xdot3LocPowerEntry
    MAX-ACCESS  not-accessible
    STATUS      current
    DESCRIPTION
            "This table contains one row per port of power ethernet 
            information (as a part of the LLDP 802.3 organizational
            extension) on the local system known to this agent."
    ::= { p8021lldpV2Xdot3LocalData 2 }

p8021lldpV2Xdot3LocPowerEntry OBJECT-TYPE
    SYNTAX      LldpV2Xdot3LocPowerEntry
    MAX-ACCESS  not-accessible
    STATUS      current
    DESCRIPTION
            "Information about a particular port component."
    INDEX   { lldpV2LocPortIfIndex }
    ::= { p8021lldpV2Xdot3LocPowerTable 1 }

LldpV2Xdot3LocPowerEntry ::= SEQUENCE {
         p8021lldpV2Xdot3LocPowerPortClass           LldpV2PowerPortClass,
         p8021lldpV2Xdot3LocPowerMDISupported        TruthValue,
         p8021lldpV2Xdot3LocPowerMDIEnabled           TruthValue,
         p8021lldpV2Xdot3LocPowerPairControlable     TruthValue,
         p8021lldpV2Xdot3LocPowerPairs               Unsigned32,
         p8021lldpV2Xdot3LocPowerClass               Unsigned32
} 


p8021lldpV2Xdot3LocPowerPortClass  OBJECT-TYPE
    SYNTAX      LldpV2PowerPortClass
    MAX-ACCESS  read-only
    STATUS      current
    DESCRIPTION
            "The value that identifies the port Class of the given port
            associated with the local system."
    REFERENCE 
            "F.3.1"
    ::= { p8021lldpV2Xdot3LocPowerEntry 1 }

p8021lldpV2Xdot3LocPowerMDISupported  OBJECT-TYPE
    SYNTAX      TruthValue
    MAX-ACCESS  read-only
    STATUS      current
    DESCRIPTION
            "The truth value used to indicate whether the MDI power is
            supported on the given port associated with the local system."
    REFERENCE 
            "F.3.1"
    ::= { p8021lldpV2Xdot3LocPowerEntry 2 }

p8021lldpV2Xdot3LocPowerMDIEnabled  OBJECT-TYPE
    SYNTAX      TruthValue
    MAX-ACCESS  read-only
    STATUS      current
    DESCRIPTION
            "The truth value used to identify whether MDI power is
            enabled on the given port associated with the local system."
    REFERENCE 
            "F.3.1"
    ::= { p8021lldpV2Xdot3LocPowerEntry 3 }

p8021lldpV2Xdot3LocPowerPairControlable  OBJECT-TYPE
    SYNTAX      TruthValue
    MAX-ACCESS  read-only
    STATUS      current
    DESCRIPTION
            "The truth value is derived from the value of
            pethPsePortPowerPairsControlAbility object (defined in IETF
            RFC 3621) and is used to indicate whether the pair selection
            can be controlled on the given port associated with the
            local system."
    REFERENCE 
            "F.3.1"
    ::= { p8021lldpV2Xdot3LocPowerEntry 4 }

p8021lldpV2Xdot3LocPowerPairs  OBJECT-TYPE
    SYNTAX      Unsigned32(1|2)
    MAX-ACCESS  read-only
    STATUS      current
    DESCRIPTION
            "This object contains the value of the pethPsePortPowerPairs
            object (defined in IETF RFC 3621) which is associated with
            the given port on the local system."
    REFERENCE 
            "F.3.2"
    ::= { p8021lldpV2Xdot3LocPowerEntry 5 }

p8021lldpV2Xdot3LocPowerClass  OBJECT-TYPE
    SYNTAX      Unsigned32(1|2|3|4|5)
    MAX-ACCESS  read-only
    STATUS      current
    DESCRIPTION
            "This object contains the value of the
            pethPsePortPowerClassifications object (defined in IETF
            RFC 3621) which is associated with the given port on the
            local system."
    REFERENCE 
            "F.3.3"
    ::= { p8021lldpV2Xdot3LocPowerEntry 6 }



---
---
--- lldpV2Xdot3LocMaxFrameSizeTable: Maximum Frame Size information 
--- V2 modified to be indexed by ifIndex.
---
---
p8021lldpV2Xdot3LocMaxFrameSizeTable  OBJECT-TYPE
    SYNTAX      SEQUENCE OF LldpV2Xdot3LocMaxFrameSizeEntry
    MAX-ACCESS  not-accessible
    STATUS      current
    DESCRIPTION
            "This table contains one row per port of maximum frame 
            size information (as a part of the LLDP 802.3 organizational
            extension) on the local system known to this agent."
    ::= { p8021lldpV2Xdot3LocalData 3 }

p8021lldpV2Xdot3LocMaxFrameSizeEntry OBJECT-TYPE
    SYNTAX      LldpV2Xdot3LocMaxFrameSizeEntry
    MAX-ACCESS  not-accessible
    STATUS      current
    DESCRIPTION
            "Maximum Frame Size information about a particular port
            component."
    INDEX   { lldpV2LocPortIfIndex }
    ::= { p8021lldpV2Xdot3LocMaxFrameSizeTable 1 }

LldpV2Xdot3LocMaxFrameSizeEntry ::= SEQUENCE {
        p8021lldpV2Xdot3LocMaxFrameSize             Unsigned32
} 

p8021lldpV2Xdot3LocMaxFrameSize OBJECT-TYPE
    SYNTAX      Unsigned32(0..65535)
    MAX-ACCESS  read-only
    STATUS      current
    DESCRIPTION
            "An integer value indicating the maximum supported frame 
             size in octets on the given port of the local system."
    REFERENCE 
            "F.4.1"
    ::= { p8021lldpV2Xdot3LocMaxFrameSizeEntry 1 }



------------------------------------------------------------------------------
-- IEEE 802.3 - Remote Devices Information
------------------------------------------------------------------------------

---
---
--- lldpV2Xdot3RemPortTable: Ethernet Information Table
--- V2 modified to be indexed by ifIndex and destination MAC address.
---
---

p8021lldpV2Xdot3RemPortTable OBJECT-TYPE
    SYNTAX      SEQUENCE OF LldpV2Xdot3RemPortEntry
    MAX-ACCESS  not-accessible
    STATUS      current
    DESCRIPTION
            "This table contains Ethernet port information (as a part
            of the LLDP 802.3 organizational extension) of the remote
            system."
    ::= { p8021lldpV2Xdot3RemoteData 1 }

p8021lldpV2Xdot3RemPortEntry OBJECT-TYPE
    SYNTAX      LldpV2Xdot3RemPortEntry
    MAX-ACCESS  not-accessible
    STATUS      current
    DESCRIPTION
            "Information about a particular physical network connection."
    INDEX   { lldpV2RemTimeMark,
              lldpV2RemLocalIfIndex, 
              lldpV2RemLocalDestMACAddress,
              lldpV2RemIndex }
    ::= { p8021lldpV2Xdot3RemPortTable 1 }

LldpV2Xdot3RemPortEntry ::= SEQUENCE {
              p8021lldpV2Xdot3RemPortAutoNegSupported     TruthValue,
              p8021lldpV2Xdot3RemPortAutoNegEnabled       TruthValue,
              p8021lldpV2Xdot3RemPortAutoNegAdvertisedCap OCTET STRING,
              p8021lldpV2Xdot3RemPortOperMauType          Unsigned32
} 


p8021lldpV2Xdot3RemPortAutoNegSupported OBJECT-TYPE
    SYNTAX      TruthValue
    MAX-ACCESS  read-only
    STATUS      current
    DESCRIPTION
            "The truth value used to indicate whether the given port
            (associated with remote system) supports Auto-negotiation."
    REFERENCE 
            "F.2.1"
    ::= { p8021lldpV2Xdot3RemPortEntry 1 }

p8021lldpV2Xdot3RemPortAutoNegEnabled  OBJECT-TYPE
    SYNTAX      TruthValue
    MAX-ACCESS  read-only
    STATUS      current
    DESCRIPTION
            "The truth value used to indicate whether port
            Auto-negotiation is enabled on the given port associated
            with the remote system."
    REFERENCE 
            "F.2.1"
    ::= { p8021lldpV2Xdot3RemPortEntry 2 }

p8021lldpV2Xdot3RemPortAutoNegAdvertisedCap  OBJECT-TYPE
    SYNTAX      OCTET STRING(SIZE(2))
    MAX-ACCESS  read-only
    STATUS      current
    DESCRIPTION
            "This object contains the value (bitmap) of the
            ifMauAutoNegCapAdvertisedBits object (defined in IETF RFC
            3636) which is associated with the given port on the
            remote system."
    REFERENCE 
            "F.2.2"
    ::= { p8021lldpV2Xdot3RemPortEntry 3 }

p8021lldpV2Xdot3RemPortOperMauType OBJECT-TYPE
    SYNTAX      Unsigned32(0..2147483647)
    MAX-ACCESS  read-only
    STATUS      current
    DESCRIPTION
            "An integer value that indicates the operational MAU type
            of the sending device.

            This object contains the integer value derived from the
            list position of the corresponding dot3MauType as listed in
            in IETF RFC 4836 (or subsequent revisions) and is equal
            to the last number in the respective dot3MauType OID.
           
            For example, if the ifMauType object is dot3MauType1000BaseTHD
            which corresponds to {dot3MauType 29}, the numerical value of
            this field is 29. For MAU types not listed in RFC 4836
            (or subsequent revisions), the value of this field shall be
            set to zero."
    REFERENCE 
            "F.2.3"
    ::= { p8021lldpV2Xdot3RemPortEntry 4 }


---
---
--- lldpV2Xdot3RemPowerTable: Power Ethernet Information Table
--- V2 modified to be indexed by ifIndex and destination MAC address.
---
---

p8021lldpV2Xdot3RemPowerTable OBJECT-TYPE
    SYNTAX      SEQUENCE OF LldpV2Xdot3RemPowerEntry
    MAX-ACCESS  not-accessible
    STATUS      current
    DESCRIPTION
            "This table contains Ethernet power information (as a part
            of the LLDP 802.3 organizational extension) of the remote
            system."
    ::= { p8021lldpV2Xdot3RemoteData 2 }

p8021lldpV2Xdot3RemPowerEntry OBJECT-TYPE
    SYNTAX      LldpV2Xdot3RemPowerEntry
    MAX-ACCESS  not-accessible
    STATUS      current
    DESCRIPTION
            "Information about a particular physical network connection."
    INDEX   { lldpV2RemTimeMark,
              lldpV2RemLocalIfIndex,
              lldpV2RemLocalDestMACAddress,
              lldpV2RemIndex }
    ::= { p8021lldpV2Xdot3RemPowerTable 1 }

LldpV2Xdot3RemPowerEntry ::= SEQUENCE {
              p8021lldpV2Xdot3RemPowerPortClass           LldpV2PowerPortClass,
              p8021lldpV2Xdot3RemPowerMDISupported        TruthValue,
              p8021lldpV2Xdot3RemPowerMDIEnabled          TruthValue,
              p8021lldpV2Xdot3RemPowerPairControlable     TruthValue,
              p8021lldpV2Xdot3RemPowerPairs               Unsigned32,
              p8021lldpV2Xdot3RemPowerClass               Unsigned32
} 


p8021lldpV2Xdot3RemPowerPortClass  OBJECT-TYPE
    SYNTAX      LldpV2PowerPortClass
    MAX-ACCESS  read-only
    STATUS      current
    DESCRIPTION
            "The value that identifies the port Class of the given port
            associated with the remote system."
    REFERENCE 
            "F.3.1"
    ::= { p8021lldpV2Xdot3RemPowerEntry 1 }

p8021lldpV2Xdot3RemPowerMDISupported  OBJECT-TYPE
    SYNTAX      TruthValue
    MAX-ACCESS  read-only
    STATUS      current
    DESCRIPTION
            "The truth value used to indicate whether the MDI power
            is supported on the given port associated with the remote
            system."
    REFERENCE 
            "F.3.1"
    ::= { p8021lldpV2Xdot3RemPowerEntry 2 }

p8021lldpV2Xdot3RemPowerMDIEnabled  OBJECT-TYPE
    SYNTAX      TruthValue
    MAX-ACCESS  read-only
    STATUS      current
    DESCRIPTION
            "The truth value used to identify whether MDI power is
            enabled on the given port associated with the remote system."
    REFERENCE 
            "F.3.1"
    ::= { p8021lldpV2Xdot3RemPowerEntry 3 }

p8021lldpV2Xdot3RemPowerPairControlable  OBJECT-TYPE
    SYNTAX      TruthValue
    MAX-ACCESS  read-only
    STATUS      current
    DESCRIPTION
            "The truth value is derived from the value of
            pethPsePortPowerPairsControlAbility object (defined in IETF
            RFC 3621) and is used to indicate whether the pair selection
            can be controlled on the given port associated with the
            remote system."
    REFERENCE 
            "F.3.1"
    ::= { p8021lldpV2Xdot3RemPowerEntry 4 }

p8021lldpV2Xdot3RemPowerPairs  OBJECT-TYPE
    SYNTAX      Unsigned32(1|2)
    MAX-ACCESS  read-only
    STATUS      current
    DESCRIPTION
            "This object contains the value of the pethPsePortPowerPairs
            object (defined in IETF RFC 3621) which is associated with
            the given port on the remote system."
    REFERENCE 
            "F.3.2"
    ::= { p8021lldpV2Xdot3RemPowerEntry 5 }

p8021lldpV2Xdot3RemPowerClass  OBJECT-TYPE
    SYNTAX      Unsigned32(1|2|3|4|5)
    MAX-ACCESS  read-only
    STATUS      current
    DESCRIPTION
            "This object contains the value of the
            pethPsePortPowerClassifications object (defined in IETF
            RFC 3621) which is associated with the given port on the
            remote system."
    REFERENCE 
            "F.3.3"
    ::= { p8021lldpV2Xdot3RemPowerEntry 6 }



---
--- lldpV2Xdot3RemMaxFrameSizeTable: Maximum Frame Size information 
--- V2 modified to be indexed by ifIndex and destination MAC address.
---
---

p8021lldpV2Xdot3RemMaxFrameSizeTable  OBJECT-TYPE
    SYNTAX      SEQUENCE OF LldpV2Xdot3RemMaxFrameSizeEntry
    MAX-ACCESS  not-accessible
    STATUS      current
    DESCRIPTION
            "This table contains one row per port/destination
            address pair of maximum frame 
            size information (as a part of the LLDP IEEE 802.3 
            organizational extension) of the remote system."
    ::= { p8021lldpV2Xdot3RemoteData 3 }

p8021lldpV2Xdot3RemMaxFrameSizeEntry OBJECT-TYPE
    SYNTAX      LldpV2Xdot3RemMaxFrameSizeEntry
    MAX-ACCESS  not-accessible
    STATUS      current
    DESCRIPTION
            "Maximum Frame Size information about a particular port
            component."
    INDEX   { lldpV2RemTimeMark,
              lldpV2RemLocalIfIndex,
              lldpV2RemLocalDestMACAddress,
              lldpV2RemIndex }
    ::= { p8021lldpV2Xdot3RemMaxFrameSizeTable 1 }

LldpV2Xdot3RemMaxFrameSizeEntry ::= SEQUENCE {
              p8021lldpV2Xdot3RemMaxFrameSize   Unsigned32
}

p8021lldpV2Xdot3RemMaxFrameSize OBJECT-TYPE
    SYNTAX      Unsigned32(0..65535)
    MAX-ACCESS  read-only
    STATUS      current
    DESCRIPTION
            "An integer value indicating the maximum supported frame 
             size in octets on the port component associated with the 
             remote system."
    REFERENCE 
            "F.4.1"
    ::= { p8021lldpV2Xdot3RemMaxFrameSizeEntry 1 }


------------------------------------------------------------------------------
-- Conformance Information
------------------------------------------------------------------------------
p8021lldpV2Xdot3Conformance OBJECT IDENTIFIER ::= { lldpV2Xdot3MIB 2 }
p8021lldpV2Xdot3Compliances OBJECT IDENTIFIER ::= { p8021lldpV2Xdot3Conformance 1 }
p8021lldpV2Xdot3Groups      OBJECT IDENTIFIER ::= { p8021lldpV2Xdot3Conformance 2 }

-- compliance statements


p8021lldpV2Xdot3TxRxCompliance MODULE-COMPLIANCE
    STATUS  current
    DESCRIPTION
            "A compliance statement for SNMP entities that implement
            the LLDP 802.3 organizational extension MIB.

            This group is mandatory for all agents that implement the 
            LLDP 802.3 organizational extension in TX and/or RX mode.

            This version defines compliance requirements for
            V2 of the LLDP MIB."
    MODULE  -- this module
        MANDATORY-GROUPS { p8021lldpV2Xdot3ConfigGroup
        }
    MODULE  IF-MIB -- The interfaces Group MIB, RFC 2863
        MANDATORY-GROUPS { ifGeneralInformationGroup
        }
    ::= { p8021lldpV2Xdot3Compliances 1 }

p8021lldpV2Xdot3TxCompliance MODULE-COMPLIANCE
    STATUS  current
    DESCRIPTION
            "The compliance statement for SNMP entities which implement
            the LLDP 802.3 organizational extension MIB.

            This group is mandatory for agents which implement the 
            LLDP 802.3 organizational extension in the TX mode.

            This version defines compliance requirements for
            V2 of the LLDP MIB."
    MODULE  -- this module
        MANDATORY-GROUPS { p8021lldpV2Xdot3LocSysGroup }
    ::= { p8021lldpV2Xdot3Compliances 2 }

p8021lldpV2Xdot3RxCompliance MODULE-COMPLIANCE
    STATUS  current
    DESCRIPTION
            "The compliance statement for SNMP entities which implement
            the LLDP 802.3 organizational extension MIB.

            This group is mandatory for agents which implement the 
            LLDP 802.3 organizational extension in the RX mode.

            This version defines compliance requirements for
            V2 of the LLDP MIB."
    MODULE  -- this module
        MANDATORY-GROUPS { p8021lldpV2Xdot3RemSysGroup }
    ::= { p8021lldpV2Xdot3Compliances 3 }


-- MIB groupings


p8021lldpV2Xdot3ConfigGroup    OBJECT-GROUP
    OBJECTS {
        p8021lldpV2Xdot3PortConfigTLVsTxEnable
    }
    STATUS  current
    DESCRIPTION
            "The collection of objects which are used to configure the
            LLDP 802.3 organizational extension implementation behavior. "
    ::= { p8021lldpV2Xdot3Groups 1 }

p8021lldpV2Xdot3LocSysGroup  OBJECT-GROUP
    OBJECTS {
        p8021lldpV2Xdot3LocPortAutoNegSupported,
        p8021lldpV2Xdot3LocPortAutoNegEnabled,
        p8021lldpV2Xdot3LocPortAutoNegAdvertisedCap,
        p8021lldpV2Xdot3LocPortOperMauType,
        p8021lldpV2Xdot3LocPowerPortClass,
        p8021lldpV2Xdot3LocPowerMDISupported,
        p8021lldpV2Xdot3LocPowerMDIEnabled,
        p8021lldpV2Xdot3LocPowerPairControlable,
        p8021lldpV2Xdot3LocPowerPairs,
        p8021lldpV2Xdot3LocPowerClass,
        p8021lldpV2Xdot3LocMaxFrameSize
    }
    STATUS  current
    DESCRIPTION
            "The collection of objects which are used to represent LLDP
            802.3 organizational extension Local Device Information. "
    ::= { p8021lldpV2Xdot3Groups 2 }

p8021lldpV2Xdot3RemSysGroup  OBJECT-GROUP
    OBJECTS {
        p8021lldpV2Xdot3RemPortAutoNegSupported,
        p8021lldpV2Xdot3RemPortAutoNegEnabled,
        p8021lldpV2Xdot3RemPortAutoNegAdvertisedCap,
        p8021lldpV2Xdot3RemPortOperMauType,
        p8021lldpV2Xdot3RemPowerPortClass,
        p8021lldpV2Xdot3RemPowerMDISupported,
        p8021lldpV2Xdot3RemPowerMDIEnabled,
        p8021lldpV2Xdot3RemPowerPairControlable,
        p8021lldpV2Xdot3RemPowerPairs,
        p8021lldpV2Xdot3RemPowerClass,
        p8021lldpV2Xdot3RemMaxFrameSize
    }
    STATUS  current
    DESCRIPTION
            "The collection of objects which are used to represent LLDP
            802.3 organizational extension Local Device Information. "
    ::= { p8021lldpV2Xdot3Groups 3 }

END
