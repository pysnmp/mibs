--
-- IRT-DAB-SINGLETRANSMITTER-MIB.my
-- MIB generated by MG-SOFT Visual MIB Builder Version 6.0  Build 88
-- Friday, May 04, 2007 at 18:15:31
--

	IRT-DAB-SINGLETRANSMITTER-MIB DEFINITIONS ::= BEGIN
 
		IMPORTS
			eventTimeStamp, eventPriority, eventCounter, mibRelease			
				FROM IRT-COMMONVARBINDS-MIB			
			dab, Input1Input2, SelectManualAuto, SelectOnOff, PresentNotPresent, 
			FaultOK, WarningOK, OkNotOk, LocalRemote, MuteOk, 
			SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			TruthValue			
				FROM SNMPv2-TC;
	
	
		-- 1.3.6.1.4.1.19831.1.1.2.1
		dabSingleTransmitter MODULE-IDENTITY 
			LAST-UPDATED "200705041400Z"		-- May 04, 2007 at 14:00 GMT
			ORGANIZATION 
				"IRT for WORKING-GROUP-TC-MIB"
			CONTACT-INFO 
				"Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"DAB Single Transmitter
				
				branch definition
				
				1st level
				
				events               OBJECT IDENTIFIER ::= { dabSingleTransmitter 0 }
				dabSTGeneral         OBJECT IDENTIFIER ::= { dabSingleTransmitter 1 }
				dabSTEventEnable     OBJECT IDENTIFIER ::= { dabSingleTransmitter 2 }
				dabSTEventPriority   OBJECT IDENTIFIER ::= { dabSingleTransmitter 3 }
				groups               OBJECT IDENTIFIER ::= { dabSingleTransmitter 4 }
				
				2nd level
				
				dabSTEventEnableGeneral     OBJECT IDENTIFIER ::= { dabSTEventEnable 1 }
				dabSTEventPriorityGeneral   OBJECT IDENTIFIER ::= { dabSTEventPriority 1 }
				
				end branch
				"
			REVISION "200705041400Z"		-- May 04, 2007 at 14:00 GMT
			DESCRIPTION 
				"change SFNMode, LocalMode (description) and Module-COMPLIANCE
				"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dab 1 }

		
	
	
--
-- Node definitions
--
	
-- dab single transmitter events
		-- 1.3.6.1.4.1.19831.1.1.2.1.0
		dabEventsST OBJECT IDENTIFIER ::= { dabSingleTransmitter 0 }

		
		-- 1.3.6.1.4.1.19831.1.1.2.1.0.1
		dabSTInputPreselectionEvent NOTIFICATION-TYPE
			OBJECTS { sysDescr, sysName, sysLocation, eventTimeStamp, eventPriority, 
				eventCounter, dabSTInputPreselection }
			STATUS current
			DESCRIPTION 
				"Description.dabSTInputPreselection notification"
			::= { dabEventsST 1 }

		
		-- 1.3.6.1.4.1.19831.1.1.2.1.0.2
		dabSTInputAutomaticEvent NOTIFICATION-TYPE
			OBJECTS { sysDescr, sysName, sysLocation, eventTimeStamp, eventPriority, 
				eventCounter, dabSTInputAutomatic }
			STATUS current
			DESCRIPTION 
				"Description. dabSTInputAutomatic notification"
			::= { dabEventsST 2 }

		
		-- 1.3.6.1.4.1.19831.1.1.2.1.0.3
		dabSTTransmitterOpModeEvent NOTIFICATION-TYPE
			OBJECTS { sysDescr, sysName, sysLocation, eventTimeStamp, eventPriority, 
				eventCounter, dabSTTransmitterOpMode }
			STATUS current
			DESCRIPTION 
				"Description. dabSTTransmitterOpMode notification"
			::= { dabEventsST 3 }

		
		-- 1.3.6.1.4.1.19831.1.1.2.1.0.4
		dabSTRFPresentEvent NOTIFICATION-TYPE
			OBJECTS { sysDescr, sysName, sysLocation, eventTimeStamp, eventPriority, 
				eventCounter, dabSTRFPresent }
			STATUS current
			DESCRIPTION 
				"Description. dabSTRFPresent notification"
			::= { dabEventsST 4 }

		
		-- 1.3.6.1.4.1.19831.1.1.2.1.0.5
		dabSTResetFaultEvent NOTIFICATION-TYPE
			OBJECTS { sysDescr, sysName, sysLocation, eventTimeStamp, eventPriority, 
				eventCounter, dabSTResetFault }
			STATUS obsolete
			DESCRIPTION 
				"Notification is inactive!
				
				Description. dabSTResetFault notification"
			::= { dabEventsST 5 }

		
		-- 1.3.6.1.4.1.19831.1.1.2.1.0.6
		dabSTFaultEvent NOTIFICATION-TYPE
			OBJECTS { sysDescr, sysName, sysLocation, eventTimeStamp, eventPriority, 
				eventCounter, dabSTFault }
			STATUS current
			DESCRIPTION 
				"Description. dabSTFault notification"
			::= { dabEventsST 6 }

		
		-- 1.3.6.1.4.1.19831.1.1.2.1.0.7
		dabSTWarningEvent NOTIFICATION-TYPE
			OBJECTS { sysDescr, sysName, sysLocation, eventTimeStamp, eventPriority, 
				eventCounter, dabSTWarning }
			STATUS current
			DESCRIPTION 
				"Description. dabSTWarning notification"
			::= { dabEventsST 7 }

		
		-- 1.3.6.1.4.1.19831.1.1.2.1.0.8
		dabSTInput1OKEvent NOTIFICATION-TYPE
			OBJECTS { sysDescr, sysName, sysLocation, eventTimeStamp, eventPriority, 
				eventCounter, dabSTInput1OK }
			STATUS current
			DESCRIPTION 
				"Description.dabSTInput1OK notification"
			::= { dabEventsST 8 }

		
		-- 1.3.6.1.4.1.19831.1.1.2.1.0.9
		dabSTInput2OKEvent NOTIFICATION-TYPE
			OBJECTS { sysDescr, sysName, sysLocation, eventTimeStamp, eventPriority, 
				eventCounter, dabSTInput2OK }
			STATUS current
			DESCRIPTION 
				"Description.dabSTInput2OK notification"
			::= { dabEventsST 9 }

		
		-- 1.3.6.1.4.1.19831.1.1.2.1.0.10
		dabSTLocalModeEvent NOTIFICATION-TYPE
			OBJECTS { sysDescr, sysName, sysLocation, eventTimeStamp, eventPriority, 
				eventCounter, dabSTLocalMode }
			STATUS current
			DESCRIPTION 
				"Description. dabSTLocalMode notification"
			::= { dabEventsST 10 }

		
		-- 1.3.6.1.4.1.19831.1.1.2.1.0.11
		dabSTActiveInputEvent NOTIFICATION-TYPE
			OBJECTS { sysDescr, sysName, sysLocation, eventTimeStamp, eventPriority, 
				eventCounter, dabSTActiveInput }
			STATUS current
			DESCRIPTION 
				"Description. dabSTActiveInput notification"
			::= { dabEventsST 11 }

		
		-- 1.3.6.1.4.1.19831.1.1.2.1.0.12
		dabSTSFNModeEvent NOTIFICATION-TYPE
			OBJECTS { sysDescr, sysName, sysLocation, eventTimeStamp, eventPriority, 
				eventCounter, dabSTSFNMode }
			STATUS current
			DESCRIPTION 
				"Description. dabSTSFNMode notification"
			::= { dabEventsST 12 }

		
		-- 1.3.6.1.4.1.19831.1.1.2.1.0.13
		dabSTRefFaultEvent NOTIFICATION-TYPE
			OBJECTS { sysDescr, sysName, sysLocation, eventTimeStamp, eventPriority, 
				eventCounter, dabSTRefFault }
			STATUS current
			DESCRIPTION 
				"Description. dabSTRefFault notification"
			::= { dabEventsST 13 }

		
		-- 1.3.6.1.4.1.19831.1.1.2.1.0.14
		dabSTMuteEvent NOTIFICATION-TYPE
			OBJECTS { sysDescr, sysName, sysLocation, eventTimeStamp, eventPriority, 
				eventCounter, dabSTMute }
			STATUS current
			DESCRIPTION 
				"Description. dabSTMute notification"
			::= { dabEventsST 14 }

		
		-- 1.3.6.1.4.1.19831.1.1.2.1.0.15
		dabSTWarningTimeStampEvent NOTIFICATION-TYPE
			OBJECTS { sysDescr, sysName, sysLocation, eventTimeStamp, eventPriority, 
				eventCounter, dabSTWarningTimeStamp }
			STATUS current
			DESCRIPTION 
				"Description. dabSTSStuffingMode notification"
			::= { dabEventsST 15 }

		
-- dab single transmitter general
		-- 1.3.6.1.4.1.19831.1.1.2.1.1
		dabSTGeneral OBJECT IDENTIFIER ::= { dabSingleTransmitter 1 }

		
		-- 1.3.6.1.4.1.19831.1.1.2.1.1.1
		dabSTInputPreselection OBJECT-TYPE
			SYNTAX Input1Input2
			UNITS " "
			MAX-ACCESS read-write
			STATUS current
			DESCRIPTION
				"Single transmitter. Preselection input of single transmitter
				
				(0) undefined
				(1) Input 1
				(2) Input 2"
			::= { dabSTGeneral 1 }

		
		-- 1.3.6.1.4.1.19831.1.1.2.1.1.2
		dabSTInputAutomatic OBJECT-TYPE
			SYNTAX SelectManualAuto
			UNITS " "
			MAX-ACCESS read-write
			STATUS current
			DESCRIPTION
				"Single transmitter. Input selection mode of single  transmitter:  manual or automatic
				
				(0) undefined
				(1) manual 
				(2) automatic"
			::= { dabSTGeneral 2 }

		
		-- 1.3.6.1.4.1.19831.1.1.2.1.1.3
		dabSTTransmitterOpMode OBJECT-TYPE
			SYNTAX SelectOnOff
			UNITS " "
			MAX-ACCESS read-write
			STATUS current
			DESCRIPTION
				"Single transmitter. Transmitter control of single  transmitter
				
				(0) undefined
				(1) ON
				(2) OFF"
			::= { dabSTGeneral 3 }

		
		-- 1.3.6.1.4.1.19831.1.1.2.1.1.4
		dabSTRFPresent OBJECT-TYPE
			SYNTAX PresentNotPresent
			MAX-ACCESS read-only
			STATUS current
			DESCRIPTION
				"Single  transmitter. Describes if  the output power is present
				
				(0) undefined
				(1) present
				(2) not present
				"
			::= { dabSTGeneral 4 }

		
		-- 1.3.6.1.4.1.19831.1.1.2.1.1.5
		dabSTResetFault OBJECT-TYPE
			SYNTAX Unsigned32
			MAX-ACCESS read-write
			STATUS obsolete
			DESCRIPTION
				"Description. Massage is inactive!
				
				Single  transmitter. Reset fault. Trigger for reset the sum fault
				
				<1>
				
				1: reset sum fault"
			::= { dabSTGeneral 5 }

		
		-- 1.3.6.1.4.1.19831.1.1.2.1.1.6
		dabSTFault OBJECT-TYPE
			SYNTAX FaultOK
			MAX-ACCESS read-only
			STATUS current
			DESCRIPTION
				"Single transmitter. Fault state of transmitter
				
				(0) undefined
				(1) fault
				(2) ok"
			::= { dabSTGeneral 6 }

		
		-- 1.3.6.1.4.1.19831.1.1.2.1.1.7
		dabSTWarning OBJECT-TYPE
			SYNTAX WarningOK
			MAX-ACCESS read-only
			STATUS current
			DESCRIPTION
				"Single transmitter. Warning state of single transmitter
				
				(0) undefined
				(1) warning
				(2) ok"
			::= { dabSTGeneral 7 }

		
		-- 1.3.6.1.4.1.19831.1.1.2.1.1.8
		dabSTInput1OK OBJECT-TYPE
			SYNTAX OkNotOk
			MAX-ACCESS read-only
			STATUS current
			DESCRIPTION
				"Single transmitter.Describes if the input signal at the input 1 of single transmitter  is ok
				
				(0) undefined
				(1) signal ok
				(2) signal is not ok"
			::= { dabSTGeneral 8 }

		
		-- 1.3.6.1.4.1.19831.1.1.2.1.1.9
		dabSTInput2OK OBJECT-TYPE
			SYNTAX OkNotOk
			MAX-ACCESS read-only
			STATUS current
			DESCRIPTION
				"Describes if the input signal at the input 2 of single transmitters  is ok
				
				(0) undefined
				(1) signal ok
				(2) signal is not ok "
			::= { dabSTGeneral 9 }

		
		-- 1.3.6.1.4.1.19831.1.1.2.1.1.10
		dabSTLocalMode OBJECT-TYPE
			SYNTAX LocalRemote
			MAX-ACCESS read-only
			STATUS current
			DESCRIPTION
				"Single transmitter. Local  mode
				
				(0) undefined
				(1) local
				(2) remote"
			::= { dabSTGeneral 10 }

		
		-- 1.3.6.1.4.1.19831.1.1.2.1.1.11
		dabSTActiveInput OBJECT-TYPE
			SYNTAX INTEGER
				{
				undefined(0),
				input1(1),
				input2(2),
				seamless(3),
				hmHierarchicalModulation(4)
				}
			MAX-ACCESS read-only
			STATUS current
			DESCRIPTION
				"Single transmitter.Active input of the single transmitter 
				
				
				"
			::= { dabSTGeneral 11 }

		
		-- 1.3.6.1.4.1.19831.1.1.2.1.1.12
		dabSTSFNMode OBJECT-TYPE
			SYNTAX SFNMFN
			MAX-ACCESS read-only
			STATUS current
			DESCRIPTION
				"Single transmitter. SFN mode of single transmitter 
				
				(0) undefined
				(1) SFN
				(2) MFN"
			::= { dabSTGeneral 12 }

		
		-- 1.3.6.1.4.1.19831.1.1.2.1.1.13
		dabSTRefFault OBJECT-TYPE
			SYNTAX FaultOK
			MAX-ACCESS read-only
			STATUS current
			DESCRIPTION
				"Single transmitter.Fault state of the GPS input or the reference frequency of single transmitter 
				
				(0) undefined
				(1) fault
				(2) ok"
			::= { dabSTGeneral 13 }

		
		-- 1.3.6.1.4.1.19831.1.1.2.1.1.14
		dabSTMute OBJECT-TYPE
			SYNTAX MuteOk
			MAX-ACCESS read-only
			STATUS current
			DESCRIPTION
				"Single transmitter. Mute state of single transmitter
				
				(0) undefined
				(1) mute
				(2) ok"
			::= { dabSTGeneral 14 }

		
		-- 1.3.6.1.4.1.19831.1.1.2.1.1.15
		dabSTWarningTimeStamp OBJECT-TYPE
			SYNTAX WarningOK
			MAX-ACCESS read-only
			STATUS current
			DESCRIPTION
				"Time stamp warning state of single transmitter
				
				(0) undefined
				(1) warning
				(2) ok"
			::= { dabSTGeneral 15 }

		
-- dab single transmitter switch for event
		-- 1.3.6.1.4.1.19831.1.1.2.1.2
		dabSTEventEnable OBJECT IDENTIFIER ::= { dabSingleTransmitter 2 }

		
		-- 1.3.6.1.4.1.19831.1.1.2.1.2.1
		dabSTEventEnableGeneral OBJECT IDENTIFIER ::= { dabSTEventEnable 1 }

		
		-- 1.3.6.1.4.1.19831.1.1.2.1.2.1.1
		dabSTInputPreselectionEnable OBJECT-TYPE
			SYNTAX TruthValue
			MAX-ACCESS read-write
			STATUS current
			DESCRIPTION
				"Description.Enable/Disable switch for dabSTInputPreselection event"
			::= { dabSTEventEnableGeneral 1 }

		
		-- 1.3.6.1.4.1.19831.1.1.2.1.2.1.2
		dabSTInputAutomaticEnable OBJECT-TYPE
			SYNTAX TruthValue
			MAX-ACCESS read-write
			STATUS current
			DESCRIPTION
				"Description.Enable/Disable switch for dabSTInputAutomatic event"
			::= { dabSTEventEnableGeneral 2 }

		
		-- 1.3.6.1.4.1.19831.1.1.2.1.2.1.3
		dabSTTransmitterOpModeEnable OBJECT-TYPE
			SYNTAX TruthValue
			MAX-ACCESS read-write
			STATUS current
			DESCRIPTION
				"Description.Enable/Disable switch for dabSTTransmitterOpMode event"
			::= { dabSTEventEnableGeneral 3 }

		
		-- 1.3.6.1.4.1.19831.1.1.2.1.2.1.4
		dabSTRFPresentEnable OBJECT-TYPE
			SYNTAX TruthValue
			MAX-ACCESS read-write
			STATUS current
			DESCRIPTION
				"Description.Enable/Disable switch for dabSTRFPresent event"
			::= { dabSTEventEnableGeneral 4 }

		
		-- 1.3.6.1.4.1.19831.1.1.2.1.2.1.5
		dabSTResetFaultEnable OBJECT-TYPE
			SYNTAX TruthValue
			MAX-ACCESS read-write
			STATUS obsolete
			DESCRIPTION
				"Massage is inactive!
				
				Description. Enable/Disable switch for dabSTResetFault event"
			::= { dabSTEventEnableGeneral 5 }

		
		-- 1.3.6.1.4.1.19831.1.1.2.1.2.1.6
		dabSTFaultEnable OBJECT-TYPE
			SYNTAX TruthValue
			MAX-ACCESS read-write
			STATUS current
			DESCRIPTION
				"Description.Enable/Disable switch for dabSTFault event"
			::= { dabSTEventEnableGeneral 6 }

		
		-- 1.3.6.1.4.1.19831.1.1.2.1.2.1.7
		dabSTWarningEnable OBJECT-TYPE
			SYNTAX TruthValue
			MAX-ACCESS read-write
			STATUS current
			DESCRIPTION
				"Description.Enable/Disable switch for dabSTWarning event"
			::= { dabSTEventEnableGeneral 7 }

		
		-- 1.3.6.1.4.1.19831.1.1.2.1.2.1.8
		dabSTInput1OKEnable OBJECT-TYPE
			SYNTAX TruthValue
			MAX-ACCESS read-write
			STATUS current
			DESCRIPTION
				"Description.Enable/Disable switch for dabSTInput1OK event"
			::= { dabSTEventEnableGeneral 8 }

		
		-- 1.3.6.1.4.1.19831.1.1.2.1.2.1.9
		dabSTInput2OKEnable OBJECT-TYPE
			SYNTAX TruthValue
			MAX-ACCESS read-write
			STATUS current
			DESCRIPTION
				"Description.Enable/Disable switch for dabSTInput2OK event"
			::= { dabSTEventEnableGeneral 9 }

		
		-- 1.3.6.1.4.1.19831.1.1.2.1.2.1.10
		dabSTLocalModeEnable OBJECT-TYPE
			SYNTAX TruthValue
			MAX-ACCESS read-write
			STATUS current
			DESCRIPTION
				"Description.Enable/Disable switch for dabSTLocalMode event"
			::= { dabSTEventEnableGeneral 10 }

		
		-- 1.3.6.1.4.1.19831.1.1.2.1.2.1.11
		dabSTActiveInputEnable OBJECT-TYPE
			SYNTAX TruthValue
			MAX-ACCESS read-write
			STATUS current
			DESCRIPTION
				"Description.Enable/Disable switch for dabSTActiveInput event"
			::= { dabSTEventEnableGeneral 11 }

		
		-- 1.3.6.1.4.1.19831.1.1.2.1.2.1.12
		dabSTSFNModeEnable OBJECT-TYPE
			SYNTAX TruthValue
			MAX-ACCESS read-write
			STATUS current
			DESCRIPTION
				"Description.Enable/Disable switch for dabSTSFNMode event"
			::= { dabSTEventEnableGeneral 12 }

		
		-- 1.3.6.1.4.1.19831.1.1.2.1.2.1.13
		dabSTRefFaultEnable OBJECT-TYPE
			SYNTAX TruthValue
			MAX-ACCESS read-write
			STATUS current
			DESCRIPTION
				"Description.Enable/Disable switch for dabSTRefFault event"
			::= { dabSTEventEnableGeneral 13 }

		
		-- 1.3.6.1.4.1.19831.1.1.2.1.2.1.14
		dabSTMuteEnable OBJECT-TYPE
			SYNTAX TruthValue
			MAX-ACCESS read-write
			STATUS current
			DESCRIPTION
				"Description.Enable/Disable switch for dabSTMute event"
			::= { dabSTEventEnableGeneral 14 }

		
		-- 1.3.6.1.4.1.19831.1.1.2.1.2.1.15
		dabSTWarningTimeStampEnable OBJECT-TYPE
			SYNTAX TruthValue
			MAX-ACCESS read-write
			STATUS current
			DESCRIPTION
				"Description.Enable/Disable switch for dabSTWarningTimeStamp event"
			::= { dabSTEventEnableGeneral 15 }

		
-- dab single trnasmitter event priority
		-- 1.3.6.1.4.1.19831.1.1.2.1.3
		dabSTEventPriority OBJECT IDENTIFIER ::= { dabSingleTransmitter 3 }

		
		-- 1.3.6.1.4.1.19831.1.1.2.1.3.1
		dabSTEventPriorityGeneral OBJECT IDENTIFIER ::= { dabSTEventPriority 1 }

		
		-- 1.3.6.1.4.1.19831.1.1.2.1.3.1.1
		dabSTInputPreselectionPriority OBJECT-TYPE
			SYNTAX Unsigned32
			MAX-ACCESS read-write
			STATUS current
			DESCRIPTION
				"Description.Priority for dabSTInputPreselection event"
			::= { dabSTEventPriorityGeneral 1 }

		
		-- 1.3.6.1.4.1.19831.1.1.2.1.3.1.2
		dabSTInputAutomaticPriority OBJECT-TYPE
			SYNTAX Unsigned32
			MAX-ACCESS read-write
			STATUS current
			DESCRIPTION
				"Description.Priority for dabSTInputAutomatic event"
			::= { dabSTEventPriorityGeneral 2 }

		
		-- 1.3.6.1.4.1.19831.1.1.2.1.3.1.3
		dabSTTransmitterOpModePriority OBJECT-TYPE
			SYNTAX Unsigned32
			MAX-ACCESS read-write
			STATUS current
			DESCRIPTION
				"Description.Priority for dabSTTransmitterOpMode event"
			::= { dabSTEventPriorityGeneral 3 }

		
		-- 1.3.6.1.4.1.19831.1.1.2.1.3.1.4
		dabSTRFPresentPriority OBJECT-TYPE
			SYNTAX Unsigned32
			MAX-ACCESS read-write
			STATUS current
			DESCRIPTION
				"Description.Priority for dabSTRFPresent event"
			::= { dabSTEventPriorityGeneral 4 }

		
		-- 1.3.6.1.4.1.19831.1.1.2.1.3.1.5
		dabSTResetFaultPriority OBJECT-TYPE
			SYNTAX Unsigned32
			MAX-ACCESS read-write
			STATUS obsolete
			DESCRIPTION
				"Massage is inactive!
				
				Description. Priority for dabSTResetFault event"
			::= { dabSTEventPriorityGeneral 5 }

		
		-- 1.3.6.1.4.1.19831.1.1.2.1.3.1.6
		dabSTFaultPriority OBJECT-TYPE
			SYNTAX Unsigned32
			MAX-ACCESS read-write
			STATUS current
			DESCRIPTION
				"Description.Priority for dabSTFault event"
			::= { dabSTEventPriorityGeneral 6 }

		
		-- 1.3.6.1.4.1.19831.1.1.2.1.3.1.7
		dabSTWarningPriority OBJECT-TYPE
			SYNTAX Unsigned32
			MAX-ACCESS read-write
			STATUS current
			DESCRIPTION
				"Description.Priority for dabSTWarning event"
			::= { dabSTEventPriorityGeneral 7 }

		
		-- 1.3.6.1.4.1.19831.1.1.2.1.3.1.8
		dabSTInput1OKPriority OBJECT-TYPE
			SYNTAX Unsigned32
			MAX-ACCESS read-write
			STATUS current
			DESCRIPTION
				"Description.Priority for dabSTInput1OK event"
			::= { dabSTEventPriorityGeneral 8 }

		
		-- 1.3.6.1.4.1.19831.1.1.2.1.3.1.9
		dabSTInput2OKPriority OBJECT-TYPE
			SYNTAX Unsigned32
			MAX-ACCESS read-write
			STATUS current
			DESCRIPTION
				"Description.Priority for dabSTInput2OK event"
			::= { dabSTEventPriorityGeneral 9 }

		
		-- 1.3.6.1.4.1.19831.1.1.2.1.3.1.10
		dabSTLocalModePriority OBJECT-TYPE
			SYNTAX Unsigned32
			MAX-ACCESS read-write
			STATUS current
			DESCRIPTION
				"Description.Priority for dabSTLocalMode event"
			::= { dabSTEventPriorityGeneral 10 }

		
		-- 1.3.6.1.4.1.19831.1.1.2.1.3.1.11
		dabSTActiveInputPriority OBJECT-TYPE
			SYNTAX Unsigned32
			MAX-ACCESS read-write
			STATUS current
			DESCRIPTION
				"Description.Priority for dabSTActiveInput event"
			::= { dabSTEventPriorityGeneral 11 }

		
		-- 1.3.6.1.4.1.19831.1.1.2.1.3.1.12
		dabSTSFNModePriority OBJECT-TYPE
			SYNTAX Unsigned32
			MAX-ACCESS read-write
			STATUS current
			DESCRIPTION
				"Description.Priority for dabSTSFNMode event"
			::= { dabSTEventPriorityGeneral 12 }

		
		-- 1.3.6.1.4.1.19831.1.1.2.1.3.1.13
		dabSTRefFaultPriority OBJECT-TYPE
			SYNTAX Unsigned32
			MAX-ACCESS read-write
			STATUS current
			DESCRIPTION
				"Description.Priority for dabSTRefFault event"
			::= { dabSTEventPriorityGeneral 13 }

		
		-- 1.3.6.1.4.1.19831.1.1.2.1.3.1.14
		dabSTMutePriority OBJECT-TYPE
			SYNTAX Unsigned32
			MAX-ACCESS read-write
			STATUS current
			DESCRIPTION
				"Description.Priority for dabSTMute event"
			::= { dabSTEventPriorityGeneral 14 }

		
		-- 1.3.6.1.4.1.19831.1.1.2.1.3.1.15
		dabSTWarningTimeStampPriority OBJECT-TYPE
			SYNTAX Unsigned32
			MAX-ACCESS read-write
			STATUS current
			DESCRIPTION
				"Description.Priority for dabSTWarningTimeStamp event"
			::= { dabSTEventPriorityGeneral 15 }

		
		-- 1.3.6.1.4.1.19831.1.1.2.1.4
		groupsST OBJECT IDENTIFIER ::= { dabSingleTransmitter 4 }

		
		-- 1.3.6.1.4.1.19831.1.1.2.1.4.1
		objectGroupST OBJECT-GROUP
			OBJECTS { dabSTInputPreselection, dabSTInputAutomatic, dabSTTransmitterOpMode, dabSTRFPresent, dabSTFault, 
				dabSTWarning, dabSTInput1OK, dabSTInput2OK, dabSTLocalMode, dabSTActiveInput, 
				dabSTSFNMode, dabSTRefFault, dabSTMute, dabSTWarningTimeStamp, dabSTInputPreselectionEnable, 
				dabSTInputAutomaticEnable, dabSTTransmitterOpModeEnable, dabSTRFPresentEnable, dabSTFaultEnable, dabSTWarningEnable, 
				dabSTInput1OKEnable, dabSTInput2OKEnable, dabSTLocalModeEnable, dabSTActiveInputEnable, dabSTSFNModeEnable, 
				dabSTRefFaultEnable, dabSTMuteEnable, dabSTWarningTimeStampEnable, dabSTInputPreselectionPriority, dabSTInputAutomaticPriority, 
				dabSTTransmitterOpModePriority, dabSTRFPresentPriority, dabSTFaultPriority, dabSTWarningPriority, dabSTInput1OKPriority, 
				dabSTInput2OKPriority, dabSTLocalModePriority, dabSTActiveInputPriority, dabSTSFNModePriority, dabSTRefFaultPriority, 
				dabSTMutePriority, dabSTWarningTimeStampPriority }
			STATUS current
			DESCRIPTION 
				"Description. dab single transmitter  objects"
			::= { groupsST 1 }

		
		-- 1.3.6.1.4.1.19831.1.1.2.1.4.2
		eventGroupST NOTIFICATION-GROUP
			NOTIFICATIONS { dabSTMuteEvent, dabSTRefFaultEvent, dabSTSFNModeEvent, dabSTActiveInputEvent, dabSTLocalModeEvent, 
				dabSTInput2OKEvent, dabSTInput1OKEvent, dabSTWarningEvent, dabSTFaultEvent, dabSTRFPresentEvent, 
				dabSTTransmitterOpModeEvent, dabSTInputAutomaticEvent, dabSTInputPreselectionEvent, dabSTWarningTimeStampEvent }
			STATUS current
			DESCRIPTION 
				"Description. dab single transmitter  events"
			::= { groupsST 2 }

		
		-- 1.3.6.1.4.1.19831.1.1.2.1.4.3
		objectGroupSTobsolete OBJECT-GROUP
			OBJECTS { dabSTResetFault, dabSTResetFaultEnable, dabSTResetFaultPriority }
			STATUS obsolete
			DESCRIPTION 
				"Description.Inactive objects"
			::= { groupsST 3 }

		
		-- 1.3.6.1.4.1.19831.1.1.2.1.4.4
		eventGroupSTobsolete NOTIFICATION-GROUP
			NOTIFICATIONS { dabSTResetFaultEvent }
			STATUS obsolete
			DESCRIPTION 
				"Description."
			::= { groupsST 4 }

		
		-- 1.3.6.1.4.1.19831.1.1.2.1.5
		complianceST OBJECT IDENTIFIER ::= { dabSingleTransmitter 5 }

		
		-- 1.3.6.1.4.1.19831.1.1.2.1.5.1
		dabSingleTransmitterCompliance MODULE-COMPLIANCE
			STATUS current
			DESCRIPTION 
				"Compliance Statement"
			MODULE -- this module
				MANDATORY-GROUPS { objectGroupST, eventGroupST }
			::= { complianceST 1 }

		
	
	END

--
-- IRT-DAB-SINGLETRANSMITTER-MIB.my
--
