-- Extreme Networks ExtremeXOS 15.3.2.11 Proprietary MIB


-- ################################################################################

-- ################################################################################

EXTREME-MLAG-MIB DEFINITIONS ::= BEGIN

          IMPORTS
                     MODULE-IDENTITY         FROM SNMPv2-SMI
                     OBJECT-TYPE             FROM SNMPv2-SMI
                     DisplayString           FROM SNMPv2-TC
                     TimeStamp               FROM SNMPv2-TC
                     RowStatus               FROM SNMPv2-TC
                     TruthValue              FROM SNMPv2-TC
                     Counter32               FROM SNMPv2-SMI
                     NOTIFICATION-TYPE       FROM SNMPv2-SMI
                     Integer32               FROM SNMPv2-SMI
                     Unsigned32              FROM SNMPv2-SMI
                     InetAddressType, InetAddress FROM INET-ADDRESS-MIB
                     extremeAgent            FROM EXTREME-BASE-MIB
                     MacAddress              FROM SNMPv2-TC;

    extremeMlag MODULE-IDENTITY
        LAST-UPDATED "201208080000Z"
        ORGANIZATION "Extreme Networks, Inc."
        CONTACT-INFO "www.extremenetworks.com"
        DESCRIPTION
            "Extreme Networks Multi-Switch LAG MIB"
        REVISION     "201208080000Z"
        DESCRIPTION
            "Extreme Networks Multi-Switch LAG MIB"
        ::= { extremeAgent 41 }

        extremeMlagObjects               OBJECT IDENTIFIER ::= { extremeMlag 1 }
        extremeMlagNotificationObjects   OBJECT IDENTIFIER ::= { extremeMlag 2 }
        extremeMlagNotifications         OBJECT IDENTIFIER ::= { extremeMlag 3 }
        extremeMlagNotificationsPrefix   OBJECT IDENTIFIER ::= { extremeMlagNotifications 0 }

        extremeMlagPeerTable OBJECT-TYPE
            SYNTAX          SEQUENCE OF ExtremeMlagPeerEntry
            MAX-ACCESS      not-accessible
            STATUS          current
            DESCRIPTION
                    "This table contains MLAG peer entries.
                    This table contains a MLAG peer switch association structure, associates an MLAG peer structure with an MLAG peer switch IP address.
                    Displays User configured items, MLAG peer switch state, MLAG port count and health-check statistics."
            ::= { extremeMlagObjects 1 }

        extremeMlagPeerEntry OBJECT-TYPE
            SYNTAX          ExtremeMlagPeerEntry
            MAX-ACCESS      not-accessible
            STATUS          current
            DESCRIPTION
                    "An entry in the MLAG Peer Table"
            INDEX { extremeMlagPeerName }
            ::= { extremeMlagPeerTable 1 }

        ExtremeMlagPeerEntry ::= SEQUENCE {
            extremeMlagPeerName                 DisplayString,
            extremeMlagPeerVlan                 DisplayString,
            extremeMlagPeerVR                   DisplayString,
            extremeMlagLocalAddrType            InetAddressType,
            extremeMlagLocalIP                  InetAddress,
            extremeMlagPeerAddrType             InetAddressType,
            extremeMlagPeerIP                   InetAddress,
            extremeMlagPeerPortCount            Integer32,
            extremeMlagPeerCheckPointStatus     INTEGER,
            extremeMlagPeerRxHellos             Counter32,
            extremeMlagPeerRxCheckpointMsgs     Counter32,
            extremeMlagPeerHelloErrors          Counter32,
            extremeMlagPeerHelloTimeouts        Counter32,
            extremeMlagPeerUptime               TimeStamp,
            extremeMlagPeerLocalTxInterval      Integer32,
            extremeMlagPeerRemoteTxInterval     Integer32,
            extremeMlagPeerTxHellos             Counter32,
            extremeMlagPeerTxCheckpoints        Counter32,
            extremeMlagPeerCheckpointErrors     Counter32,
            extremeMlagPeerConnnectErrors       Counter32,
            extremeMlagPeerRowStatus            RowStatus,
            extremeMlagPeerCfgLacpMac           MacAddress,
            extremeMlagPeerOperLacpMac          MacAddress
        }
        
        extremeMlagPeerName  OBJECT-TYPE
            SYNTAX          DisplayString (SIZE(1..32))
            MAX-ACCESS      read-create
            STATUS          current
            DESCRIPTION
                    "The name of the MLAG Peer switch.
                    MLAG Peer names must be alpha-numeric and must start with an alpha character."
            ::= { extremeMlagPeerEntry 1 }

        extremeMlagPeerVlan OBJECT-TYPE
            SYNTAX          DisplayString (SIZE(1..32))
            MAX-ACCESS      read-only
            STATUS          current
            DESCRIPTION
                    "The name of the VLAN through which the MLAG Peer can be reached."
            ::= { extremeMlagPeerEntry 2 }

        extremeMlagPeerVR OBJECT-TYPE
            SYNTAX          DisplayString (SIZE(1..32))
            MAX-ACCESS      read-write
            STATUS          current
            DESCRIPTION
                    "The name of the VR with which the MLAG peer VLAN is associated with." 
            ::= { extremeMlagPeerEntry 3 }

        extremeMlagLocalAddrType OBJECT-TYPE
                SYNTAX      InetAddressType
                MAX-ACCESS  read-write
                STATUS      current
                DESCRIPTION
                "The IP address type of the extremeMlagLocalIP object."
                ::= { extremeMlagPeerEntry 4 }

        extremeMlagLocalIP OBJECT-TYPE
                SYNTAX      InetAddress
                MAX-ACCESS  read-write
                STATUS      current
                DESCRIPTION
                        "Local Switch IPAddress of ISC connection."
                ::= { extremeMlagPeerEntry 5 }

        extremeMlagPeerAddrType OBJECT-TYPE
                SYNTAX      InetAddressType
                MAX-ACCESS  read-write
                STATUS      current
                DESCRIPTION
                "The IP address type of the extremeMlagPeerIP object."
                ::= { extremeMlagPeerEntry 6 }

        extremeMlagPeerIP OBJECT-TYPE
                SYNTAX      InetAddress
                MAX-ACCESS  read-write
                STATUS      current
                DESCRIPTION
                        "MLAG peer IP address for the ISC.
                        The specified IP address must be contained within an existing direct route."
                ::= { extremeMlagPeerEntry 7 }
               
        extremeMlagPeerPortCount OBJECT-TYPE
            SYNTAX          Integer32
            MAX-ACCESS      read-only
            STATUS          current
            DESCRIPTION
                    "Number of MLAG Ports associated with this MLAG peer"
            ::= { extremeMlagPeerEntry 8 }

        extremeMlagPeerCheckPointStatus OBJECT-TYPE
            SYNTAX          INTEGER {
                                up(1),
                                down(2)
                            }
            MAX-ACCESS      read-only
            STATUS          current
            DESCRIPTION
                        "Checkpointing Status of this MLAG peer"
            ::= { extremeMlagPeerEntry 9 }
                
        extremeMlagPeerRxHellos OBJECT-TYPE
            SYNTAX          Counter32
            MAX-ACCESS      read-only
            STATUS          current
            DESCRIPTION
                    "Number of Hellos received from the peer"
            ::= { extremeMlagPeerEntry 10 }
                
        extremeMlagPeerRxCheckpointMsgs OBJECT-TYPE
            SYNTAX          Counter32
            MAX-ACCESS      read-only
            STATUS          current
            DESCRIPTION
                    "Number of Checkpoint Messages received from the peer"
            ::= { extremeMlagPeerEntry 11 }

        extremeMlagPeerHelloErrors OBJECT-TYPE
            SYNTAX          Counter32
            MAX-ACCESS      read-only
            STATUS          current
            DESCRIPTION
                    "Number of Hello Error Messages"
            ::= { extremeMlagPeerEntry 12 }

        extremeMlagPeerHelloTimeouts OBJECT-TYPE
            SYNTAX          Counter32
            MAX-ACCESS      read-only
            STATUS          current
            DESCRIPTION
                    "Number of Hello Timeout Messages"
            ::= { extremeMlagPeerEntry 13 }
                
        extremeMlagPeerUptime OBJECT-TYPE
            SYNTAX          TimeStamp
            MAX-ACCESS      read-only
            STATUS          current
            DESCRIPTION
                    "Specifies the time that the Connectivity with the peer is up"
            ::= { extremeMlagPeerEntry 14 }
            
        extremeMlagPeerLocalTxInterval      OBJECT-TYPE
            SYNTAX          Integer32 (50..10000)
            MAX-ACCESS      read-write
            STATUS          current
            DESCRIPTION
                    "Length of the time in milli seconds between health check hello packets 
                    transmitted by this switch."
            DEFVAL { 100 }
            ::= { extremeMlagPeerEntry 15 }
                
        extremeMlagPeerRemoteTxInterval OBJECT-TYPE
            SYNTAX          Integer32 (50..10000)
            MAX-ACCESS      read-only
            STATUS          current
            DESCRIPTION
                    "Transmitting Hello Interval of Peer Switch in milli seconds"
            ::= { extremeMlagPeerEntry 16 }
                
        extremeMlagPeerTxHellos OBJECT-TYPE
            SYNTAX          Counter32
            MAX-ACCESS      read-only
            STATUS          current
            DESCRIPTION
                    "Number of Health Check Hellos transmitted"
            ::= { extremeMlagPeerEntry 17 }
                
        extremeMlagPeerTxCheckpoints OBJECT-TYPE
            SYNTAX          Counter32
            MAX-ACCESS      read-only
            STATUS          current
            DESCRIPTION
                    "Number of transmitted Checkpoint messages"
            ::= { extremeMlagPeerEntry 18 }

        extremeMlagPeerCheckpointErrors OBJECT-TYPE
            SYNTAX          Counter32
            MAX-ACCESS      read-only
            STATUS          current
            DESCRIPTION
                    "Number of Checkpoint Errors"
            ::= { extremeMlagPeerEntry 19 }
                
        extremeMlagPeerConnnectErrors OBJECT-TYPE
            SYNTAX          Counter32
            MAX-ACCESS      read-only
            STATUS          current
            DESCRIPTION
                    "Number of Peer Connect errors"
            ::= { extremeMlagPeerEntry 20 }

        extremeMlagPeerRowStatus OBJECT-TYPE
            SYNTAX          RowStatus
            MAX-ACCESS      read-create
            STATUS          current
            DESCRIPTION
                    "The status of this entry"
            ::= { extremeMlagPeerEntry 21 }

        extremeMlagPeerCfgLacpMac OBJECT-TYPE
            SYNTAX          MacAddress
            MAX-ACCESS      read-only
            STATUS          current
            DESCRIPTION
                    "This MAC address specifies the MLAG LACP MAC configured on this switch. If configured, this MAC is used as the System Identifier in the LACPDUs sent over the MLAG Ports. If not configured, the MAC address of MLAG peer having highest IP address for ISC control VLAN is chosen as the System Identifier in the LACPDUs sent over the MALG ports."
            ::= { extremeMlagPeerEntry 22 }

        extremeMlagPeerOperLacpMac OBJECT-TYPE
            SYNTAX          MacAddress
            MAX-ACCESS      read-only
            STATUS          current
            DESCRIPTION
                    "This MAC address specifies the MLAG LACP MAC that is being used as the System Identifier in the LACPDUs sent over the MLAG Ports. This may be different from extremeMlagPeerCfgLacpMac if same extremeMlagPeerCfgLacpMac is not configured on both the MLAG peers."
            ::= { extremeMlagPeerEntry 23 }

        extremeMlagPortTable OBJECT-TYPE
            SYNTAX          SEQUENCE OF ExtremeMlagPortEntry
            MAX-ACCESS      not-accessible
            STATUS          current
            DESCRIPTION
                    "This table contains Mlag port entries.
                    Binds a local port or LAG port to an MLAG port uniquely indentified by the MLAG Id value.
                    Once the MLAG group binding is made, any change to load sharing on MLAG ports is disallowed.
                    Displays User configured items, MLAG peer switch state, port count and health-check statistics."
            ::= { extremeMlagObjects 2 }

        extremeMlagPortEntry OBJECT-TYPE
            SYNTAX          ExtremeMlagPortEntry
            MAX-ACCESS      not-accessible
            STATUS          current
            DESCRIPTION
                "An entry in the MLagPortTable"
            INDEX { extremeMlagPortLocalPortIfIndex }
            ::= { extremeMlagPortTable 1 }

        ExtremeMlagPortEntry ::= SEQUENCE {
            extremeMlagPortLocalPortIfIndex    Unsigned32,
            extremeMlagPortId                  Integer32,
            extremeMlagPortPeer                DisplayString,
            extremeMlagPortLocalLinkStatus     INTEGER,
            extremeMlagPortRemoteLinkStatus    INTEGER,
            extremeMlagPortPeerState           INTEGER,
            extremeMlagPortLocalFailures       Counter32,
            extremeMlagPortRemoteFailures      Counter32,
            extremeMlagPortRowStatus           RowStatus
        }

        extremeMlagPortLocalPortIfIndex OBJECT-TYPE
            SYNTAX          Unsigned32
            MAX-ACCESS      read-write
            STATUS          current
            DESCRIPTION
                    "The ifIndex of the local member port of the MLAG port.
                    The specified port ifIndex may be a single port or the master port of a
                    load share port but should not be a load share member port."
            ::= { extremeMlagPortEntry 1 }

        extremeMlagPortId OBJECT-TYPE
            SYNTAX          Integer32 (1 .. 65000)
            MAX-ACCESS      read-create
            STATUS          current
            DESCRIPTION
                    "The identifier which is used to identify the MLAG port"
            ::= { extremeMlagPortEntry 2 }
                
        extremeMlagPortPeer OBJECT-TYPE
            SYNTAX          DisplayString
            MAX-ACCESS      read-write
            STATUS          current
            DESCRIPTION
                    "This object identifies the MLAG peer switch with which this port is associated"
            ::= { extremeMlagPortEntry 3 }

        extremeMlagPortLocalLinkStatus OBJECT-TYPE
            SYNTAX          INTEGER {
                                active(1),
                                disabled(2),
                                ready(3),
                                portNotPresent(4)
                            }
            MAX-ACCESS      read-only
            STATUS          current
            DESCRIPTION
                    "Local MLAG Port Status, that can be Active/Disabled/Ready/Port not present.
                    It reflects the status of entire LAG when LAG is used in conjunction with MLAG."
            ::= { extremeMlagPortEntry 4 }
         
        extremeMlagPortRemoteLinkStatus OBJECT-TYPE
            SYNTAX          INTEGER {
                                up(1),
                                down(2),
                                notAvailable(3)
                            }
            MAX-ACCESS      read-only
            STATUS          current
            DESCRIPTION
                    "Remote MLAG Port Status,  which can be
                    Up(1) - One or more links are active on the remote switch or
                    Down(2)- No links are active on the remote switch or
                    N/A(3) - The peer has not communicated link state for this MLAG group.
                    It reflects the status of entire LAG when LAG is used in conjunction with MLAG."
            ::= { extremeMlagPortEntry 5 }
                
        extremeMlagPortPeerState OBJECT-TYPE
            SYNTAX          INTEGER {
                                up(1),
                                down(2)
                            }
            MAX-ACCESS      read-only
            STATUS          current
            DESCRIPTION
                    "MLAG Peer Switch State, up/down"
            ::= { extremeMlagPortEntry 6 }
                
        extremeMlagPortLocalFailures OBJECT-TYPE
            SYNTAX          Counter32
            MAX-ACCESS      read-only
            STATUS          current
            DESCRIPTION
                    "Gives the number of ports that are down in the local MLAG port."
            ::= { extremeMlagPortEntry 7 }
                
        extremeMlagPortRemoteFailures OBJECT-TYPE
            SYNTAX          Counter32
            MAX-ACCESS      read-only
            STATUS          current
            DESCRIPTION
                    "Gives number of ports that are down in the remote MLAG port"
            ::= { extremeMlagPortEntry 8 }

        extremeMlagPortRowStatus OBJECT-TYPE
            SYNTAX          RowStatus
            MAX-ACCESS      read-create
            STATUS          current
            DESCRIPTION
                    "The status of this entry."
            ::= { extremeMlagPortEntry 9 }
                
    extremeMlagConvergenceControl OBJECT-TYPE
            SYNTAX          INTEGER {
                                fastConvergence(1),
                                conserveAccessLists(2)
                            }
        MAX-ACCESS      read-write
        STATUS          current
        DESCRIPTION
                "This object specifies if an ACL can be used on an MLAG port to achieve faster convergence. If an ACL is used, better
                 convergence times can be achieved irrespective of the number of FDB entries present on the MLAG port.
                 The second time can be chosen when convergence time is not an issue and ACLs are to be preserved."
        DEFVAL { conserveAccessLists }
        ::= { extremeMlagObjects 3 }

   extremeMlagPeerUp NOTIFICATION-TYPE
       OBJECTS { extremeMlagPeerName }
       STATUS  current
       DESCRIPTION
               "This trap is sent when the MLAG peer comes up."
       ::= { extremeMlagNotificationsPrefix 1 }

   extremeMlagPeerDown NOTIFICATION-TYPE
       OBJECTS { extremeMlagPeerName }
       STATUS  current
       DESCRIPTION
               "This notification is sent when health check messages are not received from 
               the peer MLAG switch for 3 times the configured hello interval."
       ::= { extremeMlagNotificationsPrefix 2 }

END
