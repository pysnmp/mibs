ACOS-SYSTEMCPU-CTRL-CPU-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		systemCpuCtrlCpuModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "systemCpuCtrlCpuModule OID for ACOS"
				::=  {  acosSchema 112 }

ctrlCpu		 OBJECT IDENTIFIER ::= { systemCpuCtrlCpuModule 1}

ctrlCpuOperTable OBJECT-TYPE
	 SYNTAX SEQUENCE OF CtrlCpuOperEntry
	 MAX-ACCESS not-accessible
	 STATUS current
	 DESCRIPTION
		 "Control CPU usage from object 'system-cpu.ctrl-cpu'"
	::= {ctrlCpu 2}

ctrlCpuOperEntry OBJECT-TYPE
	SYNTAX CtrlCpuOperEntry
	MAX-ACCESS not-accessible
	STATUS current
	DESCRIPTION
		"The ctrlCpuOper entry"
	INDEX {
		ctrlCpuOperSlotId
	}
	::= { ctrlCpuOperTable 1 }

CtrlCpuOperEntry ::=
	SEQUENCE {
		ctrlCpuOperSlotId Integer32,
		ctrlCpuOperCurrentTime	 DisplayString,
		ctrlCpuOperNumberOfCpu	 Integer32
	}

ctrlCpuOperSlotId OBJECT-TYPE
	 SYNTAX Integer32
	 MAX-ACCESS read-only
	 STATUS current
	 DESCRIPTION
		 ""
	::= { ctrlCpuOperEntry 1 }

ctrlCpuOperCurrentTime OBJECT-TYPE
	 SYNTAX DisplayString
	 MAX-ACCESS read-only
	 STATUS current
	 DESCRIPTION
		 "current-time"
	::= { ctrlCpuOperEntry 2 }

ctrlCpuOperNumberOfCpu OBJECT-TYPE
	 SYNTAX Integer32
	 MAX-ACCESS read-only
	 STATUS current
	 DESCRIPTION
		 "number-of-cpu"
	::= { ctrlCpuOperEntry 3 }

ctrlCpuOperCpuUsageTable OBJECT-TYPE
	 SYNTAX SEQUENCE OF CtrlCpuOperCpuUsageEntry
	 MAX-ACCESS not-accessible
	 STATUS current
	 DESCRIPTION
		 "Control CPU usage from object 'system-cpu.ctrl-cpu'"
	::= {ctrlCpu 3}

ctrlCpuOperCpuUsageEntry OBJECT-TYPE
	SYNTAX CtrlCpuOperCpuUsageEntry
	MAX-ACCESS not-accessible
	STATUS current
	DESCRIPTION
		"The ctrlCpuOperCpuUsage entry:cpu-usage"
	INDEX {
		ctrlCpuOperCpuUsageSlotId,
		ctrlCpuOperCpuUsageCpuUsageListId
	}
	::= { ctrlCpuOperCpuUsageTable 1}

CtrlCpuOperCpuUsageEntry ::=
	SEQUENCE {
		ctrlCpuOperCpuUsageSlotId Integer32,
		ctrlCpuOperCpuUsageCpuUsageListId Integer32,
		ctrlCpuOperCpuUsageCpuId	Integer32,
		ctrlCpuOperCpuUsage1Sec	Integer32,
		ctrlCpuOperCpuUsage5Sec	Integer32,
		ctrlCpuOperCpuUsage10Sec	Integer32,
		ctrlCpuOperCpuUsage30Sec	Integer32,
		ctrlCpuOperCpuUsage60Sec	Integer32
	}

ctrlCpuOperCpuUsageSlotId OBJECT-TYPE
	SYNTAX Integer32
	MAX-ACCESS read-only
	STATUS current
	DESCRIPTION
		""
	::= { ctrlCpuOperCpuUsageEntry 1}

ctrlCpuOperCpuUsageCpuUsageListId OBJECT-TYPE
	SYNTAX Integer32
	MAX-ACCESS read-only
	STATUS current
	DESCRIPTION
		""
	::= { ctrlCpuOperCpuUsageEntry 2}

ctrlCpuOperCpuUsageCpuId OBJECT-TYPE
	SYNTAX Integer32
	MAX-ACCESS read-only
	STATUS current
	DESCRIPTION
		"cpu-id"
	::= { ctrlCpuOperCpuUsageEntry 3}

ctrlCpuOperCpuUsage1Sec OBJECT-TYPE
	SYNTAX Integer32
	MAX-ACCESS read-only
	STATUS current
	DESCRIPTION
		"1-sec"
	::= { ctrlCpuOperCpuUsageEntry 4}

ctrlCpuOperCpuUsage5Sec OBJECT-TYPE
	SYNTAX Integer32
	MAX-ACCESS read-only
	STATUS current
	DESCRIPTION
		"5-sec"
	::= { ctrlCpuOperCpuUsageEntry 5}

ctrlCpuOperCpuUsage10Sec OBJECT-TYPE
	SYNTAX Integer32
	MAX-ACCESS read-only
	STATUS current
	DESCRIPTION
		"10-sec"
	::= { ctrlCpuOperCpuUsageEntry 6}

ctrlCpuOperCpuUsage30Sec OBJECT-TYPE
	SYNTAX Integer32
	MAX-ACCESS read-only
	STATUS current
	DESCRIPTION
		"30-sec"
	::= { ctrlCpuOperCpuUsageEntry 7}

ctrlCpuOperCpuUsage60Sec OBJECT-TYPE
	SYNTAX Integer32
	MAX-ACCESS read-only
	STATUS current
	DESCRIPTION
		"60-sec"
	::= { ctrlCpuOperCpuUsageEntry 8}

END
