ACOS-CGNV6-SHARED-SERVICE-GROUP-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		cgnv6SharedServiceGroupModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "cgnv6SharedServiceGroupModule OID for ACOS"
				::=  {  acosSchema 412 }

sharedServiceGroup		 OBJECT IDENTIFIER ::= { cgnv6SharedServiceGroupModule 1}

sharedServiceGroupOperSharedServiceGroupListTable OBJECT-TYPE
	 SYNTAX SEQUENCE OF SharedServiceGroupOperSharedServiceGroupListEntry
	 MAX-ACCESS not-accessible
	 STATUS current
	 DESCRIPTION
		 "CGNv6 Shared Service Group from object 'cgnv6.shared-service-group'"
	::= {sharedServiceGroup 2}

sharedServiceGroupOperSharedServiceGroupListEntry OBJECT-TYPE
	SYNTAX SharedServiceGroupOperSharedServiceGroupListEntry
	MAX-ACCESS not-accessible
	STATUS current
	DESCRIPTION
		"The sharedServiceGroupOperSharedServiceGroupList entry:shared-service-group-list"
	INDEX {
		sharedServiceGroupOperSharedServiceGroupListSlotId,
		sharedServiceGroupOperSharedServiceGroupListSharedServiceGroupListListId
	}
	::= { sharedServiceGroupOperSharedServiceGroupListTable 1}

SharedServiceGroupOperSharedServiceGroupListEntry ::=
	SEQUENCE {
		sharedServiceGroupOperSharedServiceGroupListSlotId Integer32,
		sharedServiceGroupOperSharedServiceGroupListSharedServiceGroupListListId Integer32,
		sharedServiceGroupOperSharedServiceGroupListServiceGroupName	DisplayString
	}

sharedServiceGroupOperSharedServiceGroupListSlotId OBJECT-TYPE
	SYNTAX Integer32
	MAX-ACCESS read-only
	STATUS current
	DESCRIPTION
		""
	::= { sharedServiceGroupOperSharedServiceGroupListEntry 1}

sharedServiceGroupOperSharedServiceGroupListSharedServiceGroupListListId OBJECT-TYPE
	SYNTAX Integer32
	MAX-ACCESS read-only
	STATUS current
	DESCRIPTION
		""
	::= { sharedServiceGroupOperSharedServiceGroupListEntry 2}

sharedServiceGroupOperSharedServiceGroupListServiceGroupName OBJECT-TYPE
	SYNTAX DisplayString
	MAX-ACCESS read-only
	STATUS current
	DESCRIPTION
		"service-group-name"
	::= { sharedServiceGroupOperSharedServiceGroupListEntry 3}

END
