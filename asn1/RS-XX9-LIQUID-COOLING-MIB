--
-- RS-XX9-LIQUID-COOLING-MIB.mi2
-- MIB generated by MG-SOFT Visual MIB Builder 2010 Version 8.0  Build 403
-- Monday, November 30, 2015 at 16:33:54
--

    RS-XX9-LIQUID-COOLING-MIB DEFINITIONS ::= BEGIN
 
        IMPORTS
            commonNotificationAlarmClass            
                FROM RS-XX9-COMMON-MIB            
            rsXx9LiquidCooling, rsXx9MibModule            
                FROM RS-XX9-SMI-MIB            
            NotificationMask, NotificationPriority, NotificationState, SwitchOnOff            
                FROM RS-XX9-TC-MIB            
            SnmpAdminString            
                FROM SNMP-FRAMEWORK-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI;
    
    
        rsXx9LqMibModule MODULE-IDENTITY 
            LAST-UPDATED "201511301700Z"		-- November 30, 2015 at 17:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines liquid cooling specific objects
                of XX9000 transmitting systems from Rohde & Schwarz.
                
                The following MIBs are related to this:
                - RS-COMMON-MIB         - mandatory for this MIB.
                - RS-XX9-SMI-MIB        - mandatory for this MIB.
                - RS-XX9-TC-MIB         - mandatory for this MIB.
                - RS-XX9-COMMON-MIB     - mandatory for this MIB."
            REVISION "201511301700Z"		-- November 30, 2015 at 17:00 GMT
            DESCRIPTION 
                "removed lqFStFanIdx from complianceStatement to be SMI compliant"
            REVISION "201508201500Z"		-- August 20, 2015 at 15:00 GMT
            DESCRIPTION 
                "extended CycleIdx from 8 to max 12 cycles
                added compactCfgServiceMode"
            REVISION "201506231200Z"		-- June 23, 2015 at 12:00 GMT
            DESCRIPTION 
                "added compactCoolingConfigTable, lqStCompactCompensateMode, lqStCompactRelayState, lqStCompactPumpDesiredSpeed
                added lqCfgAutoOn"
            REVISION "201502271500Z"		-- February 27, 2015 at 15:00 GMT
            DESCRIPTION 
                "updated description texts"
            REVISION "201412221600Z"		-- December 22, 2014 at 16:00 GMT
            DESCRIPTION 
                "updated description texts
                "
            REVISION "201310071200Z"		-- October 07, 2013 at 12:00 GMT
            DESCRIPTION 
                "extend liquid cooling cycle range from 1..2 to 1..8. 
                Up to 8 cooling cycles are now possible for each system."
            REVISION "201301311300Z"		-- January 31, 2013 at 13:00 GMT
            DESCRIPTION 
                "lqStInletTemperatureFaultLimit,
                lqStInletTemperatureWarningLimit
                obsoleted"
            REVISION "201205110800Z"		-- May 11, 2012 at 08:00 GMT
            DESCRIPTION 
                "Initial revision"
            REVISION "201201260800Z"		-- January 26, 2012 at 08:00 GMT
            DESCRIPTION 
                "Preliminary release."
            ::= { rsXx9MibModule 100 }

        
    
    
--
-- Node definitions
--
    
        rsXx9LiquidCoolingNotifications OBJECT IDENTIFIER ::= { rsXx9LiquidCooling 0 }

        
        lqSummary NOTIFICATION-TYPE
            OBJECTS { commonNotificationAlarmClass, lqNotificationPriority, lqNotificationState }
            STATUS current
            DESCRIPTION 
                "The cooling, assigned to this transmitter, reports a failure. 
                To get more information check the system logbook and the 
                shared system cooling.
                
                Possible values:
                off(2)       -
                fault(3)     - 
                warning(4)   - 
                ok(5)        - 
                
                Notification class: fault"
            ::= { rsXx9LiquidCoolingNotifications 1 }

        
        lqFilterSummary NOTIFICATION-TYPE
            OBJECTS { commonNotificationAlarmClass, lqNotificationPriority, lqNotificationState }
            STATUS current
            DESCRIPTION 
                "Indicates a polluted filter in cooling cycle. 
                Please clean the filter located to the pump unit.
                
                Possible values:
                off(2)       -
                warning(4)   - liquid filter is polluted
                ok(5)        - liquid filter is clean
                
                Notification class: warning"
            ::= { rsXx9LiquidCoolingNotifications 2 }

        
        lqSensorsSummary NOTIFICATION-TYPE
            OBJECTS { commonNotificationAlarmClass, lqNotificationPriority, lqNotificationState }
            STATUS current
            DESCRIPTION 
                "Liquid cooling sensors
                (inlet temperature, outlet temperature, pressure)
                summary state.
                
                Possible values:
                off(2)       -
                fault(3)     - pressure sensor fault
                warning(4)   - temperature sensor warning
                ok(5)        - 
                
                Notification class: warning"
            ::= { rsXx9LiquidCoolingNotifications 3 }

        
        lqSiteWarning NOTIFICATION-TYPE
            OBJECTS { commonNotificationAlarmClass, lqNotificationPriority, lqNotificationState }
            STATUS current
            DESCRIPTION 
                "Warnings from the site cooling system.
                Applicable only if the appropriate signals from the site cooling system
                are supplied via terminal x8000 of the mains distribution board (MDB).
                
                Possible values:
                off(2)       -
                warning(4)   - 
                ok(5)        - 
                
                Notification class: warning"
            ::= { rsXx9LiquidCoolingNotifications 4 }

        
        lqSiteFault NOTIFICATION-TYPE
            OBJECTS { commonNotificationAlarmClass, lqNotificationPriority, lqNotificationState }
            STATUS current
            DESCRIPTION 
                "Faults from the site cooling system.
                Applicable only if the appropriate signals from the site cooling system
                are supplied via terminal x8000 of the mains distribution board (MDB).
                
                Possible values:
                off(2)     -
                fault(3)   - 
                ok(5)      - 
                
                Notification class: warning"
            ::= { rsXx9LiquidCoolingNotifications 5 }

        
        rsXx9LiquidCoolingObjects OBJECT IDENTIFIER ::= { rsXx9LiquidCooling 1 }

        
        lqStatus OBJECT IDENTIFIER ::= { rsXx9LiquidCoolingObjects 1 }

        
        lqNotificationTable OBJECT-TYPE
            SYNTAX SEQUENCE OF LqNotificationEntry
            MAX-ACCESS not-accessible
            STATUS current
            DESCRIPTION
                "The context information/configuration for the
                liquid cooling status notifications."
            ::= { lqStatus 1 }

        
        lqNotificationEntry OBJECT-TYPE
            SYNTAX LqNotificationEntry
            MAX-ACCESS not-accessible
            STATUS current
            DESCRIPTION
                "An entry in the lqNotificationTable."
            INDEX { lqNotificationCycleIdx, lqNotificationIdx }
            ::= { lqNotificationTable 1 }

        
        LqNotificationEntry ::=
            SEQUENCE { 
                lqNotificationCycleIdx
                    Unsigned32,
                lqNotificationIdx
                    Unsigned32,
                lqNotificationName
                    INTEGER,
                lqNotificationMask
                    NotificationMask,
                lqNotificationPriority
                    NotificationPriority,
                lqNotificationState
                    NotificationState
             }

        lqNotificationCycleIdx OBJECT-TYPE
            SYNTAX Unsigned32 (1..12)
            MAX-ACCESS not-accessible
            STATUS current
            DESCRIPTION
                "Liquid cooling cycle index."
            ::= { lqNotificationEntry 1 }

        
        lqNotificationIdx OBJECT-TYPE
            SYNTAX Unsigned32 (1..5)
            MAX-ACCESS not-accessible
            STATUS current
            DESCRIPTION
                "The notification number as below rsXx9LiquidCoolingNotifications.
                This is a helper column and therefore not-accessible."
            ::= { lqNotificationEntry 2 }

        
        lqNotificationName OBJECT-TYPE
            SYNTAX INTEGER
                {
                lqSummary(1),
                lqFilterSummary(2),
                lqSensorsSummary(3),
                lqSiteWarning(4),
                lqSiteFault(5)
                }
            MAX-ACCESS read-only
            STATUS current
            DESCRIPTION
                "The notification number as an enumeration.
                The enumeration correlates with the notifications
                under rsXx9LiquidCoolingNotifications."
            ::= { lqNotificationEntry 3 }

        
        lqNotificationMask OBJECT-TYPE
            SYNTAX NotificationMask
            MAX-ACCESS read-write
            STATUS current
            DESCRIPTION
                "See textual convention for details."
            ::= { lqNotificationEntry 4 }

        
        lqNotificationPriority OBJECT-TYPE
            SYNTAX NotificationPriority
            MAX-ACCESS read-write
            STATUS current
            DESCRIPTION
                "See textual convention for details."
            ::= { lqNotificationEntry 5 }

        
        lqNotificationState OBJECT-TYPE
            SYNTAX NotificationState
            MAX-ACCESS read-only
            STATUS current
            DESCRIPTION
                "See textual convention for details."
            ::= { lqNotificationEntry 6 }

        
        lqStateTable OBJECT-TYPE
            SYNTAX SEQUENCE OF LqStateEntry
            MAX-ACCESS not-accessible
            STATUS current
            DESCRIPTION
                "Liquid cooling state information."
            ::= { lqStatus 2 }

        
        lqStateEntry OBJECT-TYPE
            SYNTAX LqStateEntry
            MAX-ACCESS not-accessible
            STATUS current
            DESCRIPTION
                "An entry in the lqStateTable."
            INDEX { lqNotificationCycleIdx }
            ::= { lqStateTable 1 }

        
        LqStateEntry ::=
            SEQUENCE { 
                lqStInletTemperature
                    Integer32,
                lqStInletTemperatureSensor
                    NotificationState,
                lqStInletTemperatureSumState
                    NotificationState,
                lqStOutletTemperature
                    Integer32,
                lqStOutletTemperatureSensor
                    NotificationState,
                lqStOutletTemperatureSumState
                    NotificationState,
                lqStCoolantPressure
                    Unsigned32,
                lqStCoolantPressureSensor
                    NotificationState,
                lqStCoolantPressureSumState
                    NotificationState,
                lqStInletTemperatureFaultLimit
                    Integer32,
                lqStInletTemperatureWarningLimit
                    Integer32,
                lqStCompactPumpDesiredSpeed
                    Unsigned32
             }

        lqStInletTemperature OBJECT-TYPE
            SYNTAX Integer32
            UNITS "degree Celsius"
            MAX-ACCESS read-only
            STATUS current
            DESCRIPTION
                "Temperature of the pouring in coolant."
            ::= { lqStateEntry 2 }

        
        lqStInletTemperatureSensor OBJECT-TYPE
            SYNTAX NotificationState
            MAX-ACCESS read-only
            STATUS current
            DESCRIPTION
                "Indicates whether the inlet temperature sensor is working.
                If a fault is displayed, please check the connection between
                sensor and cooling interface which is located in TCE900 System Control.
                fault(3) - sensor fault
                ok(5)    - sensor is working.
                "
            ::= { lqStateEntry 3 }

        
        lqStInletTemperatureSumState OBJECT-TYPE
            SYNTAX NotificationState
            MAX-ACCESS read-only
            STATUS current
            DESCRIPTION
                "Indicates whether the inlet temperature of coolant is 
                too high. If this problem is not caused by the ambient 
                air temperature of heat exchangers the pumps and the 
                fans of heat exchanger should be checked and the 
                filter should be cleaned.
                
                fault(3)   - exceeds fault limit
                warning(4) - exceeds warning limit
                ok(5)      - is ok
                "
            ::= { lqStateEntry 4 }

        
        lqStOutletTemperature OBJECT-TYPE
            SYNTAX Integer32
            UNITS "degree Celsius"
            MAX-ACCESS read-only
            STATUS current
            DESCRIPTION
                "Temperature of coolant before going into heat exchanger."
            ::= { lqStateEntry 5 }

        
        lqStOutletTemperatureSensor OBJECT-TYPE
            SYNTAX NotificationState
            MAX-ACCESS read-only
            STATUS current
            DESCRIPTION
                " Indicates the status of the temperature sensor at the outlet of the rack."
            ::= { lqStateEntry 6 }

        
        lqStOutletTemperatureSumState OBJECT-TYPE
            SYNTAX NotificationState
            MAX-ACCESS read-only
            STATUS current
            DESCRIPTION
                "Indicates whether the outlet temperature of coolant is too high. 
                If this problem is not caused by the ambient air temperature of 
                heat exchangers the pumps and the fans of heat exchanger 
                should be checked and the filter should be cleaned. 
                The display of this alarm disappears when the outlet 
                temperature is lower than the selected warning limit.
                
                off(2)
                fault(3)   - exceeds fault limit
                warning(4) - exceeds warning limit
                ok(5)      - is ok"
            ::= { lqStateEntry 7 }

        
        lqStCoolantPressure OBJECT-TYPE
            SYNTAX Unsigned32
            UNITS "deci bar"
            MAX-ACCESS read-only
            STATUS current
            DESCRIPTION
                "Coolant pressure."
            ::= { lqStateEntry 8 }

        
        lqStCoolantPressureSensor OBJECT-TYPE
            SYNTAX NotificationState
            MAX-ACCESS read-only
            STATUS current
            DESCRIPTION
                "Coolant pressure sensor state."
            ::= { lqStateEntry 9 }

        
        lqStCoolantPressureSumState OBJECT-TYPE
            SYNTAX NotificationState
            MAX-ACCESS read-only
            STATUS current
            DESCRIPTION
                "Indicates whether the coolant pressure is too low. 
                If a fault is displayed the cooling equipment should 
                be checked for a leakage and the filter should be cleaned.
                
                Possible values:
                off(2)       -
                fault(3)     - sensor fault
                warning(4)   - 
                ok(5)        - 
                "
            ::= { lqStateEntry 10 }

        
        lqStInletTemperatureFaultLimit OBJECT-TYPE
            SYNTAX Integer32
            UNITS "degree Celsius"
            MAX-ACCESS read-only
            STATUS obsolete
            DESCRIPTION
                "If the outlet temperature sensor is defective
                then an inlet temperature exceeding this value
                will lead to an error."
            ::= { lqStateEntry 11 }

        
        lqStInletTemperatureWarningLimit OBJECT-TYPE
            SYNTAX Integer32
            UNITS "degree Celsius"
            MAX-ACCESS read-only
            STATUS obsolete
            DESCRIPTION
                "If the outlet temperature sensor is defective
                then an inlet temperature exceeding this value
                will lead to a warning."
            ::= { lqStateEntry 12 }

        
        lqStCompactPumpDesiredSpeed OBJECT-TYPE
            SYNTAX Unsigned32 (0..100)
            UNITS "percent"
            MAX-ACCESS read-only
            STATUS current
            DESCRIPTION
                "Description."
            ::= { lqStateEntry 13 }

        
        lqPumpStateTable OBJECT-TYPE
            SYNTAX SEQUENCE OF LqPumpStateEntry
            MAX-ACCESS not-accessible
            STATUS current
            DESCRIPTION
                "pump state information"
            ::= { lqStatus 3 }

        
        lqPumpStateEntry OBJECT-TYPE
            SYNTAX LqPumpStateEntry
            MAX-ACCESS not-accessible
            STATUS current
            DESCRIPTION
                "An entry in the lqPumpStateTable."
            INDEX { lqNotificationCycleIdx, lqPStPumpIdx }
            ::= { lqPumpStateTable 1 }

        
        LqPumpStateEntry ::=
            SEQUENCE { 
                lqPStPumpIdx
                    Unsigned32,
                lqPStCommunicationState
                    NotificationState,
                lqPStSumState
                    NotificationState,
                lqPStMotorBlocked
                    NotificationState,
                lqPStOperatingHours
                    Unsigned32,
                lqPStType
                    SnmpAdminString,
                lqPStCurrentFlowRate
                    Unsigned32,
                lqPStCurrentSpeed
                    Unsigned32
             }

        lqPStPumpIdx OBJECT-TYPE
            SYNTAX Unsigned32 (1..2)
            MAX-ACCESS not-accessible
            STATUS current
            DESCRIPTION
                "pump index"
            ::= { lqPumpStateEntry 2 }

        
        lqPStCommunicationState OBJECT-TYPE
            SYNTAX NotificationState
            MAX-ACCESS read-only
            STATUS current
            DESCRIPTION
                "State of communication between TCE and pump."
            ::= { lqPumpStateEntry 3 }

        
        lqPStSumState OBJECT-TYPE
            SYNTAX NotificationState
            MAX-ACCESS read-only
            STATUS current
            DESCRIPTION
                "pump summary state"
            ::= { lqPumpStateEntry 4 }

        
        lqPStMotorBlocked OBJECT-TYPE
            SYNTAX NotificationState
            MAX-ACCESS read-only
            STATUS current
            DESCRIPTION
                "Indicates whether the pump motor can run freely or is 
                mechanically blocked. To rectify this fault, the pump 
                must be disassembled and checked for foreign objects.
                
                off(2)
                fault(3)   - blocked
                ok(5)
                "
            ::= { lqPumpStateEntry 5 }

        
        lqPStOperatingHours OBJECT-TYPE
            SYNTAX Unsigned32
            UNITS "hour"
            MAX-ACCESS read-only
            STATUS current
            DESCRIPTION
                "Operating hours of pump."
            ::= { lqPumpStateEntry 6 }

        
        lqPStType OBJECT-TYPE
            SYNTAX SnmpAdminString
            MAX-ACCESS read-only
            STATUS current
            DESCRIPTION
                "Indicates the used pump type. The displayed type is identical to 
                the type specified on the type plate of the pump. The type 
                'Magna2: 40-100' should be used for transmitters with up to 6 
                amplifiers.  The type 'Magna2: 32-120' should be used for 
                transmitters with more than 6 amplifiers. 
                "
            ::= { lqPumpStateEntry 7 }

        
        lqPStCurrentFlowRate OBJECT-TYPE
            SYNTAX Unsigned32
            UNITS "liter per minute"
            MAX-ACCESS read-only
            STATUS current
            DESCRIPTION
                "current flow rate of pump"
            ::= { lqPumpStateEntry 8 }

        
        lqPStCurrentSpeed OBJECT-TYPE
            SYNTAX Unsigned32
            UNITS "percent"
            MAX-ACCESS read-only
            STATUS current
            DESCRIPTION
                "rotational speed of pump motor"
            ::= { lqPumpStateEntry 9 }

        
        lqFanStateTable OBJECT-TYPE
            SYNTAX SEQUENCE OF LqFanStateEntry
            MAX-ACCESS not-accessible
            STATUS current
            DESCRIPTION
                "fan state table"
            ::= { lqStatus 4 }

        
        lqFanStateEntry OBJECT-TYPE
            SYNTAX LqFanStateEntry
            MAX-ACCESS not-accessible
            STATUS current
            DESCRIPTION
                "An entry in the lqFanStateTable."
            INDEX { lqNotificationCycleIdx, lqFStFanIdx }
            ::= { lqFanStateTable 1 }

        
        LqFanStateEntry ::=
            SEQUENCE { 
                lqFStFanIdx
                    Unsigned32,
                lqFStCommunicationState
                    NotificationState,
                lqFStSumState
                    NotificationState,
                lqFStMotorBlocked
                    NotificationState,
                lqFStOperatingHours
                    Unsigned32,
                lqFStSupplyFailure
                    NotificationState,
                lqFStCurrentSpeed
                    Unsigned32
             }

        lqFStFanIdx OBJECT-TYPE
            SYNTAX Unsigned32 (1..4)
            MAX-ACCESS not-accessible
            STATUS current
            DESCRIPTION
                "fan index"
            ::= { lqFanStateEntry 1 }

        
        lqFStCommunicationState OBJECT-TYPE
            SYNTAX NotificationState
            MAX-ACCESS read-only
            STATUS current
            DESCRIPTION
                "Indicates whether the assigned fan is correctly registered 
                on the fan communication bus.  If a fault is displayed the 
                corresponding task to re-register the fans on its 
                communication bus should be started.
                
                
                Possible values:
                off(2)       -
                fault(3)     - not found
                ok(5)        - installed
                "
            ::= { lqFanStateEntry 2 }

        
        lqFStSumState OBJECT-TYPE
            SYNTAX NotificationState
            MAX-ACCESS read-only
            STATUS current
            DESCRIPTION
                "fan summary state"
            ::= { lqFanStateEntry 3 }

        
        lqFStMotorBlocked OBJECT-TYPE
            SYNTAX NotificationState
            MAX-ACCESS read-only
            STATUS current
            DESCRIPTION
                "Shows whether the fan motor is mechanical blocked."
            ::= { lqFanStateEntry 4 }

        
        lqFStOperatingHours OBJECT-TYPE
            SYNTAX Unsigned32
            UNITS "hour"
            MAX-ACCESS read-only
            STATUS current
            DESCRIPTION
                "fan operating hours"
            ::= { lqFanStateEntry 5 }

        
        lqFStSupplyFailure OBJECT-TYPE
            SYNTAX NotificationState
            MAX-ACCESS read-only
            STATUS current
            DESCRIPTION
                "Shows whether the fan is disconnected from power supply."
            ::= { lqFanStateEntry 6 }

        
        lqFStCurrentSpeed OBJECT-TYPE
            SYNTAX Unsigned32
            UNITS "percent"
            MAX-ACCESS read-only
            STATUS current
            DESCRIPTION
                "rotational speed of fan motor"
            ::= { lqFanStateEntry 7 }

        
        lqConfiguration OBJECT IDENTIFIER ::= { rsXx9LiquidCoolingObjects 2 }

        
        lqConfigTable OBJECT-TYPE
            SYNTAX SEQUENCE OF LqConfigEntry
            MAX-ACCESS not-accessible
            STATUS current
            DESCRIPTION
                "Liquid cooling configuration."
            ::= { lqConfiguration 1 }

        
        lqConfigEntry OBJECT-TYPE
            SYNTAX LqConfigEntry
            MAX-ACCESS not-accessible
            STATUS current
            DESCRIPTION
                "An entry in the lqConfigTable table."
            INDEX { lqCfgCycleIdx }
            ::= { lqConfigTable 1 }

        
        LqConfigEntry ::=
            SEQUENCE { 
                lqCfgCycleIdx
                    Unsigned32,
                lqCfgType
                    INTEGER,
                lqCfgHeatExchangersPerRack
                    Unsigned32,
                lqCfgFansPerHeatExchanger
                    Unsigned32,
                lqCfgCoolantSetPointTemperature
                    Integer32,
                lqCfgCoolantTemperatureFaultLimit
                    Integer32,
                lqCfgCoolantTemperatureWarningLimit
                    Integer32,
                lqCfgCoolantPressureFaultLimit
                    Unsigned32,
                lqCfgCoolantPressureWarningLimit
                    Unsigned32,
                lqCfgFanMaxSpeed
                    Unsigned32,
                lqCfgPumpsExtraFlowRate
                    Unsigned32,
                lqCfgAntiFreeze
                    SwitchOnOff,
                lqCfgAutoOn
                    INTEGER
             }

        lqCfgCycleIdx OBJECT-TYPE
            SYNTAX Unsigned32 (1..12)
            MAX-ACCESS not-accessible
            STATUS current
            DESCRIPTION
                "Liquid cooling cycle index."
            ::= { lqConfigEntry 1 }

        
        lqCfgType OBJECT-TYPE
            SYNTAX INTEGER
                {
                coolingRS(1),
                coolingSite(2),
                coolingRSsmall(3),
                cooling8000(4)
                }
            MAX-ACCESS read-write
            STATUS current
            DESCRIPTION
                "coolingRS(1)      - XX9 cooling system
                coolingSite(2)    - already existing site cooling
                coolingRSsmall(3) - small XX9 cooling system
                cooling8000(4)    - legacy XX8000 cooling system"
            ::= { lqConfigEntry 2 }

        
        lqCfgHeatExchangersPerRack OBJECT-TYPE
            SYNTAX Unsigned32 (1..2)
            MAX-ACCESS read-write
            STATUS current
            DESCRIPTION
                "Number of heat exchangers per rack."
            ::= { lqConfigEntry 3 }

        
        lqCfgFansPerHeatExchanger OBJECT-TYPE
            SYNTAX Unsigned32 (1..2)
            MAX-ACCESS read-write
            STATUS current
            DESCRIPTION
                "Number of fans per heat exchanger."
            ::= { lqConfigEntry 4 }

        
        lqCfgCoolantSetPointTemperature OBJECT-TYPE
            SYNTAX Integer32 (20..65)
            UNITS "degree Celsius"
            MAX-ACCESS read-write
            STATUS current
            DESCRIPTION
                "The nominal value of the coolant temperature
                for fan control."
            ::= { lqConfigEntry 5 }

        
        lqCfgCoolantTemperatureFaultLimit OBJECT-TYPE
            SYNTAX Integer32 (50..65)
            UNITS "degree Celsius"
            MAX-ACCESS read-write
            STATUS current
            DESCRIPTION
                "A coolant temperature exceeding this value
                will lead to an error."
            ::= { lqConfigEntry 6 }

        
        lqCfgCoolantTemperatureWarningLimit OBJECT-TYPE
            SYNTAX Integer32 (40..65)
            UNITS "degree Celsius"
            MAX-ACCESS read-write
            STATUS current
            DESCRIPTION
                "A coolant temperature exceeding this value
                will lead to a warning."
            ::= { lqConfigEntry 7 }

        
        lqCfgCoolantPressureFaultLimit OBJECT-TYPE
            SYNTAX Unsigned32 (0..40)
            UNITS "deci bar"
            MAX-ACCESS read-write
            STATUS current
            DESCRIPTION
                "A coolant pressure equal or below this value
                will lead to an error."
            ::= { lqConfigEntry 8 }

        
        lqCfgCoolantPressureWarningLimit OBJECT-TYPE
            SYNTAX Unsigned32 (0..40)
            UNITS "deci bar"
            MAX-ACCESS read-write
            STATUS current
            DESCRIPTION
                "A coolant pressure equal or below this value
                will lead to a warning."
            ::= { lqConfigEntry 9 }

        
        lqCfgFanMaxSpeed OBJECT-TYPE
            SYNTAX Unsigned32 (50..100)
            UNITS "percent"
            MAX-ACCESS read-write
            STATUS current
            DESCRIPTION
                "You can diminish the fan speed for noise reduction.
                But this may lead to an unwanted increase of
                coolant temperature."
            ::= { lqConfigEntry 10 }

        
        lqCfgPumpsExtraFlowRate OBJECT-TYPE
            SYNTAX Unsigned32 (0..2)
            UNITS "10 liter per minute"
            MAX-ACCESS read-write
            STATUS current
            DESCRIPTION
                "If the cooling system is used for further components
                the flow rate can be increased in two steps.
                "
            ::= { lqConfigEntry 11 }

        
        lqCfgAntiFreeze OBJECT-TYPE
            SYNTAX SwitchOnOff
            MAX-ACCESS read-write
            STATUS current
            DESCRIPTION
                "Used to define whether or not the fans at the heat exchanger are 
                to switch off if the temperature drops well below the specified 
                temperature. 
                
                off(2): The fans switch off. This setting is recommended in order 
                to reduce the energy consumption of the cooling system. 
                on(1): The fans continue to run even at low outside temperatures. 
                This setting is recommended if the risk of fan seizure due to 
                freezing is to be reduced. Note: Even if antifreeze mode is active, 
                the condensation protection function of the transmitter will still 
                switch off the fans at an inlet temperature below approx. +10 deg C. 
                The fans are designed in such a way that they are not damaged 
                if they seize up due to freezing.
                "
            ::= { lqConfigEntry 12 }

        
        lqCfgAutoOn OBJECT-TYPE
            SYNTAX INTEGER
                {
                alwaysOn(1),
                autoOn(2)
                }
            MAX-ACCESS read-write
            STATUS current
            DESCRIPTION
                "If set to alwaysOn(1), the cooling system is switched on irrespective of whether or not the transmitter is on. 
                This setting should only be used when putting the system into operation. If the switch is set to autoOn(2), 
                the cooling system is switched on/off when the transmitter is switched on/off.
                "
            ::= { lqConfigEntry 13 }

        
        compactCoolingConfigTable OBJECT-TYPE
            SYNTAX SEQUENCE OF CompactCoolingConfigEntry
            MAX-ACCESS not-accessible
            STATUS current
            DESCRIPTION
                "Compact liquid cooling configuration."
            ::= { lqConfiguration 2 }

        
        compactCoolingConfigEntry OBJECT-TYPE
            SYNTAX CompactCoolingConfigEntry
            MAX-ACCESS not-accessible
            STATUS current
            DESCRIPTION
                "An entry in the compactCoolingConfigTable table."
            INDEX { compactCfgCycleIdx }
            ::= { compactCoolingConfigTable 1 }

        
        CompactCoolingConfigEntry ::=
            SEQUENCE { 
                compactCfgCycleIdx
                    Unsigned32,
                compactCfgHeatExchangers
                    Unsigned32,
                compactCfgFans
                    Unsigned32,
                compactCfgCoolantTemperatureFaultLimit
                    Integer32,
                compactCfgCoolantTemperatureWarningLimit
                    Integer32,
                compactCfgCoolantPressureFaultLimit
                    Unsigned32,
                compactCfgCoolantPressureWarningLimit
                    Unsigned32,
                compactCfgPumpsExtraFlowRate
                    Unsigned32,
                compactCfgAutoOn
                    INTEGER,
                compactCfgServiceMode
                    SwitchOnOff
             }

        compactCfgCycleIdx OBJECT-TYPE
            SYNTAX Unsigned32 (1)
            MAX-ACCESS not-accessible
            STATUS current
            DESCRIPTION
                "Integrated small cooling cycle index."
            ::= { compactCoolingConfigEntry 1 }

        
        compactCfgHeatExchangers OBJECT-TYPE
            SYNTAX Unsigned32 (1..2)
            MAX-ACCESS read-write
            STATUS current
            DESCRIPTION
                "Number of heat exchangers."
            ::= { compactCoolingConfigEntry 2 }

        
        compactCfgFans OBJECT-TYPE
            SYNTAX Unsigned32 (0..2)
            MAX-ACCESS read-write
            STATUS current
            DESCRIPTION
                "Number of fans per heat exchanger."
            ::= { compactCoolingConfigEntry 3 }

        
        compactCfgCoolantTemperatureFaultLimit OBJECT-TYPE
            SYNTAX Integer32 (50..65)
            UNITS "degree Celsius"
            MAX-ACCESS read-write
            STATUS current
            DESCRIPTION
                "A coolant temperature exceeding this value
                will lead to an error."
            ::= { compactCoolingConfigEntry 4 }

        
        compactCfgCoolantTemperatureWarningLimit OBJECT-TYPE
            SYNTAX Integer32 (40..65)
            UNITS "degree Celsius"
            MAX-ACCESS read-write
            STATUS current
            DESCRIPTION
                "A coolant temperature exceeding this value
                will lead to a warning."
            ::= { compactCoolingConfigEntry 5 }

        
        compactCfgCoolantPressureFaultLimit OBJECT-TYPE
            SYNTAX Unsigned32 (0..40)
            UNITS "deci bar"
            MAX-ACCESS read-write
            STATUS current
            DESCRIPTION
                "A coolant pressure equal or below this value
                will lead to an error."
            ::= { compactCoolingConfigEntry 6 }

        
        compactCfgCoolantPressureWarningLimit OBJECT-TYPE
            SYNTAX Unsigned32 (0..40)
            UNITS "deci bar"
            MAX-ACCESS read-write
            STATUS current
            DESCRIPTION
                "A coolant pressure equal or below this value
                will lead to a warning."
            ::= { compactCoolingConfigEntry 7 }

        
        compactCfgPumpsExtraFlowRate OBJECT-TYPE
            SYNTAX Unsigned32 (0..2)
            UNITS "10 liter per minute"
            MAX-ACCESS read-write
            STATUS current
            DESCRIPTION
                "If the cooling system is used for further components
                the flow rate can be increased in two steps.
                "
            ::= { compactCoolingConfigEntry 8 }

        
        compactCfgAutoOn OBJECT-TYPE
            SYNTAX INTEGER
                {
                alwaysOn(1),
                autoOn(2)
                }
            MAX-ACCESS read-write
            STATUS current
            DESCRIPTION
                "If set to alwaysOn(1), the cooling system is switched on irrespective of whether or not the transmitter is on. 
                This setting should only be used when putting the system into operation. If the switch is set to autoOn(2), 
                the cooling system is switched on/off when the transmitter is switched on/off.
                "
            ::= { compactCoolingConfigEntry 9 }

        
        compactCfgServiceMode OBJECT-TYPE
            SYNTAX SwitchOnOff
            MAX-ACCESS read-write
            STATUS current
            DESCRIPTION
                "Reduces cooling faults to warnings temporariliy. To keep the transmitter on air 
                when changing a pump the service mode should be activated. The service mode 
                deactivates itself after 5 hours or after a reboot of the system control unit. 
                "
            ::= { compactCoolingConfigEntry 10 }

        
        rsXx9LiquidCoolingConformance OBJECT IDENTIFIER ::= { rsXx9LiquidCooling 2 }

        
        rsXx9LqCompliances OBJECT IDENTIFIER ::= { rsXx9LiquidCoolingConformance 1 }

        
        lqRsCompliance MODULE-COMPLIANCE
            STATUS current
            DESCRIPTION 
                "The compliance statement for the XX9000 liquid cooling system
                if lqCfgType is coolingRS(1)."
            MODULE -- this module
                MANDATORY-GROUPS { rsXx9LqObjCommon, rsXx9LqObjRS, rsXx9LqNotifyCommon, rsXx9LqNotifyRS }
            ::= { rsXx9LqCompliances 1 }

        
        lqSiteCompliance MODULE-COMPLIANCE
            STATUS current
            DESCRIPTION 
                "The compliance statement for the XX9000 liquid cooling system
                if lqCfgType is coolingSite(2)."
            MODULE -- this module
                MANDATORY-GROUPS { rsXx9LqObjCommon, rsXx9LqNotifyCommon, rsXx9LqNotifySite }
            ::= { rsXx9LqCompliances 2 }

        
        lqRsSmallCompliance MODULE-COMPLIANCE
            STATUS current
            DESCRIPTION 
                "The compliance statement for the XX9000 liquid cooling system
                if lqCfgType is coolingRSsmall(3)."
            MODULE -- this module
                MANDATORY-GROUPS { rsXx9LqObjCommon, rsXx9LqNotifyCommon, rsXx9LqObjSmall }
            ::= { rsXx9LqCompliances 3 }

        
        lqCompactCompliance MODULE-COMPLIANCE
            STATUS current
            DESCRIPTION 
                "The compliance statement for the XX9000 compact liquid cooling system.
                ISCooling has a maximum number of 2 Fans. "
            MODULE -- this module
                MANDATORY-GROUPS { rsXx9LqNotifyCommon, rsXx9CompactCoolingObjs, rsXx9CompactCoolingNotify }
            ::= { rsXx9LqCompliances 4 }

        
        rsXx9LqGroups OBJECT IDENTIFIER ::= { rsXx9LiquidCoolingConformance 2 }

        
        rsXx9LqObjCommon OBJECT-GROUP
            OBJECTS { lqNotificationName, lqNotificationMask, lqNotificationPriority, lqNotificationState, lqCfgType, 
                lqCfgCoolantTemperatureFaultLimit, lqCfgAutoOn, lqCfgCoolantTemperatureWarningLimit, lqStInletTemperature, lqStInletTemperatureSensor, 
                lqStInletTemperatureSumState, lqStOutletTemperature, lqStOutletTemperatureSensor, lqStOutletTemperatureSumState, lqStCoolantPressure, 
                lqStCoolantPressureSensor, lqStCoolantPressureSumState }
            STATUS current
            DESCRIPTION 
                "common (non ISC) liquid cooling objects"
            ::= { rsXx9LqGroups 1 }

        
        rsXx9LqObjRS OBJECT-GROUP
            OBJECTS { lqPStCommunicationState, lqPStSumState, lqPStMotorBlocked, lqPStOperatingHours, lqPStType, 
                lqPStCurrentFlowRate, lqPStCurrentSpeed, lqFStCommunicationState, lqFStSumState, lqFStMotorBlocked, 
                lqFStOperatingHours, lqFStSupplyFailure, lqFStCurrentSpeed, lqCfgHeatExchangersPerRack, lqCfgFansPerHeatExchanger, 
                lqCfgCoolantSetPointTemperature, lqCfgCoolantPressureFaultLimit, lqCfgCoolantPressureWarningLimit, lqCfgFanMaxSpeed, lqCfgPumpsExtraFlowRate, 
                lqCfgAntiFreeze }
            STATUS current
            DESCRIPTION 
                "Additional R&S liquid cooling objects"
            ::= { rsXx9LqGroups 2 }

        
        rsXx9LqObjSmall OBJECT-GROUP
            OBJECTS { lqCfgCoolantPressureFaultLimit, lqCfgCoolantPressureWarningLimit }
            STATUS current
            DESCRIPTION 
                "Additional objects for small liquid cooling."
            ::= { rsXx9LqGroups 3 }

        
        rsXx9LqNotifyCommon NOTIFICATION-GROUP
            NOTIFICATIONS { lqSummary }
            STATUS current
            DESCRIPTION 
                "common liquid cooling notifications"
            ::= { rsXx9LqGroups 4 }

        
        rsXx9LqNotifyRS NOTIFICATION-GROUP
            NOTIFICATIONS { lqFilterSummary, lqSensorsSummary }
            STATUS current
            DESCRIPTION 
                "Additional R&S liquid cooling notifications"
            ::= { rsXx9LqGroups 5 }

        
        rsXx9LqNotifySite NOTIFICATION-GROUP
            NOTIFICATIONS { lqSiteWarning, lqSiteFault }
            STATUS current
            DESCRIPTION 
                "Additional site liquid cooling notifications"
            ::= { rsXx9LqGroups 6 }

        
        rsXx9LqObjsObsoleted OBJECT-GROUP
            OBJECTS { lqStInletTemperatureFaultLimit, lqStInletTemperatureWarningLimit }
            STATUS obsolete
            DESCRIPTION 
                "Obsoleted objects."
            ::= { rsXx9LqGroups 7 }

        
        rsXx9CompactCoolingObjs OBJECT-GROUP
            OBJECTS { lqPStType, lqFStSumState, lqStCoolantPressureSumState, lqStCoolantPressureSensor, lqStCoolantPressure, 
                lqStOutletTemperatureSumState, lqStOutletTemperatureSensor, lqStOutletTemperature, lqStInletTemperatureSumState, lqStInletTemperatureSensor, 
                lqStInletTemperature, lqPStSumState, lqNotificationName, lqNotificationMask, lqNotificationPriority, 
                lqNotificationState, compactCfgHeatExchangers, compactCfgCoolantTemperatureFaultLimit, compactCfgCoolantTemperatureWarningLimit, compactCfgCoolantPressureFaultLimit, 
                compactCfgCoolantPressureWarningLimit, compactCfgPumpsExtraFlowRate, lqStCompactPumpDesiredSpeed, compactCfgServiceMode, compactCfgAutoOn, 
                compactCfgFans }
            STATUS current
            DESCRIPTION 
                "Compact liquid cooling objects."
            ::= { rsXx9LqGroups 100 }

        
        rsXx9CompactCoolingNotify NOTIFICATION-GROUP
            NOTIFICATIONS { lqSensorsSummary, lqSiteWarning, lqSiteFault }
            STATUS current
            DESCRIPTION 
                "Compact liquid cooling notifications."
            ::= { rsXx9LqGroups 200 }

        
    
    END

--
-- RS-XX9-LIQUID-COOLING-MIB.mi2
--
