ACOS-VCSVBLADES-STAT-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		vcsVbladesStatModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "vcsVbladesStatModule OID for ACOS"
				::=  {  acosSchema 497 }

stat		 OBJECT IDENTIFIER ::= { vcsVbladesStatModule 1}

statStatsTable OBJECT-TYPE
	 SYNTAX SEQUENCE OF StatStatsEntry
	 MAX-ACCESS not-accessible
	 STATUS current
	 DESCRIPTION
	 "Show aVCS vBlade box statistics information from object 'vcs-vblades.stat'"
	::= {stat 1}

statStatsEntry OBJECT-TYPE
	SYNTAX StatStatsEntry
	MAX-ACCESS not-accessible
	STATUS current
	DESCRIPTION
		"The statStats stats entry"
	INDEX {
		statStatsSlotId,
		statStatsVbladeId
	}
	::= { statStatsTable 1 }

StatStatsEntry ::=
	SEQUENCE {
		statStatsSlotId Integer32,
		statStatsVbladeId Integer32,
		statStatsSlaveRecvErr	 CounterBasedGauge64,
		statStatsSlaveSendErr	 CounterBasedGauge64,
		statStatsSlaveRecvBytes	 CounterBasedGauge64,
		statStatsSlaveSentBytes	 CounterBasedGauge64,
		statStatsSlaveNRecv	 CounterBasedGauge64,
		statStatsSlaveNSent	 CounterBasedGauge64,
		statStatsSlaveMsgInval	 CounterBasedGauge64,
		statStatsSlaveKeepalive	 CounterBasedGauge64,
		statStatsSlaveCfgUpd	 CounterBasedGauge64,
		statStatsSlaveCfgUpdL1Fail	 CounterBasedGauge64,
		statStatsSlaveCfgUpdRFail	 CounterBasedGauge64,
		statStatsSlaveCfgUpdL2Fail	 CounterBasedGauge64,
		statStatsSlaveCfgUpdNotifErr	 CounterBasedGauge64,
		statStatsSlaveCfgUpdResultErr	 CounterBasedGauge64
	}

statStatsSlotId OBJECT-TYPE
	 SYNTAX Integer32
	 MAX-ACCESS read-only
	 STATUS current
	 DESCRIPTION
		 ""
	::= { statStatsEntry 1 }

statStatsVbladeId OBJECT-TYPE
	 SYNTAX Integer32
	 MAX-ACCESS read-only
	 STATUS current
	 DESCRIPTION
		 "vblade-id"
	::= { statStatsEntry 2 }

statStatsSlaveRecvErr OBJECT-TYPE
	 SYNTAX Integer32
	 MAX-ACCESS read-only
	 STATUS current
	 DESCRIPTION
		 "slave_recv_err"
	::= { statStatsEntry 3 }

statStatsSlaveSendErr OBJECT-TYPE
	 SYNTAX Integer32
	 MAX-ACCESS read-only
	 STATUS current
	 DESCRIPTION
		 "slave_send_err"
	::= { statStatsEntry 4 }

statStatsSlaveRecvBytes OBJECT-TYPE
	 SYNTAX Integer32
	 MAX-ACCESS read-only
	 STATUS current
	 DESCRIPTION
		 "slave_recv_bytes"
	::= { statStatsEntry 5 }

statStatsSlaveSentBytes OBJECT-TYPE
	 SYNTAX Integer32
	 MAX-ACCESS read-only
	 STATUS current
	 DESCRIPTION
		 "slave_sent_bytes"
	::= { statStatsEntry 6 }

statStatsSlaveNRecv OBJECT-TYPE
	 SYNTAX Integer32
	 MAX-ACCESS read-only
	 STATUS current
	 DESCRIPTION
		 "slave_n_recv"
	::= { statStatsEntry 7 }

statStatsSlaveNSent OBJECT-TYPE
	 SYNTAX Integer32
	 MAX-ACCESS read-only
	 STATUS current
	 DESCRIPTION
		 "slave_n_sent"
	::= { statStatsEntry 8 }

statStatsSlaveMsgInval OBJECT-TYPE
	 SYNTAX Integer32
	 MAX-ACCESS read-only
	 STATUS current
	 DESCRIPTION
		 "slave_msg_inval"
	::= { statStatsEntry 9 }

statStatsSlaveKeepalive OBJECT-TYPE
	 SYNTAX Integer32
	 MAX-ACCESS read-only
	 STATUS current
	 DESCRIPTION
		 "slave_keepalive"
	::= { statStatsEntry 10 }

statStatsSlaveCfgUpd OBJECT-TYPE
	 SYNTAX Integer32
	 MAX-ACCESS read-only
	 STATUS current
	 DESCRIPTION
		 "slave_cfg_upd"
	::= { statStatsEntry 11 }

statStatsSlaveCfgUpdL1Fail OBJECT-TYPE
	 SYNTAX Integer32
	 MAX-ACCESS read-only
	 STATUS current
	 DESCRIPTION
		 "slave_cfg_upd_l1_fail"
	::= { statStatsEntry 12 }

statStatsSlaveCfgUpdRFail OBJECT-TYPE
	 SYNTAX Integer32
	 MAX-ACCESS read-only
	 STATUS current
	 DESCRIPTION
		 "slave_cfg_upd_r_fail"
	::= { statStatsEntry 13 }

statStatsSlaveCfgUpdL2Fail OBJECT-TYPE
	 SYNTAX Integer32
	 MAX-ACCESS read-only
	 STATUS current
	 DESCRIPTION
		 "slave_cfg_upd_l2_fail"
	::= { statStatsEntry 14 }

statStatsSlaveCfgUpdNotifErr OBJECT-TYPE
	 SYNTAX Integer32
	 MAX-ACCESS read-only
	 STATUS current
	 DESCRIPTION
		 "slave_cfg_upd_notif_err"
	::= { statStatsEntry 15 }

statStatsSlaveCfgUpdResultErr OBJECT-TYPE
	 SYNTAX Integer32
	 MAX-ACCESS read-only
	 STATUS current
	 DESCRIPTION
		 "slave_cfg_upd_result_err"
	::= { statStatsEntry 16 }

END
