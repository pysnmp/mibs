ACOS-VCS-VCS-SUMMARY-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		vcsVcsSummaryModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "vcsVcsSummaryModule OID for ACOS"
				::=  {  acosSchema 15 }

vcsSummary		 OBJECT IDENTIFIER ::= { vcsVcsSummaryModule 1}

vcsSummaryOperTable OBJECT-TYPE
	 SYNTAX SEQUENCE OF VcsSummaryOperEntry
	 MAX-ACCESS not-accessible
	 STATUS current
	 DESCRIPTION
		 "VCS Summary Information from object 'vcs.vcs-summary'"
	::= {vcsSummary 2}

vcsSummaryOperEntry OBJECT-TYPE
	SYNTAX VcsSummaryOperEntry
	MAX-ACCESS not-accessible
	STATUS current
	DESCRIPTION
		"The vcsSummaryOper entry"
	INDEX {
		vcsSummaryOperSlotId
	}
	::= { vcsSummaryOperTable 1 }

VcsSummaryOperEntry ::=
	SEQUENCE {
		vcsSummaryOperSlotId Integer32,
		vcsSummaryOperVcsEnabled	 DisplayString,
		vcsSummaryOperChassisId	 Integer32,
		vcsSummaryOperMulticastAddr	 DisplayString,
		vcsSummaryOperMulticastPort	 Integer32,
		vcsSummaryOperVersion	 DisplayString,
		vcsSummaryOperVmasterMaintenanceInterval	 Integer32,
		vcsSummaryOperVmasterMaintenanceLeft	 Integer32
	}

vcsSummaryOperSlotId OBJECT-TYPE
	 SYNTAX Integer32
	 MAX-ACCESS read-only
	 STATUS current
	 DESCRIPTION
		 ""
	::= { vcsSummaryOperEntry 1 }

vcsSummaryOperVcsEnabled OBJECT-TYPE
	 SYNTAX DisplayString
	 MAX-ACCESS read-only
	 STATUS current
	 DESCRIPTION
		 "vcs-enabled"
	::= { vcsSummaryOperEntry 2 }

vcsSummaryOperChassisId OBJECT-TYPE
	 SYNTAX Integer32
	 MAX-ACCESS read-only
	 STATUS current
	 DESCRIPTION
		 "chassis-id"
	::= { vcsSummaryOperEntry 3 }

vcsSummaryOperMulticastAddr OBJECT-TYPE
	 SYNTAX DisplayString
	 MAX-ACCESS read-only
	 STATUS current
	 DESCRIPTION
		 "multicast-addr"
	::= { vcsSummaryOperEntry 4 }

vcsSummaryOperMulticastPort OBJECT-TYPE
	 SYNTAX Integer32
	 MAX-ACCESS read-only
	 STATUS current
	 DESCRIPTION
		 "multicast-port"
	::= { vcsSummaryOperEntry 5 }

vcsSummaryOperVersion OBJECT-TYPE
	 SYNTAX DisplayString
	 MAX-ACCESS read-only
	 STATUS current
	 DESCRIPTION
		 "version"
	::= { vcsSummaryOperEntry 6 }

vcsSummaryOperVmasterMaintenanceInterval OBJECT-TYPE
	 SYNTAX Integer32
	 MAX-ACCESS read-only
	 STATUS current
	 DESCRIPTION
		 "vmaster-maintenance-interval"
	::= { vcsSummaryOperEntry 7 }

vcsSummaryOperVmasterMaintenanceLeft OBJECT-TYPE
	 SYNTAX Integer32
	 MAX-ACCESS read-only
	 STATUS current
	 DESCRIPTION
		 "vmaster-maintenance-left"
	::= { vcsSummaryOperEntry 8 }

vcsSummaryOperVcsHandshakeCompletedListTable OBJECT-TYPE
	 SYNTAX SEQUENCE OF VcsSummaryOperVcsHandshakeCompletedListEntry
	 MAX-ACCESS not-accessible
	 STATUS current
	 DESCRIPTION
		 "VCS Summary Information from object 'vcs.vcs-summary'"
	::= {vcsSummary 3}

vcsSummaryOperVcsHandshakeCompletedListEntry OBJECT-TYPE
	SYNTAX VcsSummaryOperVcsHandshakeCompletedListEntry
	MAX-ACCESS not-accessible
	STATUS current
	DESCRIPTION
		"The vcsSummaryOperVcsHandshakeCompletedList entry:vcs-handshake-completed-list"
	INDEX {
		vcsSummaryOperVcsHandshakeCompletedListSlotId,
		vcsSummaryOperVcsHandshakeCompletedListVcsHandshakeCompletedListListId
	}
	::= { vcsSummaryOperVcsHandshakeCompletedListTable 1}

VcsSummaryOperVcsHandshakeCompletedListEntry ::=
	SEQUENCE {
		vcsSummaryOperVcsHandshakeCompletedListSlotId Integer32,
		vcsSummaryOperVcsHandshakeCompletedListVcsHandshakeCompletedListListId Integer32,
		vcsSummaryOperVcsHandshakeCompletedListVcsHandshakeCompletedId	Integer32,
		vcsSummaryOperVcsHandshakeCompletedListVcsHandshakeCompleted	Integer32
	}

vcsSummaryOperVcsHandshakeCompletedListSlotId OBJECT-TYPE
	SYNTAX Integer32
	MAX-ACCESS read-only
	STATUS current
	DESCRIPTION
		""
	::= { vcsSummaryOperVcsHandshakeCompletedListEntry 1}

vcsSummaryOperVcsHandshakeCompletedListVcsHandshakeCompletedListListId OBJECT-TYPE
	SYNTAX Integer32
	MAX-ACCESS read-only
	STATUS current
	DESCRIPTION
		""
	::= { vcsSummaryOperVcsHandshakeCompletedListEntry 2}

vcsSummaryOperVcsHandshakeCompletedListVcsHandshakeCompletedId OBJECT-TYPE
	SYNTAX Integer32
	MAX-ACCESS read-only
	STATUS current
	DESCRIPTION
		"vcs-handshake-completed-id"
	::= { vcsSummaryOperVcsHandshakeCompletedListEntry 3}

vcsSummaryOperVcsHandshakeCompletedListVcsHandshakeCompleted OBJECT-TYPE
	SYNTAX Integer32
	MAX-ACCESS read-only
	STATUS current
	DESCRIPTION
		"vcs-handshake-completed"
	::= { vcsSummaryOperVcsHandshakeCompletedListEntry 4}

vcsSummaryOperFloatingIpv4ListTable OBJECT-TYPE
	 SYNTAX SEQUENCE OF VcsSummaryOperFloatingIpv4ListEntry
	 MAX-ACCESS not-accessible
	 STATUS current
	 DESCRIPTION
		 "VCS Summary Information from object 'vcs.vcs-summary'"
	::= {vcsSummary 4}

vcsSummaryOperFloatingIpv4ListEntry OBJECT-TYPE
	SYNTAX VcsSummaryOperFloatingIpv4ListEntry
	MAX-ACCESS not-accessible
	STATUS current
	DESCRIPTION
		"The vcsSummaryOperFloatingIpv4List entry:floating-ipv4-list"
	INDEX {
		vcsSummaryOperFloatingIpv4ListSlotId,
		vcsSummaryOperFloatingIpv4ListFloatingIpv4ListListId
	}
	::= { vcsSummaryOperFloatingIpv4ListTable 1}

VcsSummaryOperFloatingIpv4ListEntry ::=
	SEQUENCE {
		vcsSummaryOperFloatingIpv4ListSlotId Integer32,
		vcsSummaryOperFloatingIpv4ListFloatingIpv4ListListId Integer32,
		vcsSummaryOperFloatingIpv4ListFloatingIpv4	DisplayString,
		vcsSummaryOperFloatingIpv4ListFloatingIpv4Mask	DisplayString
	}

vcsSummaryOperFloatingIpv4ListSlotId OBJECT-TYPE
	SYNTAX Integer32
	MAX-ACCESS read-only
	STATUS current
	DESCRIPTION
		""
	::= { vcsSummaryOperFloatingIpv4ListEntry 1}

vcsSummaryOperFloatingIpv4ListFloatingIpv4ListListId OBJECT-TYPE
	SYNTAX Integer32
	MAX-ACCESS read-only
	STATUS current
	DESCRIPTION
		""
	::= { vcsSummaryOperFloatingIpv4ListEntry 2}

vcsSummaryOperFloatingIpv4ListFloatingIpv4 OBJECT-TYPE
	SYNTAX DisplayString
	MAX-ACCESS read-only
	STATUS current
	DESCRIPTION
		"floating-ipv4"
	::= { vcsSummaryOperFloatingIpv4ListEntry 3}

vcsSummaryOperFloatingIpv4ListFloatingIpv4Mask OBJECT-TYPE
	SYNTAX DisplayString
	MAX-ACCESS read-only
	STATUS current
	DESCRIPTION
		"floating-ipv4-mask"
	::= { vcsSummaryOperFloatingIpv4ListEntry 4}

vcsSummaryOperFloatingIpv6ListTable OBJECT-TYPE
	 SYNTAX SEQUENCE OF VcsSummaryOperFloatingIpv6ListEntry
	 MAX-ACCESS not-accessible
	 STATUS current
	 DESCRIPTION
		 "VCS Summary Information from object 'vcs.vcs-summary'"
	::= {vcsSummary 5}

vcsSummaryOperFloatingIpv6ListEntry OBJECT-TYPE
	SYNTAX VcsSummaryOperFloatingIpv6ListEntry
	MAX-ACCESS not-accessible
	STATUS current
	DESCRIPTION
		"The vcsSummaryOperFloatingIpv6List entry:floating-ipv6-list"
	INDEX {
		vcsSummaryOperFloatingIpv6ListSlotId,
		vcsSummaryOperFloatingIpv6ListFloatingIpv6ListListId
	}
	::= { vcsSummaryOperFloatingIpv6ListTable 1}

VcsSummaryOperFloatingIpv6ListEntry ::=
	SEQUENCE {
		vcsSummaryOperFloatingIpv6ListSlotId Integer32,
		vcsSummaryOperFloatingIpv6ListFloatingIpv6ListListId Integer32,
		vcsSummaryOperFloatingIpv6ListFloatingIpv6	DisplayString,
		vcsSummaryOperFloatingIpv6ListFloatingIpv6Prefix	Integer32
	}

vcsSummaryOperFloatingIpv6ListSlotId OBJECT-TYPE
	SYNTAX Integer32
	MAX-ACCESS read-only
	STATUS current
	DESCRIPTION
		""
	::= { vcsSummaryOperFloatingIpv6ListEntry 1}

vcsSummaryOperFloatingIpv6ListFloatingIpv6ListListId OBJECT-TYPE
	SYNTAX Integer32
	MAX-ACCESS read-only
	STATUS current
	DESCRIPTION
		""
	::= { vcsSummaryOperFloatingIpv6ListEntry 2}

vcsSummaryOperFloatingIpv6ListFloatingIpv6 OBJECT-TYPE
	SYNTAX DisplayString
	MAX-ACCESS read-only
	STATUS current
	DESCRIPTION
		"floating-ipv6"
	::= { vcsSummaryOperFloatingIpv6ListEntry 3}

vcsSummaryOperFloatingIpv6ListFloatingIpv6Prefix OBJECT-TYPE
	SYNTAX Integer32
	MAX-ACCESS read-only
	STATUS current
	DESCRIPTION
		"floating-ipv6-prefix"
	::= { vcsSummaryOperFloatingIpv6ListEntry 4}

vcsSummaryOperMemberListTable OBJECT-TYPE
	 SYNTAX SEQUENCE OF VcsSummaryOperMemberListEntry
	 MAX-ACCESS not-accessible
	 STATUS current
	 DESCRIPTION
		 "VCS Summary Information from object 'vcs.vcs-summary'"
	::= {vcsSummary 6}

vcsSummaryOperMemberListEntry OBJECT-TYPE
	SYNTAX VcsSummaryOperMemberListEntry
	MAX-ACCESS not-accessible
	STATUS current
	DESCRIPTION
		"The vcsSummaryOperMemberList entry:member-list"
	INDEX {
		vcsSummaryOperMemberListSlotId,
		vcsSummaryOperMemberListMemberListListId
	}
	::= { vcsSummaryOperMemberListTable 1}

VcsSummaryOperMemberListEntry ::=
	SEQUENCE {
		vcsSummaryOperMemberListSlotId Integer32,
		vcsSummaryOperMemberListMemberListListId Integer32,
		vcsSummaryOperMemberListId	Integer32,
		vcsSummaryOperMemberListState	DisplayString,
		vcsSummaryOperMemberListPriority	Integer32,
		vcsSummaryOperMemberListPort	Integer32,
		vcsSummaryOperMemberListLocation	DisplayString
	}

vcsSummaryOperMemberListSlotId OBJECT-TYPE
	SYNTAX Integer32
	MAX-ACCESS read-only
	STATUS current
	DESCRIPTION
		""
	::= { vcsSummaryOperMemberListEntry 1}

vcsSummaryOperMemberListMemberListListId OBJECT-TYPE
	SYNTAX Integer32
	MAX-ACCESS read-only
	STATUS current
	DESCRIPTION
		""
	::= { vcsSummaryOperMemberListEntry 2}

vcsSummaryOperMemberListId OBJECT-TYPE
	SYNTAX Integer32
	MAX-ACCESS read-only
	STATUS current
	DESCRIPTION
		"id"
	::= { vcsSummaryOperMemberListEntry 3}

vcsSummaryOperMemberListState OBJECT-TYPE
	SYNTAX DisplayString
	MAX-ACCESS read-only
	STATUS current
	DESCRIPTION
		"state"
	::= { vcsSummaryOperMemberListEntry 4}

vcsSummaryOperMemberListPriority OBJECT-TYPE
	SYNTAX Integer32
	MAX-ACCESS read-only
	STATUS current
	DESCRIPTION
		"priority"
	::= { vcsSummaryOperMemberListEntry 5}

vcsSummaryOperMemberListPort OBJECT-TYPE
	SYNTAX Integer32
	MAX-ACCESS read-only
	STATUS current
	DESCRIPTION
		"port"
	::= { vcsSummaryOperMemberListEntry 6}

vcsSummaryOperMemberListLocation OBJECT-TYPE
	SYNTAX DisplayString
	MAX-ACCESS read-only
	STATUS current
	DESCRIPTION
		"location"
	::= { vcsSummaryOperMemberListEntry 7}

vcsSummaryOperMemberListIpListTable OBJECT-TYPE
	 SYNTAX SEQUENCE OF VcsSummaryOperMemberListIpListEntry
	 MAX-ACCESS not-accessible
	 STATUS current
	 DESCRIPTION
		 "VCS Summary Information from object 'vcs.vcs-summary'"
	::= {vcsSummary 7}

vcsSummaryOperMemberListIpListEntry OBJECT-TYPE
	SYNTAX VcsSummaryOperMemberListIpListEntry
	MAX-ACCESS not-accessible
	STATUS current
	DESCRIPTION
		"The vcsSummaryOperMemberListIpList entry:ip-list"
	INDEX {
		vcsSummaryOperMemberListIpListSlotId,
		vcsSummaryOperMemberListIpListMemberListListId,
		vcsSummaryOperMemberListIpListIpListListId
	}
	::= { vcsSummaryOperMemberListIpListTable 1}

VcsSummaryOperMemberListIpListEntry ::=
	SEQUENCE {
		vcsSummaryOperMemberListIpListSlotId Integer32,
		vcsSummaryOperMemberListIpListMemberListListId Integer32,
		vcsSummaryOperMemberListIpListIpListListId Integer32,
		vcsSummaryOperMemberListIpListIp	DisplayString
	}

vcsSummaryOperMemberListIpListSlotId OBJECT-TYPE
	SYNTAX Integer32
	MAX-ACCESS read-only
	STATUS current
	DESCRIPTION
		""
	::= { vcsSummaryOperMemberListIpListEntry 1}

vcsSummaryOperMemberListIpListMemberListListId OBJECT-TYPE
	SYNTAX Integer32
	MAX-ACCESS read-only
	STATUS current
	DESCRIPTION
		""
	::= { vcsSummaryOperMemberListIpListEntry 2}

vcsSummaryOperMemberListIpListIpListListId OBJECT-TYPE
	SYNTAX Integer32
	MAX-ACCESS read-only
	STATUS current
	DESCRIPTION
		""
	::= { vcsSummaryOperMemberListIpListEntry 3}

vcsSummaryOperMemberListIpListIp OBJECT-TYPE
	SYNTAX DisplayString
	MAX-ACCESS read-only
	STATUS current
	DESCRIPTION
		"ip"
	::= { vcsSummaryOperMemberListIpListEntry 4}

END
