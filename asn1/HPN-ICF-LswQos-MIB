-- ------------------------------------------------------------------
-- Copyright (c) 2010-2013 Hewlett-Packard Development Company, L.P.
--
-- Descripton: Qos MIB
--
-- History V2.3
--     V1.0 2002-11-18 created by qizhenglin
--     V1.1 2004-05-09 add and modify hpnicfPortWredTable by tangshun
--     V1.2 2004-08-05 modify hpnicfQueueScheduleMode(add hq_wrr(9)) by qizhenglin
--     v1.3 2004-08-12 add hpnicfFlowtempVlanId,hpnicfFlowtempCos to hpnicfFlowtempTable
--     v1.4 2004-09-17 change value range of hpnicfRateLimitTargetRateKbps from 200..100000
--          to 64..1000000 by zhuangyu
--     v1.5 2004-10-12 updated by gaolong
--          Import Counter64.
--          Remove some adjacent hyphens
--          Rewrite value of hpnicfQueueScheduleMode and hpnicfRateLimitConformActionType.
--          Change all underscore('_') characters to hyphen characters('-') because
--          underscore character is not allowed in MIB module.
--     v1.51 2004-10-27 changed by zhuangyu
--          1 Add an enumeration in hpnicfRateLimitConformActionType
--          2 Add hpnicfRateLimitConformCos and hpnicfRateLimitConformDscp in hpnicfRateLimitTable
--          3 Import IpAddress
--     v1.52 2004-12-13 updated by jinyi
--          Fix syntax bugs and adjust format of the whole file.
--     v1.53 2004-12-13 updated by zhuangyu
--          Modify description of hpnicfRateLimitExceedDscp,hpnicfRateLimitConformDscp and hpnicfPriorityDscp.
--     v1.6 2004-12-1 changed by yangjianjun
--          Add  hpnicfMirroringGroupTable
--               hpnicfMirroringGroupMirrorTable
--               hpnicfMirroringGroupMonitorTable
--               hpnicfMirroringGroupReflectorTable
--               hpnicfMirroringGroupRprobeVlanTable
--     v1.7 2005-4-6 changed by fanghailin
--          Add hpnicfRedirectToSlotNo hpnicfRedirectRemarkedDSCP hpnicfRedirectRemarkedPri hpnicfRedirectRemarkedTos
--          hpnicfRedirectToNextHop3 hpnicfRedirectTargetVlan hpnicfRedirectMode
--          in hpnicfRedirectTable Notice:All the nodes are used only for L3plus funtion and speciality.
--     v1.8 2005-5-18 updated by zhangyinxi
--          Add  hpnicfRedirectToNestedVlanID and hpnicfRedirectToModifiedVlanID
--     v1.9 2005-6-27
--          1. Add hpnicfMirroringGroupMirrorMacTable, hpnicfMirroringGroupMirrorVlanTable,
--             hpnicfPortTrustTable, hpnicfRemarkVlanIDTable, hpnicfCosToDscpMapTable, hpnicfDscpToLocalPreMapTable,
--             hpnicfDscpToDropPreMapTable, hpnicfDscpToCosMapTable, hpnicfDscpToDscpMapTable,
--             hpnicfRateLimitMeterStatByteCount, hpnicfRateLimitMeterStatByteXCount,
--             hpnicfRateLimitMeterStatState by liyan and wangyingxia
--          2. Modify the range of hpnicfRateLimitTargetRateKbps by liyan and wangyingxia
--          3. Add hpnicfMirrorToGroup in hpnicfMirrorTable by yubin
--     v2.0 2005-10-25 updated by houli
--          1. Remove value range of hpnicfLineRateValue
--          2. Remove value range of hpnicfRateLimitTargetRateMbps
--     V2.1 2005-11-07 update by wangyingxia
--          1. Add HpnicfMirrorOrMonitorType and hpnicfMirroringGroupMonitorType
--          2. Modify the description of hpnicfMirroringGroupMonitorIfIndex
--          3. Change the value range of hpnicfRedirectTargetVlan by lihaijun
--     V2.2 2005-12-19 update by wangyingxia
--          1. Add hpnicfMirroringGroupMirrorInTypeList, hpnicfMirroringGroupMirrorOutTypeList
--             by wangyingxia
--          2. change the description of hpnicfMirroringGroupMirrorInboundIfIndexList  
--             add hpnicfMirroringGroupMirrorOutboundIfIndexList by wangyingxia
--     v2.3 2006-01-16 updated by houli
--          1. Remove value range of hpnicfTrafficShapeMaxRate
--          2. Remove value range of hpnicfTrafficShapeBurstSize
-- ------------------------------------------------------------------
-- ------------------------------------------------------------------
--
-- Import and definition
--
-- ------------------------------------------------------------------
HPN-ICF-LswQos-MIB DEFINITIONS ::= BEGIN

IMPORTS

    Integer32, MODULE-IDENTITY,OBJECT-TYPE,Counter32, Counter64,IpAddress
        FROM SNMPv2-SMI
    TruthValue, MacAddress, RowStatus, TEXTUAL-CONVENTION
        FROM SNMPv2-TC
    hpnicflswCommon
        FROM HPN-ICF-OID-MIB;


---------- Following is for Node:hpnicfLswQosMib --------
  hpnicfLswQosAclMib MODULE-IDENTITY
    LAST-UPDATED "200211190000Z"
    ORGANIZATION
        ""
    CONTACT-INFO
        ""
    DESCRIPTION
      "Module node for qos and acl."
    REVISION "200211190000Z"
    DESCRIPTION
      "Table of qos and acl."
    ::= { hpnicflswCommon  16 }

  HpnicfMirrorOrMonitorType ::= TEXTUAL-CONVENTION
    STATUS current
    DESCRIPTION
    "
     Specify the mirror source or destination type.
     port(1):
        the mirror source or destination is port.
     board(2):
        the mirror source or destination is board.
    "
    SYNTAX INTEGER
    {
       port(1),
       board(2)
    }

---------- Following is for Node:hpnicfLswQosMibObject --------
  hpnicfLswQosMibObject OBJECT IDENTIFIER ::= {  hpnicfLswQosAclMib 2  }

  hpnicfPriorityTrustMode OBJECT-TYPE
    SYNTAX      INTEGER
            {
                default(0),
                dscp(1),
                ipprecedence(2),
                cos(3),
                localprecedence(4)
            }
    MAX-ACCESS  read-write
    STATUS      current
    DESCRIPTION
      "Priority type of inbound queue."
    DEFVAL      { 0}
    ::= { hpnicfLswQosMibObject 1 }

  hpnicfPortMonitorBothIfIndex OBJECT-TYPE
    SYNTAX      INTEGER
    MAX-ACCESS  read-write
    STATUS      current
    DESCRIPTION
      "The ifIndex of in/out monitor port."
    DEFVAL      { 0}
    ::= { hpnicfLswQosMibObject 2 }


 --TABLE: hpnicfQueueTable

  hpnicfQueueTable OBJECT-TYPE
    SYNTAX      SEQUENCE OF HpnicfQueueEntry
    MAX-ACCESS  not-accessible
    STATUS      current
    DESCRIPTION
      "Queue table which contains queue entry."
    ::= { hpnicfLswQosMibObject 3 }

  hpnicfQueueEntry OBJECT-TYPE
    SYNTAX      HpnicfQueueEntry
    MAX-ACCESS  not-accessible
    STATUS      current
    DESCRIPTION
      "The configuration information of queue."
    INDEX {
              hpnicfQueueIfIndex
          }
    ::= { hpnicfQueueTable 1 }

  HpnicfQueueEntry ::=
    SEQUENCE
    {
      hpnicfQueueIfIndex    INTEGER,
      hpnicfQueueScheduleMode    INTEGER,
      hpnicfQueueWeight1    INTEGER,
      hpnicfQueueWeight2    INTEGER,
      hpnicfQueueWeight3    INTEGER,
      hpnicfQueueWeight4    INTEGER,
      hpnicfQueueMaxDelay    INTEGER,
      hpnicfQueueWeight5    INTEGER,
      hpnicfQueueWeight6    INTEGER,
      hpnicfQueueWeight7    INTEGER,
      hpnicfQueueWeight8    INTEGER
    }


  hpnicfQueueIfIndex OBJECT-TYPE
    SYNTAX      INTEGER
    MAX-ACCESS  read-only
    STATUS      current
    DESCRIPTION
      "ifIndex of port."
    ::= { hpnicfQueueEntry 1 }

  hpnicfQueueScheduleMode OBJECT-TYPE
    SYNTAX      INTEGER{
                        sp(1),
                        wrr(2),
                        wrr-max-delay(3),
                        sc-0(4),
                        sc-1(5),
                        sc-2(6),
                        rr(7),
                        wfq(8),
                        hq-wrr(9)
                       }
    MAX-ACCESS  read-write
    STATUS      current
    DESCRIPTION
      "The mode of the queue schedule."
    DEFVAL      { sp }
    ::= { hpnicfQueueEntry 2 }

  hpnicfQueueWeight1 OBJECT-TYPE
    SYNTAX      INTEGER
    MAX-ACCESS  read-write
    STATUS      current
    DESCRIPTION
      "If queue mode is wfq, then hpnicfQueueWeight1 represent the bandwidth of queue 1.
      If queue mode is wrr, then hpnicfQueueWeight1 represent the weight of queue 1."
    ::= { hpnicfQueueEntry 3 }

  hpnicfQueueWeight2 OBJECT-TYPE
    SYNTAX      INTEGER
    MAX-ACCESS  read-write
    STATUS      current
    DESCRIPTION
      "If queue mode is wfq, then hpnicfQueueWeight2 represent the bandwidth of queue 2.
      If queue mode is wrr, then hpnicfQueueWeight2 represent the weight of queue 2."
    ::= { hpnicfQueueEntry 4 }

  hpnicfQueueWeight3 OBJECT-TYPE
    SYNTAX      INTEGER
    MAX-ACCESS  read-write
    STATUS      current
    DESCRIPTION
      "If queue mode is wfq, then hpnicfQueueWeight3 represent the bandwidth of queue 3.
      If queue mode is wrr, then hpnicfQueueWeight3 represent the weight of queue 3."
    ::= { hpnicfQueueEntry 5 }

  hpnicfQueueWeight4 OBJECT-TYPE
    SYNTAX      INTEGER
    MAX-ACCESS  read-write
    STATUS      current
    DESCRIPTION
      "If queue mode is wfq, then hpnicfQueueWeight4 represent the bandwidth of queue 4.
      If queue mode is wrr, then hpnicfQueueWeight4 represent the weight of queue 4."
    ::= { hpnicfQueueEntry 6 }

  hpnicfQueueMaxDelay OBJECT-TYPE
    SYNTAX      INTEGER(0..255)
    MAX-ACCESS  read-write
    STATUS      current
    DESCRIPTION
      " "
    ::= { hpnicfQueueEntry 7 }

  hpnicfQueueWeight5 OBJECT-TYPE
    SYNTAX      INTEGER
    MAX-ACCESS  read-write
    STATUS      current
    DESCRIPTION
      "If queue mode is wfq, then hpnicfQueueWeight5 represent the bandwidth of queue 5.
      If queue mode is wrr, then hpnicfQueueWeight5 represent the weight of queue 5."
    ::= { hpnicfQueueEntry 8 }

  hpnicfQueueWeight6 OBJECT-TYPE
    SYNTAX      INTEGER
    MAX-ACCESS  read-write
    STATUS      current
    DESCRIPTION
      "If queue mode is wfq, then hpnicfQueueWeight6 represent the bandwidth of queue 6.
      If queue mode is wrr, then hpnicfQueueWeight6 represent the weight of queue 6."
    ::= { hpnicfQueueEntry 9 }

  hpnicfQueueWeight7 OBJECT-TYPE
    SYNTAX      INTEGER
    MAX-ACCESS  read-write
    STATUS      current
    DESCRIPTION
      "If queue mode is wfq, then hpnicfQueueWeight7 represent the bandwidth of queue 7.
      If queue mode is wrr, then hpnicfQueueWeight7 represent the weight of queue 7."
    ::= { hpnicfQueueEntry 10 }

  hpnicfQueueWeight8 OBJECT-TYPE
    SYNTAX      INTEGER
    MAX-ACCESS  read-write
    STATUS      current
    DESCRIPTION
      "If queue mode is wfq, then hpnicfQueueWeight8 represent the bandwidth of queue 8.
      If queue mode is wrr, then hpnicfQueueWeight8 represent the weight of queue 8."
    ::= { hpnicfQueueEntry 11 }


  -- TABLE: hpnicfRateLimitTable ------
  hpnicfRateLimitTable OBJECT-TYPE
    SYNTAX      SEQUENCE OF HpnicfRateLimitEntry
    MAX-ACCESS  not-accessible
    STATUS      current
    DESCRIPTION
      "Rate limit table which contains limit entry. "
    ::= { hpnicfLswQosMibObject 4 }

  hpnicfRateLimitEntry OBJECT-TYPE
    SYNTAX      HpnicfRateLimitEntry
    MAX-ACCESS  not-accessible
    STATUS      current
    DESCRIPTION
      "The configuration information of the rate-limited port."
    INDEX {
              hpnicfRateLimitAclIndex,
              hpnicfRateLimitIfIndex,
              hpnicfRateLimitVlanID,
              hpnicfRateLimitDirection
          }
    ::= { hpnicfRateLimitTable 1 }

  HpnicfRateLimitEntry ::=
    SEQUENCE
    {
      hpnicfRateLimitAclIndex    INTEGER,
      hpnicfRateLimitIfIndex    INTEGER,
      hpnicfRateLimitVlanID    INTEGER,
      hpnicfRateLimitDirection    INTEGER,
      hpnicfRateLimitUserAclNum    INTEGER,
      hpnicfRateLimitUserAclRule    INTEGER,
      hpnicfRateLimitIpAclNum    INTEGER,
      hpnicfRateLimitIpAclRule    INTEGER,
      hpnicfRateLimitLinkAclNum    INTEGER,
      hpnicfRateLimitLinkAclRule    INTEGER,
      hpnicfRateLimitTargetRateMbps    INTEGER,
      hpnicfRateLimitTargetRateKbps    INTEGER,
      hpnicfRateLimitPeakRate    INTEGER,
      hpnicfRateLimitCIR    INTEGER,
      hpnicfRateLimitCBS    INTEGER,
      hpnicfRateLimitEBS    INTEGER,
      hpnicfRateLimitPIR    INTEGER,
      hpnicfRateLimitConformLocalPre    INTEGER,
      hpnicfRateLimitConformActionType    INTEGER,
      hpnicfRateLimitExceedActionType    INTEGER,
      hpnicfRateLimitExceedDscp    INTEGER,
      hpnicfRateLimitRuntime    TruthValue,
      hpnicfRateLimitRowStatus    RowStatus,
      hpnicfRateLimitExceedCos INTEGER,
      hpnicfRateLimitConformCos INTEGER,
      hpnicfRateLimitConformDscp INTEGER,
      hpnicfRateLimitMeterStatByteCount Counter64,
      hpnicfRateLimitMeterStatByteXCount Counter64,
      hpnicfRateLimitMeterStatState INTEGER
    }

  hpnicfRateLimitAclIndex OBJECT-TYPE
    SYNTAX      INTEGER(0..2999)
    MAX-ACCESS  read-create
    STATUS      current
    DESCRIPTION
      "Index of acl rule."
    ::= { hpnicfRateLimitEntry 1 }

  hpnicfRateLimitIfIndex OBJECT-TYPE
    SYNTAX      INTEGER
    MAX-ACCESS  read-create
    STATUS      current
    DESCRIPTION
      "ifIndex of the rate-limited port."
    ::= { hpnicfRateLimitEntry 2 }

  hpnicfRateLimitVlanID OBJECT-TYPE
    SYNTAX      INTEGER(0..4094)
    MAX-ACCESS  read-create
    STATUS      current
    DESCRIPTION
      "Vlan ID."
    ::= { hpnicfRateLimitEntry 3 }

  hpnicfRateLimitDirection OBJECT-TYPE
    SYNTAX      INTEGER{invalid(0), input(1), output(2)}
    MAX-ACCESS  read-create
    STATUS      current
    DESCRIPTION
      "Direction of the rate-limited port."
    ::= { hpnicfRateLimitEntry 4 }

  hpnicfRateLimitUserAclNum OBJECT-TYPE
    SYNTAX      INTEGER(0|5000..5999|10000..12999)
    MAX-ACCESS  read-create
    STATUS      current
    DESCRIPTION
      "The number of user acl."
    ::= { hpnicfRateLimitEntry 5 }

  hpnicfRateLimitUserAclRule OBJECT-TYPE
    SYNTAX      INTEGER(0..65535)
    MAX-ACCESS  read-create
    STATUS      current
    DESCRIPTION
      "The number of user acl-rule."
    ::= { hpnicfRateLimitEntry 6 }

  hpnicfRateLimitIpAclNum OBJECT-TYPE
    SYNTAX      INTEGER(0|2000..3999|10000..12999)
    MAX-ACCESS  read-create
    STATUS      current
    DESCRIPTION
      "The number of Ip acl."
    ::= { hpnicfRateLimitEntry 7 }

  hpnicfRateLimitIpAclRule OBJECT-TYPE
    SYNTAX      INTEGER(0..65535)
    MAX-ACCESS  read-create
    STATUS      current
    DESCRIPTION
      "The number of Ip acl-rule."
    ::= { hpnicfRateLimitEntry 8 }

  hpnicfRateLimitLinkAclNum OBJECT-TYPE
    SYNTAX      INTEGER(0|4000..4999|10000..12999)
    MAX-ACCESS  read-create
    STATUS      current
    DESCRIPTION
      "The number of link acl."
    ::= { hpnicfRateLimitEntry 9 }

  hpnicfRateLimitLinkAclRule OBJECT-TYPE
    SYNTAX      INTEGER(0..65535)
    MAX-ACCESS  read-create
    STATUS      current
    DESCRIPTION
      "The number of link acl-rule."
    ::= { hpnicfRateLimitEntry 10 }

  hpnicfRateLimitTargetRateMbps OBJECT-TYPE
    SYNTAX      INTEGER
    MAX-ACCESS  read-create
    STATUS      current
    DESCRIPTION
      "Target rate: Mbps."
    ::= { hpnicfRateLimitEntry 11 }

  hpnicfRateLimitTargetRateKbps OBJECT-TYPE
    SYNTAX      INTEGER
    MAX-ACCESS  read-create
    STATUS      current
    DESCRIPTION
      "Target rate: Kbps."
    ::= { hpnicfRateLimitEntry 12 }

  hpnicfRateLimitPeakRate OBJECT-TYPE
    SYNTAX      INTEGER(0|64..8388608)
    MAX-ACCESS  read-create
    STATUS      current
    DESCRIPTION
      "Peak rate of the rate-limited port."
    ::= { hpnicfRateLimitEntry 13 }

  hpnicfRateLimitCIR OBJECT-TYPE
    SYNTAX      INTEGER(0..34120000)
    MAX-ACCESS  read-create
    STATUS      current
    DESCRIPTION
      "CIR of the rate-limited port."
    ::= { hpnicfRateLimitEntry 14 }

  hpnicfRateLimitCBS OBJECT-TYPE
    SYNTAX      INTEGER(0..1048575)
    MAX-ACCESS  read-create
    STATUS      current
    DESCRIPTION
      "Burst traffic of the rate-limited port."
    ::= { hpnicfRateLimitEntry 15 }

  hpnicfRateLimitEBS OBJECT-TYPE
    SYNTAX      INTEGER(0..268435455)
    MAX-ACCESS  read-create
    STATUS      current
    DESCRIPTION
      "Excess burst traffic of the rate-limited port."
    ::= { hpnicfRateLimitEntry 16 }

  hpnicfRateLimitPIR OBJECT-TYPE
    SYNTAX      INTEGER(0..34120000)
    MAX-ACCESS  read-create
    STATUS      current
    DESCRIPTION
      "PIR of the rate-limited port."
    ::= { hpnicfRateLimitEntry 17 }

  hpnicfRateLimitConformLocalPre OBJECT-TYPE
    SYNTAX      INTEGER
    MAX-ACCESS  read-create
    STATUS      current
    DESCRIPTION
      "Conform local pre."
    DEFVAL      { 1 }
    ::= { hpnicfRateLimitEntry 18 }

  hpnicfRateLimitConformActionType OBJECT-TYPE
    SYNTAX      INTEGER{
                       invalid(0),
                       remark-cos(1),
                       remark-drop-priority(2),
                       remark-cos-drop-priority(3),
                       remark-policed-service(4),
                       remark-dscp(5)
                       }
    MAX-ACCESS  read-create
    STATUS      current
    DESCRIPTION
      "Conform action type."
    DEFVAL      { 1 }
    ::= { hpnicfRateLimitEntry 19 }

  hpnicfRateLimitExceedActionType OBJECT-TYPE
    SYNTAX      INTEGER{invalid(0), forward(1), drop(2), remarkdscp(3), exceed-cos(4)}
    MAX-ACCESS  read-create
    STATUS      current
    DESCRIPTION
      "Exceed action type."
    DEFVAL      { 1 }
    ::= { hpnicfRateLimitEntry 20 }

  hpnicfRateLimitExceedDscp OBJECT-TYPE
    SYNTAX      INTEGER(0..63|255)
    MAX-ACCESS  read-create
    STATUS      current
    DESCRIPTION
      "Exceed DSCP.
      <0-63>  Value of DSCP
      af11    Specify Assured Forwarding 11 service(10)
      af12    Specify Assured Forwarding 12 service(12)
      af13    Specify Assured Forwarding 13 service(14)
      af21    Specify Assured Forwarding 21 service(18)
      af22    Specify Assured Forwarding 22 service(20)
      af23    Specify Assured Forwarding 23 service(22)
      af31    Specify Assured Forwarding 31 service(26)
      af32    Specify Assured Forwarding 32 service(28)
      af33    Specify Assured Forwarding 33 service(30)
      af41    Specify Assured Forwarding 41 service(34)
      af42    Specify Assured Forwarding 42 service(36)
      af43    Specify Assured Forwarding 43 service(38)
      be      Specify Best Effort service(0)
      cs1     Specify Class Selector 1 service(8)
      cs2     Specify Class Selector 2 service(16)
      cs3     Specify Class Selector 3 service(24)
      cs4     Specify Class Selector 4 service(32)
      cs5     Specify Class Selector 5 service(40)
      cs6     Specify Class Selector 6 service(48)
      cs7     Specify Class Selector 7 service(56)
      ef      Specify Expedited Forwarding service(46)"
    DEFVAL      { 255 }
    ::= { hpnicfRateLimitEntry 21 }

  hpnicfRateLimitRuntime OBJECT-TYPE
    SYNTAX      TruthValue
    MAX-ACCESS  read-only
    STATUS      current
    DESCRIPTION
      "Runtime."
    ::= { hpnicfRateLimitEntry 22 }

  hpnicfRateLimitRowStatus OBJECT-TYPE
    SYNTAX      RowStatus
    MAX-ACCESS  read-create
    STATUS      current
    DESCRIPTION
      "RowStatus, now support three status: createAndGo, active, destroy."
    ::= { hpnicfRateLimitEntry 23 }

  hpnicfRateLimitExceedCos OBJECT-TYPE
    SYNTAX      INTEGER
    MAX-ACCESS  read-create
    STATUS      current
    DESCRIPTION
      "Exceeding COS of rate-limited port."
    DEFVAL      { 255 }
    ::= { hpnicfRateLimitEntry 24 }

  hpnicfRateLimitConformCos OBJECT-TYPE
    SYNTAX      INTEGER(0..7|255)
    MAX-ACCESS  read-create
    STATUS      current
    DESCRIPTION
      "If the user choose remark-cos value of the hpnicfRateLimitConformActionType,
      This object can be used to set the conform COS value.  There are a few
      enumerations as follows:
      background          Specify background priority(1)
      best-effort         Specify best-effort priority(0)
      controlled-load     Specify controlled-load priority(4)
      excellent-effort    Specify excellent-effort priority(3)
      network-management  Specify network-management priority(7)
      spare               Specify spare priority(2)
      video               Specify video priority(5)
      voice               Specify voice priority(6)"
    DEFVAL      { 255 }
    ::= { hpnicfRateLimitEntry 25 }

  hpnicfRateLimitConformDscp OBJECT-TYPE
    SYNTAX      INTEGER(0..63|255)
    MAX-ACCESS  read-create
    STATUS      current
    DESCRIPTION
      "If the user choose remark-dscp value of the hpnicfRateLimitConformActionType,
      This object can be used to set the conform dscp value.  There are a few
      enumerations as follows:
      <0-63>  Value of DSCP
      af11    Specify Assured Forwarding 11 service(10)
      af12    Specify Assured Forwarding 12 service(12)
      af13    Specify Assured Forwarding 13 service(14)
      af21    Specify Assured Forwarding 21 service(18)
      af22    Specify Assured Forwarding 22 service(20)
      af23    Specify Assured Forwarding 23 service(22)
      af31    Specify Assured Forwarding 31 service(26)
      af32    Specify Assured Forwarding 32 service(28)
      af33    Specify Assured Forwarding 33 service(30)
      af41    Specify Assured Forwarding 41 service(34)
      af42    Specify Assured Forwarding 42 service(36)
      af43    Specify Assured Forwarding 43 service(38)
      be      Specify Best Effort service(0)
      cs1     Specify Class Selector 1 service(8)
      cs2     Specify Class Selector 2 service(16)
      cs3     Specify Class Selector 3 service(24)
      cs4     Specify Class Selector 4 service(32)
      cs5     Specify Class Selector 5 service(40)
      cs6     Specify Class Selector 6 service(48)
      cs7     Specify Class Selector 7 service(56)
      ef      Specify Expedited Forwarding service(46)"
    DEFVAL      { 255 }
    ::= { hpnicfRateLimitEntry 26 }

  hpnicfRateLimitMeterStatByteCount  OBJECT-TYPE
    SYNTAX      Counter64
    MAX-ACCESS  read-only
    STATUS      current
    DESCRIPTION
               "The counter of conform byte."
    ::= { hpnicfRateLimitEntry 27 }

  hpnicfRateLimitMeterStatByteXCount  OBJECT-TYPE
    SYNTAX      Counter64
    MAX-ACCESS  read-only
    STATUS      current
    DESCRIPTION
               "The counter of exceed byte."
    ::= { hpnicfRateLimitEntry 28 }

  hpnicfRateLimitMeterStatState  OBJECT-TYPE
    SYNTAX      INTEGER
                       {
                       set(1), --enable meter statistic
                       unDo(2), --undo meter statistic
                       reset(3), --reset meter statistic
                       running(4), --status of meter statistic running
                       notRunning(5) --status of meter statistic not running
                       }
    MAX-ACCESS  read-create
    STATUS      current
    DESCRIPTION
               "The status of meter statistic."
    ::= { hpnicfRateLimitEntry 29 }

  -- TABLE: hpnicfPriorityTable ------
  hpnicfPriorityTable OBJECT-TYPE
    SYNTAX      SEQUENCE OF HpnicfPriorityEntry
    MAX-ACCESS  not-accessible
    STATUS      current
    DESCRIPTION
      "The priority table which contains priority entry."
    ::= { hpnicfLswQosMibObject 5 }

  hpnicfPriorityEntry OBJECT-TYPE
    SYNTAX      HpnicfPriorityEntry
    MAX-ACCESS  not-accessible
    STATUS      current
    DESCRIPTION
      "The configuration information of priority."
    INDEX {
              hpnicfPriorityAclIndex,
              hpnicfPriorityIfIndex,
              hpnicfPriorityVlanID,
              hpnicfPriorityDirection
          }
    ::= { hpnicfPriorityTable 1 }

  HpnicfPriorityEntry ::=
    SEQUENCE
    {
      hpnicfPriorityAclIndex    INTEGER,
      hpnicfPriorityIfIndex    INTEGER,
      hpnicfPriorityVlanID    INTEGER,
      hpnicfPriorityDirection    INTEGER,
      hpnicfPriorityUserAclNum    INTEGER,
      hpnicfPriorityUserAclRule    INTEGER,
      hpnicfPriorityIpAclNum    INTEGER,
      hpnicfPriorityIpAclRule    INTEGER,
      hpnicfPriorityLinkAclNum    INTEGER,
      hpnicfPriorityLinkAclRule    INTEGER,
      hpnicfPriorityDscp    INTEGER,
      hpnicfPriorityIpPre    INTEGER,
      hpnicfPriorityIpPreFromCos    TruthValue,
      hpnicfPriorityCos    INTEGER,
      hpnicfPriorityCosFromIpPre    TruthValue,
      hpnicfPriorityLocalPre    INTEGER,
      hpnicfPriorityPolicedServiceType    INTEGER,
      hpnicfPriorityPolicedServiceDscp    INTEGER,
      hpnicfPriorityPolicedServiceExp    INTEGER,
      hpnicfPriorityPolicedServiceCos    INTEGER,
      hpnicfPriorityPolicedServiceLoaclPre    INTEGER,
      hpnicfPriorityPolicedServiceDropPriority    INTEGER,
      hpnicfPriorityRuntime    TruthValue,
      hpnicfPriorityRowStatus    RowStatus
    }

  hpnicfPriorityAclIndex OBJECT-TYPE
    SYNTAX      INTEGER(0..2999)
    MAX-ACCESS  read-create
    STATUS      current
    DESCRIPTION
      "Index of acl rule."
    ::= { hpnicfPriorityEntry 1 }

  hpnicfPriorityIfIndex OBJECT-TYPE
    SYNTAX      INTEGER
    MAX-ACCESS  read-create
    STATUS      current
    DESCRIPTION
      "ifIndex of the port."
    ::= { hpnicfPriorityEntry 2 }

  hpnicfPriorityVlanID OBJECT-TYPE
    SYNTAX      INTEGER(0..4094)
    MAX-ACCESS  read-create
    STATUS      current
    DESCRIPTION
      "Vlan ID."
    ::= { hpnicfPriorityEntry 3 }

  hpnicfPriorityDirection OBJECT-TYPE
    SYNTAX      INTEGER{invalid(0), input(1), output(2)}
    MAX-ACCESS  read-create
    STATUS      current
    DESCRIPTION
      "Direction of data stream."
    ::= { hpnicfPriorityEntry 4 }

  hpnicfPriorityUserAclNum OBJECT-TYPE
    SYNTAX      INTEGER(0|5000..5999|10000..12999)
    MAX-ACCESS  read-create
    STATUS      current
    DESCRIPTION
      "The number of user acl."
    ::= { hpnicfPriorityEntry 5 }

  hpnicfPriorityUserAclRule OBJECT-TYPE
    SYNTAX      INTEGER(0..65535)
    MAX-ACCESS  read-create
    STATUS      current
    DESCRIPTION
      "The subitem of the user acl."
    ::= { hpnicfPriorityEntry 6 }

  hpnicfPriorityIpAclNum OBJECT-TYPE
    SYNTAX      INTEGER(0|2000..3999|10000..12999)
    MAX-ACCESS  read-create
    STATUS      current
    DESCRIPTION
      "The number of Ip acl."
    ::= { hpnicfPriorityEntry 7 }

  hpnicfPriorityIpAclRule OBJECT-TYPE
    SYNTAX      INTEGER(0..65535)
    MAX-ACCESS  read-create
    STATUS      current
    DESCRIPTION
      "The subitem of the IP acl."
    ::= { hpnicfPriorityEntry 8 }

  hpnicfPriorityLinkAclNum OBJECT-TYPE
    SYNTAX      INTEGER(0|4000..4999|10000..12999)
    MAX-ACCESS  read-create
    STATUS      current
    DESCRIPTION
      "The number of Link acl."
    ::= { hpnicfPriorityEntry 9 }

  hpnicfPriorityLinkAclRule OBJECT-TYPE
    SYNTAX      INTEGER(0..65535)
    MAX-ACCESS  read-create
    STATUS      current
    DESCRIPTION
      "The subitem of the link acl."
    ::= { hpnicfPriorityEntry 10 }

  hpnicfPriorityDscp OBJECT-TYPE
    SYNTAX      INTEGER(0..63|255)
    MAX-ACCESS  read-create
    STATUS      current
    DESCRIPTION
      "Set DSCP Value.
      <0-63>  Value of DSCP
      af11    Specify Assured Forwarding 11 service(10)
      af12    Specify Assured Forwarding 12 service(12)
      af13    Specify Assured Forwarding 13 service(14)
      af21    Specify Assured Forwarding 21 service(18)
      af22    Specify Assured Forwarding 22 service(20)
      af23    Specify Assured Forwarding 23 service(22)
      af31    Specify Assured Forwarding 31 service(26)
      af32    Specify Assured Forwarding 32 service(28)
      af33    Specify Assured Forwarding 33 service(30)
      af41    Specify Assured Forwarding 41 service(34)
      af42    Specify Assured Forwarding 42 service(36)
      af43    Specify Assured Forwarding 43 service(38)
      be      Specify Best Effort service(0)
      cs1     Specify Class Selector 1 service(8)
      cs2     Specify Class Selector 2 service(16)
      cs3     Specify Class Selector 3 service(24)
      cs4     Specify Class Selector 4 service(32)
      cs5     Specify Class Selector 5 service(40)
      cs6     Specify Class Selector 6 service(48)
      cs7     Specify Class Selector 7 service(56)
      ef      Specify Expedited Forwarding service(46)"
    DEFVAL      { 255 }
    ::= { hpnicfPriorityEntry 11 }

  hpnicfPriorityIpPre OBJECT-TYPE
    SYNTAX      INTEGER(0..7|255)
    MAX-ACCESS  read-create
    STATUS      current
    DESCRIPTION
      "Set Ip precedence."
    DEFVAL      { 255 }
    ::= { hpnicfPriorityEntry 12 }

  hpnicfPriorityIpPreFromCos OBJECT-TYPE
    SYNTAX      TruthValue
    MAX-ACCESS  read-create
    STATUS      current
    DESCRIPTION
      "Set Ip precedence according to vlan priority."
    DEFVAL      { 2 }
    ::= { hpnicfPriorityEntry 13 }

  hpnicfPriorityCos OBJECT-TYPE
    SYNTAX      INTEGER(0..7|255)
    MAX-ACCESS  read-create
    STATUS      current
    DESCRIPTION
      "Set vlan priority."
    DEFVAL      { 255 }
    ::= { hpnicfPriorityEntry 14 }

  hpnicfPriorityCosFromIpPre OBJECT-TYPE
    SYNTAX      TruthValue
    MAX-ACCESS  read-create
    STATUS      current
    DESCRIPTION
      "Set vlan priority according to IP precedence."
    DEFVAL      { 2 }
    ::= { hpnicfPriorityEntry 15 }

  hpnicfPriorityLocalPre OBJECT-TYPE
    SYNTAX      INTEGER(0..7|255)
    MAX-ACCESS  read-create
    STATUS      current
    DESCRIPTION
      "Set local precedence."
    DEFVAL      { 255 }
    ::= { hpnicfPriorityEntry 16 }

  hpnicfPriorityPolicedServiceType OBJECT-TYPE
    SYNTAX      INTEGER{invalid(0), auto(1), trust-dscp(2), new-dscp(3), untrusted(4)}
    MAX-ACCESS  read-create
    STATUS      current
    DESCRIPTION
      "The service type of proliced Priority."
    ::= { hpnicfPriorityEntry 17 }

  hpnicfPriorityPolicedServiceDscp OBJECT-TYPE
    SYNTAX      INTEGER(0..63|255)
    MAX-ACCESS  read-create
    STATUS      current
    DESCRIPTION
      "The service Dscp of proliced Priority."
    DEFVAL      { 255 }
    ::= { hpnicfPriorityEntry 18 }

  hpnicfPriorityPolicedServiceExp OBJECT-TYPE
    SYNTAX      INTEGER(0..7|255)
    MAX-ACCESS  read-create
    STATUS      current
    DESCRIPTION
      "The service Exp of proliced Priority."
    DEFVAL      { 255 }
    ::= { hpnicfPriorityEntry 19 }

  hpnicfPriorityPolicedServiceCos OBJECT-TYPE
    SYNTAX      INTEGER(0..7|255)
    MAX-ACCESS  read-create
    STATUS      current
    DESCRIPTION
      "The service COS of proliced Priority."
    DEFVAL      { 255 }
    ::= { hpnicfPriorityEntry 20 }

  hpnicfPriorityPolicedServiceLoaclPre OBJECT-TYPE
    SYNTAX      INTEGER(0..7|255)
    MAX-ACCESS  read-create
    STATUS      current
    DESCRIPTION
      "The service local pre of proliced Priority."
    DEFVAL      { 255 }
    ::= { hpnicfPriorityEntry 21 }

  hpnicfPriorityPolicedServiceDropPriority OBJECT-TYPE
    SYNTAX      INTEGER(0..2|255)
    MAX-ACCESS  read-create
    STATUS      current
    DESCRIPTION
      "The service drop priority of proliced Priority."
    DEFVAL      { 255 }
    ::= { hpnicfPriorityEntry 22 }

  hpnicfPriorityRuntime OBJECT-TYPE
    SYNTAX      TruthValue
    MAX-ACCESS  read-only
    STATUS      current
    DESCRIPTION
      "Is run or not."
    ::= { hpnicfPriorityEntry 23 }

  hpnicfPriorityRowStatus OBJECT-TYPE
    SYNTAX      RowStatus
    MAX-ACCESS  read-create
    STATUS      current
    DESCRIPTION
      "RowStatus, now support three status: createAndGo, active, destroy."
    ::= { hpnicfPriorityEntry 24 }

  -- TABLE: hpnicfRedirectTable ------
  hpnicfRedirectTable OBJECT-TYPE
    SYNTAX      SEQUENCE OF HpnicfRedirectEntry
    MAX-ACCESS  not-accessible
    STATUS      current
    DESCRIPTION
      "Redirect table which contains rediect entry."
    ::= { hpnicfLswQosMibObject 6 }

  hpnicfRedirectEntry OBJECT-TYPE
    SYNTAX      HpnicfRedirectEntry
    MAX-ACCESS  not-accessible
    STATUS      current
    DESCRIPTION
      "Configuration information of redirection."
    INDEX {
              hpnicfRedirectAclIndex,
              hpnicfRedirectIfIndex,
              hpnicfRedirectVlanID,
              hpnicfRedirectDirection
          }
    ::= { hpnicfRedirectTable 1 }

  HpnicfRedirectEntry ::=
    SEQUENCE
    {
      hpnicfRedirectAclIndex    INTEGER,
      hpnicfRedirectIfIndex    INTEGER,
      hpnicfRedirectVlanID    INTEGER,
      hpnicfRedirectDirection    INTEGER,
      hpnicfRedirectUserAclNum    INTEGER,
      hpnicfRedirectUserAclRule    INTEGER,
      hpnicfRedirectIpAclNum    INTEGER,
      hpnicfRedirectIpAclRule    INTEGER,
      hpnicfRedirectLinkAclNum    INTEGER,
      hpnicfRedirectLinkAclRule    INTEGER,
      hpnicfRedirectToCpu    TruthValue,
      hpnicfRedirectToIfIndex    INTEGER,
      hpnicfRedirectToNextHop1    IpAddress,
      hpnicfRedirectToNextHop2    IpAddress,
      hpnicfRedirectRuntime    TruthValue,
      hpnicfRedirectRowStatus    RowStatus,
      hpnicfRedirectToSlotNo INTEGER,
      hpnicfRedirectRemarkedDSCP    INTEGER,
      hpnicfRedirectRemarkedPri  INTEGER,
      hpnicfRedirectRemarkedTos  INTEGER,
      hpnicfRedirectToNextHop3  IpAddress,
      hpnicfRedirectTargetVlanID INTEGER,
      hpnicfRedirectMode INTEGER,
      hpnicfRedirectToNestedVlanID Integer32,
      hpnicfRedirectToModifiedVlanID Integer32
    }

  hpnicfRedirectAclIndex OBJECT-TYPE
    SYNTAX      INTEGER(0..2999)
    MAX-ACCESS  read-create
    STATUS      current
    DESCRIPTION
      "Index of acl rule."
    ::= { hpnicfRedirectEntry 1 }

  hpnicfRedirectIfIndex OBJECT-TYPE
    SYNTAX      INTEGER
    MAX-ACCESS  read-create
    STATUS      current
    DESCRIPTION
      "ifIndex of port."
    ::= { hpnicfRedirectEntry 2 }

  hpnicfRedirectVlanID OBJECT-TYPE
    SYNTAX      INTEGER(0..4094)
    MAX-ACCESS  read-create
    STATUS      current
    DESCRIPTION
      "Vlan ID."
    ::= { hpnicfRedirectEntry 3 }

  hpnicfRedirectDirection OBJECT-TYPE
    SYNTAX      INTEGER{invalid(0), input(1), output(2)}
    MAX-ACCESS  read-create
    STATUS      current
    DESCRIPTION
      "Direction of data stream."
    ::= { hpnicfRedirectEntry 4 }

  hpnicfRedirectUserAclNum OBJECT-TYPE
    SYNTAX      INTEGER(0|5000..5999|10000..12999)
    MAX-ACCESS  read-create
    STATUS      current
    DESCRIPTION
      "The number of the user acl."
    ::= { hpnicfRedirectEntry 5 }

  hpnicfRedirectUserAclRule OBJECT-TYPE
    SYNTAX      INTEGER(0..65535)
    MAX-ACCESS  read-create
    STATUS      current
    DESCRIPTION
      "The subitem of the user acl."
    ::= { hpnicfRedirectEntry 6 }

  hpnicfRedirectIpAclNum OBJECT-TYPE
    SYNTAX      INTEGER(0|2000..3999|10000..12999)
    MAX-ACCESS  read-create
    STATUS      current
    DESCRIPTION
      "The num of the IP acl."
    ::= { hpnicfRedirectEntry 7 }

  hpnicfRedirectIpAclRule OBJECT-TYPE
    SYNTAX      INTEGER(0..65535)
    MAX-ACCESS  read-create
    STATUS      current
    DESCRIPTION
      "The subitem of the IP acl."
    ::= { hpnicfRedirectEntry 8 }

  hpnicfRedirectLinkAclNum OBJECT-TYPE
    SYNTAX      INTEGER(0|4000..4999|10000..12999)
    MAX-ACCESS  read-create
    STATUS      current
    DESCRIPTION
      "The num of the link acl."
    ::= { hpnicfRedirectEntry 9 }

  hpnicfRedirectLinkAclRule OBJECT-TYPE
    SYNTAX      INTEGER(0..65535)
    MAX-ACCESS  read-create
    STATUS      current
    DESCRIPTION
      "The subitem of the link acl."
    ::= { hpnicfRedirectEntry 10 }

  hpnicfRedirectToCpu OBJECT-TYPE
    SYNTAX      TruthValue
    MAX-ACCESS  read-create
    STATUS      current
    DESCRIPTION
      "Redirect to cpu."
    DEFVAL      { 2 }
    ::= { hpnicfRedirectEntry 11 }

  hpnicfRedirectToIfIndex OBJECT-TYPE
    SYNTAX      INTEGER
    MAX-ACCESS  read-create
    STATUS      current
    DESCRIPTION
      "The ifIndex of port to be redirect to."
    ::= { hpnicfRedirectEntry 12 }

  hpnicfRedirectToNextHop1 OBJECT-TYPE
    SYNTAX      IpAddress
    MAX-ACCESS  read-create
    STATUS      current
    DESCRIPTION
          " "
    ::= { hpnicfRedirectEntry 13 }

  hpnicfRedirectToNextHop2 OBJECT-TYPE
    SYNTAX      IpAddress
    MAX-ACCESS  read-create
    STATUS      current
    DESCRIPTION
          " "
    ::= { hpnicfRedirectEntry 14 }

  hpnicfRedirectRuntime OBJECT-TYPE
    SYNTAX      TruthValue
    MAX-ACCESS  read-only
    STATUS      current
    DESCRIPTION
      "Is run or not."
    ::= { hpnicfRedirectEntry 15 }

  hpnicfRedirectRowStatus OBJECT-TYPE
    SYNTAX      RowStatus
    MAX-ACCESS  read-create
    STATUS      current
    DESCRIPTION
          "RowStatus, now support three status: createAndGo, active, destroy."
    ::= { hpnicfRedirectEntry 16 }

  hpnicfRedirectToSlotNo OBJECT-TYPE
    SYNTAX      INTEGER(1..16)
    MAX-ACCESS  read-create
    STATUS      current
    DESCRIPTION
      "The slot number to process redirection. Default value is 15.
      When L3plus function is not supported, the default value would be set.
      For L3plus redirection function, it is necessary."
    ::= { hpnicfRedirectEntry 17 }

  hpnicfRedirectRemarkedDSCP OBJECT-TYPE
    SYNTAX      INTEGER(0..63|255)
    MAX-ACCESS  read-create
    STATUS      current
    DESCRIPTION
      "DSCP of Policy-Based Routing. When L3plus function is not supported,
      the default value would be set.
      For L3plus redirection function, it is optional."
    DEFVAL      { 255 }
    ::= { hpnicfRedirectEntry 18 }

  hpnicfRedirectRemarkedPri OBJECT-TYPE
    SYNTAX      INTEGER(0..7|255)
    MAX-ACCESS  read-create
    STATUS      current
    DESCRIPTION
      "The priority of the redirect packet. When L3plus function is not supported,
      the default value would be set.
      For L3plus redirection function, it is optional."
    DEFVAL      { 255 }
    ::= { hpnicfRedirectEntry 19 }

  hpnicfRedirectRemarkedTos OBJECT-TYPE
    SYNTAX      INTEGER(0..15|255)
    MAX-ACCESS  read-create
    STATUS      current
    DESCRIPTION
      "The TOS of the redirect packet.
      When L3plus function is not supported, the default value would be set.
      For L3plus redirection function, it is optional."
    DEFVAL      { 255 }
    ::= { hpnicfRedirectEntry 20 }

  hpnicfRedirectToNextHop3 OBJECT-TYPE
    SYNTAX      IpAddress
    MAX-ACCESS  read-create
    STATUS      current
    DESCRIPTION
      "The third IP address for PBR. Default value is 0xffffffff.
      When L3plus function is not supported, the default value would be set.
      The data stream can be redirected to three nexthops at most or one
      VLAN interface, one nexthop should be set at least if data packets
      are not redirected to VLAN interface for L3plus redirection function."
    ::= { hpnicfRedirectEntry 21 }

  hpnicfRedirectTargetVlanID OBJECT-TYPE
    SYNTAX      INTEGER(0..4094)
    MAX-ACCESS  read-create
    STATUS      current
    DESCRIPTION
      "The destination vlan ID for PBR. Default value is 0.
      When L3plus function is not supported, the default value would be set.
      For L3plus redirection function, it is necessary when no nexthop is set. "
    ::= { hpnicfRedirectEntry 22 }

  hpnicfRedirectMode OBJECT-TYPE
    SYNTAX      INTEGER{
                                strict-priority(1),
                                load-balance(2)
                       }
    MAX-ACCESS  read-create
    STATUS      current
    DESCRIPTION
      "The node denotes the strategy adopted by the PBR.
      If strict-priority is configured, the most preferential IP address
      is use as redirected nexthop.
      If the mode is load-balance, any of the three IP addresses will be
      the nexthop and the traffic distributes in the three direction.
      Default value is strict-priority.
      When L3plus function is not supported, the default value would be set.
      It is optional. "
    DEFVAL      { strict-priority }
    ::= { hpnicfRedirectEntry 23 }

  hpnicfRedirectToNestedVlanID OBJECT-TYPE
    SYNTAX      Integer32
    MAX-ACCESS  read-create
    STATUS      current
    DESCRIPTION
      "The nested vlan ID inserted before the original vlan tag. Default value is 0.
      When the function is not supported, the default value would be set.
      It is optional."
    DEFVAL      { 0 }
    ::= { hpnicfRedirectEntry 24 }

  hpnicfRedirectToModifiedVlanID OBJECT-TYPE
    SYNTAX      Integer32
    MAX-ACCESS  read-create
    STATUS      current
    DESCRIPTION
      "The new vlan ID replaced the old one. Default value is 0.
      When the function is not supported, the default value would be set.
      It is optional."
    DEFVAL      { 0 }
    ::= { hpnicfRedirectEntry 25 }

  -- TABLE: hpnicfStatisticTable ------
  hpnicfStatisticTable OBJECT-TYPE
    SYNTAX      SEQUENCE OF HpnicfStatisticEntry
    MAX-ACCESS  not-accessible
    STATUS      current
    DESCRIPTION
      "Statistic table which contains statistic entry."
    ::= { hpnicfLswQosMibObject 7 }

  hpnicfStatisticEntry OBJECT-TYPE
    SYNTAX      HpnicfStatisticEntry
    MAX-ACCESS  not-accessible
    STATUS      current
    DESCRIPTION
      "Configuration about statistic information."
    INDEX {
              hpnicfStatisticAclIndex,
              hpnicfStatisticIfIndex,
              hpnicfStatisticVlanID,
              hpnicfStatisticDirection
          }
    ::= { hpnicfStatisticTable 1 }

  HpnicfStatisticEntry ::=
    SEQUENCE
    {
      hpnicfStatisticAclIndex    INTEGER,
      hpnicfStatisticIfIndex    INTEGER,
      hpnicfStatisticVlanID    INTEGER,
      hpnicfStatisticDirection    INTEGER,
      hpnicfStatisticUserAclNum    INTEGER,
      hpnicfStatisticUserAclRule    INTEGER,
      hpnicfStatisticIpAclNum    INTEGER,
      hpnicfStatisticIpAclRule    INTEGER,
      hpnicfStatisticLinkAclNum    INTEGER,
      hpnicfStatisticLinkAclRule    INTEGER,
      hpnicfStatisticRuntime    TruthValue,
      hpnicfStatisticPacketCount    Counter64,
      hpnicfStatisticByteCount    Counter64,
      hpnicfStatisticCountClear    INTEGER,
      hpnicfStatisticRowStatus    RowStatus,
      hpnicfStatisticPacketXCount Counter64,
      hpnicfStatisticByteXCount Counter64
    }

  hpnicfStatisticAclIndex OBJECT-TYPE
    SYNTAX      INTEGER(0..2999)
    MAX-ACCESS  read-create
    STATUS      current
    DESCRIPTION
      "Index of acl rule."
    ::= { hpnicfStatisticEntry 1 }

  hpnicfStatisticIfIndex OBJECT-TYPE
    SYNTAX      INTEGER
    MAX-ACCESS  read-create
    STATUS      current
    DESCRIPTION
      "ifIndex of port."
    ::= { hpnicfStatisticEntry 2 }

  hpnicfStatisticVlanID OBJECT-TYPE
    SYNTAX      INTEGER(0..4094)
    MAX-ACCESS  read-create
    STATUS      current
    DESCRIPTION
      "Vlan ID."
    ::= { hpnicfStatisticEntry 3 }

  hpnicfStatisticDirection OBJECT-TYPE
    SYNTAX      INTEGER{invalid(0), input(1), output(2)}
    MAX-ACCESS  read-create
    STATUS      current
    DESCRIPTION
      "Direction of data stream."
    ::= { hpnicfStatisticEntry 4 }

  hpnicfStatisticUserAclNum OBJECT-TYPE
    SYNTAX      INTEGER(0|5000..5999|10000..12999)
    MAX-ACCESS  read-create
    STATUS      current
    DESCRIPTION
      "The number of the user acl."
    ::= { hpnicfStatisticEntry 5 }

  hpnicfStatisticUserAclRule OBJECT-TYPE
    SYNTAX      INTEGER(0..65535)
    MAX-ACCESS  read-create
    STATUS      current
    DESCRIPTION
      "The subitem of the user acl."
    ::= { hpnicfStatisticEntry 6 }

  hpnicfStatisticIpAclNum OBJECT-TYPE
    SYNTAX      INTEGER(0|2000..3999|10000..12999)
    MAX-ACCESS  read-create
    STATUS      current
    DESCRIPTION
      "The number of the IP acl."
    ::= { hpnicfStatisticEntry 7 }

  hpnicfStatisticIpAclRule OBJECT-TYPE
    SYNTAX      INTEGER(0..65535)
    MAX-ACCESS  read-create
    STATUS      current
    DESCRIPTION
      "The subitem of the IP acl."
    ::= { hpnicfStatisticEntry 8 }

  hpnicfStatisticLinkAclNum OBJECT-TYPE
    SYNTAX      INTEGER(0|4000..4999|10000..12999)
    MAX-ACCESS  read-create
    STATUS      current
    DESCRIPTION
      "The number of the link acl."
    ::= { hpnicfStatisticEntry 9 }

  hpnicfStatisticLinkAclRule OBJECT-TYPE
    SYNTAX      INTEGER(0..65535)
    MAX-ACCESS  read-create
    STATUS      current
    DESCRIPTION
      "The subitem of the link acl."
    ::= { hpnicfStatisticEntry 10 }

  hpnicfStatisticRuntime OBJECT-TYPE
    SYNTAX      TruthValue
    MAX-ACCESS  read-only
    STATUS      current
    DESCRIPTION
      "Is run or not."
    ::= { hpnicfStatisticEntry 11 }

  hpnicfStatisticPacketCount OBJECT-TYPE
    SYNTAX      Counter64
    MAX-ACCESS  read-only
    STATUS      current
    DESCRIPTION
      "The counter of the packets which is matched."
    ::= { hpnicfStatisticEntry 12 }

  hpnicfStatisticByteCount OBJECT-TYPE
    SYNTAX      Counter64
    MAX-ACCESS  read-only
    STATUS      current
    DESCRIPTION
      "The counter of the byte which is matched."
    ::= { hpnicfStatisticEntry 13 }

  hpnicfStatisticCountClear OBJECT-TYPE
    SYNTAX      INTEGER{cleared(1),nouse(2)}
    MAX-ACCESS  read-write
    STATUS      current
    DESCRIPTION
      "Clear the counter of the packets."
    ::= { hpnicfStatisticEntry 14 }

  hpnicfStatisticRowStatus OBJECT-TYPE
    SYNTAX      RowStatus
    MAX-ACCESS  read-create
    STATUS      current
    DESCRIPTION
      "RowStatus, now support three status: createAndGo, active, destroy."
    ::= { hpnicfStatisticEntry 15 }

  hpnicfStatisticPacketXCount OBJECT-TYPE
    SYNTAX      Counter64
    MAX-ACCESS  read-only
    STATUS      current
    DESCRIPTION
      "The counter of the outprofile packets."
    ::= { hpnicfStatisticEntry 16 }

  hpnicfStatisticByteXCount OBJECT-TYPE
    SYNTAX      Counter64
    MAX-ACCESS  read-only
    STATUS      current
    DESCRIPTION
      "The counter of the outprofile bytes."
    ::= { hpnicfStatisticEntry 17 }

  -- TABLE: hpnicfMirrorTable ------
  hpnicfMirrorTable OBJECT-TYPE
    SYNTAX      SEQUENCE OF HpnicfMirrorEntry
    MAX-ACCESS  not-accessible
    STATUS      current
    DESCRIPTION
      "Mirror table which contains mirror entry."
    ::= { hpnicfLswQosMibObject 8 }

  hpnicfMirrorEntry OBJECT-TYPE
    SYNTAX      HpnicfMirrorEntry
    MAX-ACCESS  not-accessible
    STATUS      current
    DESCRIPTION
      "Configuration information to be mirrored."
    INDEX {
              hpnicfMirrorAclIndex,
              hpnicfMirrorIfIndex,
              hpnicfMirrorVlanID,
              hpnicfMirrorDirection
          }
    ::= { hpnicfMirrorTable 1 }

  HpnicfMirrorEntry ::=
    SEQUENCE
    {
      hpnicfMirrorAclIndex    INTEGER,
      hpnicfMirrorIfIndex    INTEGER,
      hpnicfMirrorVlanID    INTEGER,
      hpnicfMirrorDirection    INTEGER,
      hpnicfMirrorUserAclNum    INTEGER,
      hpnicfMirrorUserAclRule    INTEGER,
      hpnicfMirrorIpAclNum    INTEGER,
      hpnicfMirrorIpAclRule    INTEGER,
      hpnicfMirrorLinkAclNum    INTEGER,
      hpnicfMirrorLinkAclRule    INTEGER,
      hpnicfMirrorToIfIndex    INTEGER,
      hpnicfMirrorToCpu    TruthValue,
      hpnicfMirrorRuntime    TruthValue,
      hpnicfMirrorRowStatus    RowStatus,
      hpnicfMirrorToGroup       Integer32

    }

  hpnicfMirrorAclIndex OBJECT-TYPE
    SYNTAX      INTEGER(0..2999)
    MAX-ACCESS  read-create
    STATUS      current
    DESCRIPTION
      "Index of acl rule."
    ::= { hpnicfMirrorEntry 1 }

  hpnicfMirrorIfIndex OBJECT-TYPE
    SYNTAX      INTEGER
    MAX-ACCESS  read-create
    STATUS      current
    DESCRIPTION
      "ifIndex of port."
    ::= { hpnicfMirrorEntry 2 }

  hpnicfMirrorVlanID OBJECT-TYPE
    SYNTAX      INTEGER(0..4094)
    MAX-ACCESS  read-create
    STATUS      current
    DESCRIPTION
      "Vlan ID."
    ::= { hpnicfMirrorEntry 3 }

  hpnicfMirrorDirection OBJECT-TYPE
    SYNTAX      INTEGER{invalid(0), input(1), output(2)}
    MAX-ACCESS  read-create
    STATUS      current
    DESCRIPTION
      "Direction of data stream."
    ::= { hpnicfMirrorEntry 4 }

  hpnicfMirrorUserAclNum OBJECT-TYPE
    SYNTAX      INTEGER(0|5000..5999|10000..12999)
    MAX-ACCESS  read-create
    STATUS      current
    DESCRIPTION
      "The number of the user acl."
    ::= { hpnicfMirrorEntry 5 }

  hpnicfMirrorUserAclRule OBJECT-TYPE
    SYNTAX      INTEGER(0..65535)
    MAX-ACCESS  read-create
    STATUS      current
    DESCRIPTION
      "The subitem of the user acl."
    ::= { hpnicfMirrorEntry 6 }

  hpnicfMirrorIpAclNum OBJECT-TYPE
    SYNTAX      INTEGER(0|2000..3999|10000..12999)
    MAX-ACCESS  read-create
    STATUS      current
    DESCRIPTION
      "The subitem of the user acl."
    ::= { hpnicfMirrorEntry 7 }

  hpnicfMirrorIpAclRule OBJECT-TYPE
    SYNTAX      INTEGER(0..65535)
    MAX-ACCESS  read-create
    STATUS      current
    DESCRIPTION
      "The subitem of the IP acl."
    ::= { hpnicfMirrorEntry 8 }

  hpnicfMirrorLinkAclNum OBJECT-TYPE
    SYNTAX      INTEGER(0|4000..4999|10000..12999)
    MAX-ACCESS  read-create
    STATUS      current
    DESCRIPTION
      "The number of the link acl."
    ::= { hpnicfMirrorEntry 9 }

  hpnicfMirrorLinkAclRule OBJECT-TYPE
    SYNTAX      INTEGER(0..65535)
    MAX-ACCESS  read-create
    STATUS      current
    DESCRIPTION
      "The subitem of the link acl."
    ::= { hpnicfMirrorEntry 10 }

  hpnicfMirrorToIfIndex OBJECT-TYPE
    SYNTAX      INTEGER
    MAX-ACCESS  read-create
    STATUS      current
    DESCRIPTION
      "The ifIndex of port that to be mirrored to."
    ::= { hpnicfMirrorEntry 11 }

  hpnicfMirrorToCpu OBJECT-TYPE
    SYNTAX      TruthValue
    MAX-ACCESS  read-create
    STATUS      current
    DESCRIPTION
      "Mirror to cpu."
    ::= { hpnicfMirrorEntry 12 }

  hpnicfMirrorRuntime OBJECT-TYPE
    SYNTAX      TruthValue
    MAX-ACCESS  read-only
    STATUS      current
    DESCRIPTION
      "Is run or not."
    ::= { hpnicfMirrorEntry 13 }

  hpnicfMirrorRowStatus OBJECT-TYPE
    SYNTAX      RowStatus
    MAX-ACCESS  read-create
    STATUS      current
    DESCRIPTION
          "RowStatus, now support three status: createAndGo, active, destroy. "
    ::= { hpnicfMirrorEntry 14 }

  hpnicfMirrorToGroup OBJECT-TYPE
    SYNTAX      Integer32
    MAX-ACCESS  read-create
    STATUS      current
    DESCRIPTION
      "The destination of stream-based mirroring is the mirroring group."
    ::= { hpnicfMirrorEntry 15 }


  -- TABLE: hpnicfPortMirrorTable ------
  hpnicfPortMirrorTable OBJECT-TYPE
    SYNTAX      SEQUENCE OF HpnicfPortMirrorEntry
    MAX-ACCESS  not-accessible
    STATUS      current
    DESCRIPTION
      "Port Mirror."
    ::= { hpnicfLswQosMibObject 9 }

  hpnicfPortMirrorEntry OBJECT-TYPE
    SYNTAX      HpnicfPortMirrorEntry
    MAX-ACCESS  not-accessible
    STATUS      current
    DESCRIPTION
      "Configuration information of port mirroring."
    INDEX {
              hpnicfPortMirrorIfIndex
          }
    ::= { hpnicfPortMirrorTable 1 }

  HpnicfPortMirrorEntry ::=
    SEQUENCE
    {
      hpnicfPortMirrorIfIndex    INTEGER,
      hpnicfPortMirrorDirection    INTEGER,
      hpnicfPortMirrorRowStatus    RowStatus
    }

  hpnicfPortMirrorIfIndex OBJECT-TYPE
    SYNTAX      INTEGER
    MAX-ACCESS  read-create
    STATUS      current
    DESCRIPTION
      "The ifIndex of mirror port."
    ::= { hpnicfPortMirrorEntry 1 }

  hpnicfPortMirrorDirection OBJECT-TYPE
    SYNTAX      INTEGER{in(1),out(2),both(3)}
    MAX-ACCESS  read-create
    STATUS      current
    DESCRIPTION
      "The direction of mirror port."
    ::= { hpnicfPortMirrorEntry 2 }

  hpnicfPortMirrorRowStatus OBJECT-TYPE
    SYNTAX      RowStatus
    MAX-ACCESS  read-create
    STATUS      current
    DESCRIPTION
          "RowStatus, now support three status: createAndGo, active, destroy."
    ::= { hpnicfPortMirrorEntry 3 }

  -- TABLE: hpnicfLineRateTable ------
  hpnicfLineRateTable OBJECT-TYPE
    SYNTAX      SEQUENCE OF HpnicfLineRateEntry
    MAX-ACCESS  not-accessible
    STATUS      current
    DESCRIPTION
      "Line Rate."
    ::= { hpnicfLswQosMibObject 10 }

  hpnicfLineRateEntry OBJECT-TYPE
    SYNTAX      HpnicfLineRateEntry
    MAX-ACCESS  not-accessible
    STATUS      current
    DESCRIPTION
      "Configuration information of line-rate port."
    INDEX {
              hpnicfLineRateIfIndex,
              hpnicfLineRateDirection
          }
    ::= { hpnicfLineRateTable 1 }

  HpnicfLineRateEntry ::=
    SEQUENCE
    {
      hpnicfLineRateIfIndex    INTEGER,
      hpnicfLineRateDirection    INTEGER,
      hpnicfLineRateValue    INTEGER,
      hpnicfLineRateRowStatus    RowStatus
    }

  hpnicfLineRateIfIndex OBJECT-TYPE
    SYNTAX      INTEGER
    MAX-ACCESS  read-create
    STATUS      current
    DESCRIPTION
      "The ifIndex of port of line rate."
    ::= { hpnicfLineRateEntry 1 }

  hpnicfLineRateDirection OBJECT-TYPE
    SYNTAX      INTEGER{in(1),out(2)}
    MAX-ACCESS  read-create
    STATUS      current
    DESCRIPTION
      "The direction of line rate."
    ::= { hpnicfLineRateEntry 2 }

  hpnicfLineRateValue OBJECT-TYPE
    SYNTAX      INTEGER
    MAX-ACCESS  read-create
    STATUS      current
    DESCRIPTION
      "The value of the line-rate."
    ::= { hpnicfLineRateEntry 3 }

  hpnicfLineRateRowStatus OBJECT-TYPE
    SYNTAX      RowStatus
    MAX-ACCESS  read-create
    STATUS      current
    DESCRIPTION
          "RowStatus, now support three status: createAndGo, active, destroy."
    ::= { hpnicfLineRateEntry 4 }

  -- TABLE: hpnicfBandwidthTable ------
  hpnicfBandwidthTable OBJECT-TYPE
    SYNTAX      SEQUENCE OF HpnicfBandwidthEntry
    MAX-ACCESS  not-accessible
    STATUS      current
    DESCRIPTION
      "Bandwidth."
    ::= { hpnicfLswQosMibObject 11 }

  hpnicfBandwidthEntry OBJECT-TYPE
    SYNTAX      HpnicfBandwidthEntry
    MAX-ACCESS  not-accessible
    STATUS      current
    DESCRIPTION
      "Configuration information of bandwidth of port."
    INDEX {
              hpnicfBandwidthAclIndex,
              hpnicfBandwidthIfIndex,
              hpnicfBandwidthVlanID,
              hpnicfBandwidthDirection
          }
    ::= { hpnicfBandwidthTable 1 }

  HpnicfBandwidthEntry ::=
    SEQUENCE
    {
      hpnicfBandwidthAclIndex    INTEGER,
      hpnicfBandwidthIfIndex    INTEGER,
      hpnicfBandwidthVlanID    INTEGER,
      hpnicfBandwidthDirection    INTEGER,
      hpnicfBandwidthIpAclNum    INTEGER,
      hpnicfBandwidthIpAclRule    INTEGER,
      hpnicfBandwidthLinkAclNum    INTEGER,
      hpnicfBandwidthLinkAclRule    INTEGER,
      hpnicfBandwidthMinGuaranteedWidth    INTEGER,
      hpnicfBandwidthMaxGuaranteedWidth    INTEGER,
      hpnicfBandwidthWeight    INTEGER,
      hpnicfBandwidthRuntime    TruthValue,
      hpnicfBandwidthRowStatus    RowStatus
    }

  hpnicfBandwidthAclIndex OBJECT-TYPE
    SYNTAX      INTEGER(0..2999)
    MAX-ACCESS  read-create
    STATUS      current
    DESCRIPTION
      "Index of acl rule."
    ::= { hpnicfBandwidthEntry 1 }

  hpnicfBandwidthIfIndex OBJECT-TYPE
    SYNTAX      INTEGER
    MAX-ACCESS  read-create
    STATUS      current
    DESCRIPTION
      "ifIndex of port."
    ::= { hpnicfBandwidthEntry 2 }

  hpnicfBandwidthVlanID OBJECT-TYPE
    SYNTAX      INTEGER(0..4094)
    MAX-ACCESS  read-create
    STATUS      current
    DESCRIPTION
      "Vlan ID."
    ::= { hpnicfBandwidthEntry 3 }

  hpnicfBandwidthDirection OBJECT-TYPE
    SYNTAX      INTEGER{invalid(0), output(2)}
    MAX-ACCESS  read-create
    STATUS      current
    DESCRIPTION
      "Direction of data stream."
    ::= { hpnicfBandwidthEntry 4 }

  hpnicfBandwidthIpAclNum OBJECT-TYPE
    SYNTAX      INTEGER(0|2000..3999|10000..12999)
    MAX-ACCESS  read-create
    STATUS      current
    DESCRIPTION
      "The number of Ip acl."
    ::= { hpnicfBandwidthEntry 5 }

  hpnicfBandwidthIpAclRule OBJECT-TYPE
    SYNTAX      INTEGER(0..65535)
    MAX-ACCESS  read-create
    STATUS      current
    DESCRIPTION
      "The subitem of ip acl."
    ::= { hpnicfBandwidthEntry 6 }

  hpnicfBandwidthLinkAclNum OBJECT-TYPE
    SYNTAX      INTEGER(0|4000..4999|10000..12999)
    MAX-ACCESS  read-create
    STATUS      current
    DESCRIPTION
      "The number of link acl."
    ::= { hpnicfBandwidthEntry 7 }

  hpnicfBandwidthLinkAclRule OBJECT-TYPE
    SYNTAX      INTEGER(0..65535)
    MAX-ACCESS  read-create
    STATUS      current
    DESCRIPTION
      "The subitem of link acl."
    ::= { hpnicfBandwidthEntry 8 }

  hpnicfBandwidthMinGuaranteedWidth OBJECT-TYPE
    SYNTAX      INTEGER(1..8388608)
    MAX-ACCESS  read-write
    STATUS      current
    DESCRIPTION
      "The min width which is guaranteed."
    ::= { hpnicfBandwidthEntry 9 }

  hpnicfBandwidthMaxGuaranteedWidth OBJECT-TYPE
    SYNTAX      INTEGER(1..8388608)
    MAX-ACCESS  read-write
    STATUS      current
    DESCRIPTION
      "The max width which is guaranteed."
    ::= { hpnicfBandwidthEntry 10 }

  hpnicfBandwidthWeight OBJECT-TYPE
    SYNTAX      INTEGER(0..100)
    MAX-ACCESS  read-write
    STATUS      current
    DESCRIPTION
      "Weight of bandwidth."
    ::= { hpnicfBandwidthEntry 11 }

  hpnicfBandwidthRuntime OBJECT-TYPE
    SYNTAX      TruthValue
    MAX-ACCESS  read-only
    STATUS      current
    DESCRIPTION
      "Is run or not."
    ::= { hpnicfBandwidthEntry 12 }

  hpnicfBandwidthRowStatus OBJECT-TYPE
    SYNTAX      RowStatus
    MAX-ACCESS  read-write
    STATUS      current
    DESCRIPTION
          "RowStatus, now support three status: createAndGo, active, destroy."
    ::= { hpnicfBandwidthEntry 13 }

-- TABLE: hpnicfRedTable ------
  hpnicfRedTable OBJECT-TYPE
    SYNTAX      SEQUENCE OF HpnicfRedEntry
    MAX-ACCESS  not-accessible
    STATUS      current
    DESCRIPTION
      "Red table which contains RED entry."
    ::= { hpnicfLswQosMibObject 12 }

  hpnicfRedEntry OBJECT-TYPE
    SYNTAX      HpnicfRedEntry
    MAX-ACCESS  not-accessible
    STATUS      current
    DESCRIPTION
      "Configuration information of RED."
    INDEX {
              hpnicfRedAclIndex,
              hpnicfRedIfIndex,
              hpnicfRedVlanID,
              hpnicfRedDirection
          }
    ::= { hpnicfRedTable 1 }

  HpnicfRedEntry ::=
    SEQUENCE
    {
      hpnicfRedAclIndex    INTEGER,
      hpnicfRedIfIndex    INTEGER,
      hpnicfRedVlanID    INTEGER,
      hpnicfRedDirection    INTEGER,
      hpnicfRedIpAclNum    INTEGER,
      hpnicfRedIpAclRule    INTEGER,
      hpnicfRedLinkAclNum    INTEGER,
      hpnicfRedLinkAclRule    INTEGER,
      hpnicfRedStartQueueLen    INTEGER,
      hpnicfRedStopQueueLen    INTEGER,
      hpnicfRedProbability    INTEGER,
      hpnicfRedRuntime    TruthValue,
      hpnicfRedRowStatus    RowStatus
    }

  hpnicfRedAclIndex OBJECT-TYPE
    SYNTAX      INTEGER(0..2999)
    MAX-ACCESS  read-create
    STATUS      current
    DESCRIPTION
      "Index of acl rule."
    ::= { hpnicfRedEntry 1 }

  hpnicfRedIfIndex OBJECT-TYPE
    SYNTAX      INTEGER
    MAX-ACCESS  read-create
    STATUS      current
    DESCRIPTION
      "ifIndex of port."
    ::= { hpnicfRedEntry 2 }

  hpnicfRedVlanID OBJECT-TYPE
    SYNTAX      INTEGER(0..4094)
    MAX-ACCESS  read-create
    STATUS      current
    DESCRIPTION
      "Vlan ID."
    ::= { hpnicfRedEntry 3 }

  hpnicfRedDirection OBJECT-TYPE
    SYNTAX      INTEGER{invalid(0), output(2)}
    MAX-ACCESS  read-create
    STATUS      current
    DESCRIPTION
      "Direction of data stream."
    ::= { hpnicfRedEntry 4 }

  hpnicfRedIpAclNum OBJECT-TYPE
    SYNTAX      INTEGER(0|2000..3999|10000..12999)
    MAX-ACCESS  read-create
    STATUS      current
    DESCRIPTION
      "The num of Ip acl."
    ::= { hpnicfRedEntry 5 }

  hpnicfRedIpAclRule OBJECT-TYPE
    SYNTAX      INTEGER(0..65535)
    MAX-ACCESS  read-create
    STATUS      current
    DESCRIPTION
      "The subitem of Ip acl."
    ::= { hpnicfRedEntry 6 }

  hpnicfRedLinkAclNum OBJECT-TYPE
    SYNTAX      INTEGER(0|4000..4999|10000..12999)
    MAX-ACCESS  read-create
    STATUS      current
    DESCRIPTION
      "The number of link acl."
    ::= { hpnicfRedEntry 7 }

  hpnicfRedLinkAclRule OBJECT-TYPE
    SYNTAX      INTEGER(0..65535)
    MAX-ACCESS  read-create
    STATUS      current
    DESCRIPTION
      "The subitem of link acl."
    ::= { hpnicfRedEntry 8 }

  hpnicfRedStartQueueLen OBJECT-TYPE
    SYNTAX      INTEGER(0..262128)
    MAX-ACCESS  read-write
    STATUS      current
    DESCRIPTION
      "The length of Starting queue."
    ::= { hpnicfRedEntry 9 }

  hpnicfRedStopQueueLen OBJECT-TYPE
    SYNTAX      INTEGER(0..262128)
    MAX-ACCESS  read-write
    STATUS      current
    DESCRIPTION
      "The length of stopping queue."
    ::= { hpnicfRedEntry 10 }

  hpnicfRedProbability OBJECT-TYPE
    SYNTAX      INTEGER(0..100)
    MAX-ACCESS  read-write
    STATUS      current
    DESCRIPTION
      "Probability."
    ::= { hpnicfRedEntry 11 }

  hpnicfRedRuntime OBJECT-TYPE
    SYNTAX      TruthValue
    MAX-ACCESS  read-only
    STATUS      current
    DESCRIPTION
      "Is run or not."
    ::= { hpnicfRedEntry 12 }

  hpnicfRedRowStatus OBJECT-TYPE
    SYNTAX      RowStatus
    MAX-ACCESS  read-write
    STATUS      current
    DESCRIPTION
      "RowStatus, now support three status: createAndGo, active, destroy."
    ::= { hpnicfRedEntry 13 }

  -- TABLE: hpnicfMirrorGroupTable ------
  hpnicfMirrorGroupTable OBJECT-TYPE
    SYNTAX      SEQUENCE OF HpnicfMirrorGroupEntry
    MAX-ACCESS  not-accessible
    STATUS      current
    DESCRIPTION
      "Mirror Group."
    ::= { hpnicfLswQosMibObject 13 }

  hpnicfMirrorGroupEntry OBJECT-TYPE
    SYNTAX      HpnicfMirrorGroupEntry
    MAX-ACCESS  not-accessible
    STATUS      current
    DESCRIPTION
      "Configuration information of mirroring group."
    INDEX {
              hpnicfMirrorGroupID
          }
    ::= { hpnicfMirrorGroupTable 1 }

  HpnicfMirrorGroupEntry ::=
    SEQUENCE
    {
      hpnicfMirrorGroupID    INTEGER,
      hpnicfMirrorGroupDirection    INTEGER,
      hpnicfMirrorGroupMirrorIfIndexList    OCTET STRING,
      hpnicfMirrorGroupMonitorIfIndex    INTEGER,
      hpnicfMirrorGroupRowStatus    RowStatus
    }

  hpnicfMirrorGroupID OBJECT-TYPE
    SYNTAX      INTEGER(1..20)
    MAX-ACCESS  read-only
    STATUS      current
    DESCRIPTION
      "Group ID of mirroring group."
    ::= { hpnicfMirrorGroupEntry 1 }

  hpnicfMirrorGroupDirection OBJECT-TYPE
    SYNTAX      INTEGER{input(1),output(2)}
    MAX-ACCESS  read-write
    STATUS      current
    DESCRIPTION
      "Direction of data stream which would be mirrored."
    ::= { hpnicfMirrorGroupEntry 2 }

  hpnicfMirrorGroupMirrorIfIndexList OBJECT-TYPE
    SYNTAX      OCTET STRING(SIZE (1..257))
    MAX-ACCESS  read-write
    STATUS      current
    DESCRIPTION
      "ifIndex list of source port."
    ::= { hpnicfMirrorGroupEntry 3 }

  hpnicfMirrorGroupMonitorIfIndex OBJECT-TYPE
    SYNTAX      INTEGER
    MAX-ACCESS  read-write
    STATUS      current
    DESCRIPTION
      "ifIndex of destination port."
    ::= { hpnicfMirrorGroupEntry 4 }

  hpnicfMirrorGroupRowStatus OBJECT-TYPE
    SYNTAX      RowStatus
    MAX-ACCESS  read-write
    STATUS      current
    DESCRIPTION
          "RowStatus, now support three status: createAndGo, active, destroy."
    ::= { hpnicfMirrorGroupEntry 5 }

  -- TABLE: hpnicfFlowtempTable ------
  hpnicfFlowtempTable OBJECT-TYPE
    SYNTAX      SEQUENCE OF HpnicfFlowtempEntry
    MAX-ACCESS  not-accessible
    STATUS      current
    DESCRIPTION
      "Flow-template table which contains flow-template entry."
    ::= { hpnicfLswQosMibObject 14 }

  hpnicfFlowtempEntry OBJECT-TYPE
    SYNTAX      HpnicfFlowtempEntry
    MAX-ACCESS  not-accessible
    STATUS      current
    DESCRIPTION
      "Configuration information of flow-template."
    INDEX {
              hpnicfFlowtempIndex
          }
    ::= { hpnicfFlowtempTable 1 }

  HpnicfFlowtempEntry ::=
    SEQUENCE
    {
      hpnicfFlowtempIndex    INTEGER,
      hpnicfFlowtempIpProtocol    TruthValue,
      hpnicfFlowtempTcpFlag    TruthValue,
      hpnicfFlowtempSPort    TruthValue,
      hpnicfFlowtempDPort    TruthValue,
      hpnicfFlowtempIcmpType    TruthValue,
      hpnicfFlowtempIcmpCode    TruthValue,
      hpnicfFlowtempFragment    TruthValue,
      hpnicfFlowtempDscp    TruthValue,
      hpnicfFlowtempIpPre    TruthValue,
      hpnicfFlowtempTos    TruthValue,
      hpnicfFlowtempSIp          TruthValue,
      hpnicfFlowtempSIpMask    IpAddress,
      hpnicfFlowtempDIp          TruthValue,
      hpnicfFlowtempDIpMask    IpAddress,
      hpnicfFlowtempEthProtocol    TruthValue,
      hpnicfFlowtempSMac          TruthValue,
      hpnicfFlowtempSMacMask    MacAddress,
      hpnicfFlowtempDMac          TruthValue,
      hpnicfFlowtempDMacMask    MacAddress,
      hpnicfFlowtempVpn    TruthValue,
      hpnicfFlowtempRowStatus    RowStatus,
      hpnicfFlowtempVlanId    TruthValue,
      hpnicfFlowtempCos    TruthValue
    }

  hpnicfFlowtempIndex OBJECT-TYPE
    SYNTAX      INTEGER{default(1), user-defined(2)}
    MAX-ACCESS  read-only
    STATUS      current
    DESCRIPTION
      "Index of flow template."
    ::= { hpnicfFlowtempEntry 1 }

  hpnicfFlowtempIpProtocol OBJECT-TYPE
    SYNTAX      TruthValue
    MAX-ACCESS  read-create
    STATUS      current
    DESCRIPTION
      "protocol-type of IP packet."
    ::= { hpnicfFlowtempEntry 2 }

  hpnicfFlowtempTcpFlag OBJECT-TYPE
    SYNTAX      TruthValue
    MAX-ACCESS  read-create
    STATUS      current
    DESCRIPTION
      "The flag of Tcp paceket. "
    ::= { hpnicfFlowtempEntry 3 }

  hpnicfFlowtempSPort OBJECT-TYPE
    SYNTAX      TruthValue
    MAX-ACCESS  read-create
    STATUS      current
    DESCRIPTION
      "The port of source."
    ::= { hpnicfFlowtempEntry 4 }

  hpnicfFlowtempDPort OBJECT-TYPE
    SYNTAX      TruthValue
    MAX-ACCESS  read-create
    STATUS      current
    DESCRIPTION
      "The port of destination."
    ::= { hpnicfFlowtempEntry 5 }

  hpnicfFlowtempIcmpType OBJECT-TYPE
    SYNTAX      TruthValue
    MAX-ACCESS  read-create
    STATUS      current
    DESCRIPTION
      "The type of Icmp."
    ::= { hpnicfFlowtempEntry 6 }

  hpnicfFlowtempIcmpCode OBJECT-TYPE
    SYNTAX      TruthValue
    MAX-ACCESS  read-create
    STATUS      current
    DESCRIPTION
      "The code of Icmp."
    ::= { hpnicfFlowtempEntry 7 }

  hpnicfFlowtempFragment OBJECT-TYPE
    SYNTAX      TruthValue
    MAX-ACCESS  read-create
    STATUS      current
    DESCRIPTION
      "The flag of Fragment. "
    ::= { hpnicfFlowtempEntry 8 }

  hpnicfFlowtempDscp OBJECT-TYPE
    SYNTAX      TruthValue
    MAX-ACCESS  read-create
    STATUS      current
    DESCRIPTION
      "Dscp of IP packet."
    ::= { hpnicfFlowtempEntry 9 }

  hpnicfFlowtempIpPre OBJECT-TYPE
    SYNTAX      TruthValue
    MAX-ACCESS  read-create
    STATUS      current
    DESCRIPTION
      "The Precedence of Ip packet. "
    ::= { hpnicfFlowtempEntry 10 }

  hpnicfFlowtempTos OBJECT-TYPE
    SYNTAX      TruthValue
    MAX-ACCESS  read-create
    STATUS      current
    DESCRIPTION
      "Tos of IP packet."
    ::= { hpnicfFlowtempEntry 11 }

  hpnicfFlowtempSIp OBJECT-TYPE
    SYNTAX      TruthValue
    MAX-ACCESS  read-create
    STATUS      current
    DESCRIPTION
      "The Ip of source."
    ::= { hpnicfFlowtempEntry 12 }

  hpnicfFlowtempSIpMask OBJECT-TYPE
    SYNTAX      IpAddress
    MAX-ACCESS  read-create
    STATUS      current
    DESCRIPTION
      "The mask of source-Ip."
    ::= { hpnicfFlowtempEntry 13 }

  hpnicfFlowtempDIp OBJECT-TYPE
    SYNTAX      TruthValue
    MAX-ACCESS  read-create
    STATUS      current
    DESCRIPTION
      "The Ip of destination."
    ::= { hpnicfFlowtempEntry 14 }

  hpnicfFlowtempDIpMask OBJECT-TYPE
    SYNTAX      IpAddress
    MAX-ACCESS  read-create
    STATUS      current
    DESCRIPTION
      "The mask of destination-Ip."
    ::= { hpnicfFlowtempEntry 15 }

  hpnicfFlowtempEthProtocol OBJECT-TYPE
    SYNTAX      TruthValue
    MAX-ACCESS  read-create
    STATUS      current
    DESCRIPTION
      "Protocol type of Ethernet."
    ::= { hpnicfFlowtempEntry 16 }

  hpnicfFlowtempSMac OBJECT-TYPE
    SYNTAX      TruthValue
    MAX-ACCESS  read-create
    STATUS      current
    DESCRIPTION
      "The Mac of source."
    ::= { hpnicfFlowtempEntry 17 }

  hpnicfFlowtempSMacMask OBJECT-TYPE
    SYNTAX      MacAddress
    MAX-ACCESS  read-create
    STATUS      current
    DESCRIPTION
      "The mask of source-Mac."
    ::= { hpnicfFlowtempEntry 18 }

  hpnicfFlowtempDMac OBJECT-TYPE
    SYNTAX      TruthValue
    MAX-ACCESS  read-create
    STATUS      current
    DESCRIPTION
      "The mac of destination."
    ::= { hpnicfFlowtempEntry 19 }

  hpnicfFlowtempDMacMask OBJECT-TYPE
    SYNTAX      MacAddress
    MAX-ACCESS  read-create
    STATUS      current
    DESCRIPTION
      "The mask of destination-Mac."
    ::= { hpnicfFlowtempEntry 20 }

  hpnicfFlowtempVpn OBJECT-TYPE
    SYNTAX      TruthValue
    MAX-ACCESS  read-create
    STATUS      current
    DESCRIPTION
      "Vpn"
    ::= { hpnicfFlowtempEntry 21 }

  hpnicfFlowtempRowStatus OBJECT-TYPE
    SYNTAX      RowStatus
    MAX-ACCESS  read-create
    STATUS      current
    DESCRIPTION
      "RowStatus, now support three status: createAndGo, active, destroy."
    ::= { hpnicfFlowtempEntry 22 }

  hpnicfFlowtempVlanId OBJECT-TYPE
    SYNTAX      TruthValue
    MAX-ACCESS  read-create
    STATUS      current
    DESCRIPTION
      "Source VLAN ID."
    ::= { hpnicfFlowtempEntry 23 }

  hpnicfFlowtempCos OBJECT-TYPE
    SYNTAX      TruthValue
    MAX-ACCESS  read-create
    STATUS      current
    DESCRIPTION
      "802.1P priority."
    ::= { hpnicfFlowtempEntry 24 }

  -- TABLE: hpnicfFlowtempEnableTable ------
  hpnicfFlowtempEnableTable OBJECT-TYPE
    SYNTAX      SEQUENCE OF HpnicfFlowtempEnableEntry
    MAX-ACCESS  not-accessible
    STATUS      current
    DESCRIPTION
      "The table of flow-template."
    ::= { hpnicfLswQosMibObject 15 }

  hpnicfFlowtempEnableEntry OBJECT-TYPE
    SYNTAX      HpnicfFlowtempEnableEntry
    MAX-ACCESS  not-accessible
    STATUS      current
    DESCRIPTION
      "Enable entry of flow-template."
    INDEX {
              hpnicfFlowtempEnableIfIndex,
              hpnicfFlowtempEnableVlanID
          }
    ::= { hpnicfFlowtempEnableTable 1 }

  HpnicfFlowtempEnableEntry ::=
    SEQUENCE
    {
      hpnicfFlowtempEnableIfIndex    INTEGER,
      hpnicfFlowtempEnableVlanID    INTEGER,
      hpnicfFlowtempEnableFlowtempIndex  INTEGER
    }

  hpnicfFlowtempEnableIfIndex OBJECT-TYPE
    SYNTAX      INTEGER
    MAX-ACCESS  read-create
    STATUS      current
    DESCRIPTION
      "ifIndex of port."
    ::= { hpnicfFlowtempEnableEntry 1 }

  hpnicfFlowtempEnableVlanID OBJECT-TYPE
    SYNTAX      INTEGER(0..4094)
    MAX-ACCESS  read-create
    STATUS      current
    DESCRIPTION
      "Vlan ID."
    ::= { hpnicfFlowtempEnableEntry 2 }

  hpnicfFlowtempEnableFlowtempIndex OBJECT-TYPE
    SYNTAX      INTEGER{default(1), user-defined(2)}
    MAX-ACCESS  read-write
    STATUS      current
    DESCRIPTION
      "The index of Flowtemp table."
    ::= { hpnicfFlowtempEnableEntry 3 }

  -- TABLE: hpnicfTrafficShapeTable ------
  hpnicfTrafficShapeTable OBJECT-TYPE
    SYNTAX      SEQUENCE OF HpnicfTrafficShapeEntry
    MAX-ACCESS  not-accessible
    STATUS      current
    DESCRIPTION
      "The traffic-shape table which contains traffic-shape entry."
    ::= { hpnicfLswQosMibObject 16 }

  hpnicfTrafficShapeEntry OBJECT-TYPE
    SYNTAX      HpnicfTrafficShapeEntry
    MAX-ACCESS  not-accessible
    STATUS      current
    DESCRIPTION
      "Configuration information of traffic-shape."
    INDEX {
              hpnicfTrafficShapeIfIndex,
              hpnicfTrafficShapeQueueId
          }
    ::= { hpnicfTrafficShapeTable 1 }

  HpnicfTrafficShapeEntry ::=
    SEQUENCE
    {
      hpnicfTrafficShapeIfIndex    INTEGER,
      hpnicfTrafficShapeQueueId    INTEGER,
      hpnicfTrafficShapeMaxRate    INTEGER,
      hpnicfTrafficShapeBurstSize    INTEGER,
      hpnicfTrafficShapeBufferLimit    INTEGER,
      hpnicfTrafficShapeRowStatus    RowStatus
    }

  hpnicfTrafficShapeIfIndex OBJECT-TYPE
    SYNTAX      INTEGER
    MAX-ACCESS  read-create
    STATUS      current
    DESCRIPTION
      "IfIdex of port."
    ::= { hpnicfTrafficShapeEntry 1 }

  hpnicfTrafficShapeQueueId OBJECT-TYPE
    SYNTAX      INTEGER(0..7|255)
    MAX-ACCESS  read-create
    STATUS      current
    DESCRIPTION
      "ID of queue which would be shaped."
    ::= { hpnicfTrafficShapeEntry 2 }

  hpnicfTrafficShapeMaxRate OBJECT-TYPE
    SYNTAX      INTEGER
    MAX-ACCESS  read-create
    STATUS      current
    DESCRIPTION
      "The max rate."
    ::= { hpnicfTrafficShapeEntry 3 }

  hpnicfTrafficShapeBurstSize OBJECT-TYPE
    SYNTAX      INTEGER
    MAX-ACCESS  read-create
    STATUS      current
    DESCRIPTION
      "The size of burst."
    ::= { hpnicfTrafficShapeEntry 4 }

  hpnicfTrafficShapeBufferLimit OBJECT-TYPE
    SYNTAX      INTEGER(0|16..8000)
    MAX-ACCESS  read-create
    STATUS      current
    DESCRIPTION
      "The limit of buffer."
    ::= { hpnicfTrafficShapeEntry 5 }

  hpnicfTrafficShapeRowStatus OBJECT-TYPE
    SYNTAX      RowStatus
    MAX-ACCESS  read-create
    STATUS      current
    DESCRIPTION
      "RowStatus, now support three status: createAndGo, active, destroy."
    ::= { hpnicfTrafficShapeEntry 6 }

  -- TABLE: hpnicfPortQueueTable ------
  hpnicfPortQueueTable OBJECT-TYPE
    SYNTAX      SEQUENCE OF HpnicfPortQueueEntry
    MAX-ACCESS  not-accessible
    STATUS      current
    DESCRIPTION
      "The port-queue table which contains port-queue entry."
    ::= { hpnicfLswQosMibObject 17 }

  hpnicfPortQueueEntry OBJECT-TYPE
    SYNTAX      HpnicfPortQueueEntry
    MAX-ACCESS  not-accessible
    STATUS      current
    DESCRIPTION
      "Configuration information of port-queue."
    INDEX {
              hpnicfPortQueueIfIndex,
              hpnicfPortQueueQueueID
          }
    ::= { hpnicfPortQueueTable 1 }

  HpnicfPortQueueEntry ::=
    SEQUENCE
    {
      hpnicfPortQueueIfIndex    INTEGER,
      hpnicfPortQueueQueueID    INTEGER,
      hpnicfPortQueueWrrPriority    INTEGER,
      hpnicfPortQueueWeight    INTEGER
    }

  hpnicfPortQueueIfIndex OBJECT-TYPE
    SYNTAX      INTEGER
    MAX-ACCESS  read-only
    STATUS      current
    DESCRIPTION
      "ifIndex of port."
    ::= { hpnicfPortQueueEntry 1 }

  hpnicfPortQueueQueueID OBJECT-TYPE
    SYNTAX      INTEGER(0..7)
    MAX-ACCESS  read-only
    STATUS      current
    DESCRIPTION
      "ID of port-queue."
    ::= { hpnicfPortQueueEntry 2 }

  hpnicfPortQueueWrrPriority OBJECT-TYPE
    SYNTAX      INTEGER{sp(1),wrr-high-priority(2),wrr-low-priority(3)}
    MAX-ACCESS  read-write
    STATUS      current
    DESCRIPTION
      "The priority of Wrr."
    ::= { hpnicfPortQueueEntry 3 }

  hpnicfPortQueueWeight OBJECT-TYPE
    SYNTAX      INTEGER(0|1..255)
    MAX-ACCESS  read-write
    STATUS      current
    DESCRIPTION
      "The weight of this queue."
    ::= { hpnicfPortQueueEntry 4 }

  -- TABLE: hpnicfDropModeTable ------
  hpnicfDropModeTable OBJECT-TYPE
    SYNTAX      SEQUENCE OF HpnicfDropModeEntry
    MAX-ACCESS  not-accessible
    STATUS      current
    DESCRIPTION
      "The drop-mode table which contains drop-mode entry."
    ::= { hpnicfLswQosMibObject 18 }

  hpnicfDropModeEntry OBJECT-TYPE
    SYNTAX      HpnicfDropModeEntry
    MAX-ACCESS  not-accessible
    STATUS      current
    DESCRIPTION
      "Configuration information of the drop-mode."
    INDEX {
              hpnicfDropModeIfIndex
          }
    ::= { hpnicfDropModeTable 1 }

  HpnicfDropModeEntry ::=
    SEQUENCE
    {
      hpnicfDropModeIfIndex    INTEGER,
      hpnicfDropModeMode    INTEGER,
      hpnicfDropModeWredIndex    INTEGER
    }

  hpnicfDropModeIfIndex OBJECT-TYPE
    SYNTAX      INTEGER
    MAX-ACCESS  read-only
    STATUS      current
    DESCRIPTION
      "ifIndex of port."
    ::= { hpnicfDropModeEntry 1 }

  hpnicfDropModeMode OBJECT-TYPE
    SYNTAX      INTEGER{random-detect(1),tail-drop(2)}
    MAX-ACCESS  read-write
    STATUS      current
    DESCRIPTION
      "Mode."
    DEFVAL      { 2 }
    ::= { hpnicfDropModeEntry 2 }

  hpnicfDropModeWredIndex OBJECT-TYPE
    SYNTAX      INTEGER(0..3)
    MAX-ACCESS  read-write
    STATUS      current
    DESCRIPTION
      "The index of Wred table."
    ::= { hpnicfDropModeEntry 3 }

  -- TABLE: hpnicfWredTable ------
  hpnicfWredTable OBJECT-TYPE
    SYNTAX      SEQUENCE OF HpnicfWredEntry
    MAX-ACCESS  not-accessible
    STATUS      current
    DESCRIPTION
      "The Wred table which contains wred Entry."
    ::= { hpnicfLswQosMibObject 19 }

  hpnicfWredEntry OBJECT-TYPE
    SYNTAX      HpnicfWredEntry
    MAX-ACCESS  not-accessible
    STATUS      current
    DESCRIPTION
      "Configuration information of Wred."
    INDEX {
              hpnicfWredIndex,
              hpnicfWredQueueId
          }
    ::= { hpnicfWredTable 1 }

  HpnicfWredEntry ::=
    SEQUENCE
    {
      hpnicfWredIndex    INTEGER,
      hpnicfWredQueueId    INTEGER,
      hpnicfWredGreenMinThreshold    INTEGER,
      hpnicfWredGreenMaxThreshold    INTEGER,
      hpnicfWredGreenMaxProb    INTEGER,
      hpnicfWredYellowMinThreshold    INTEGER,
      hpnicfWredYellowMaxThreshold    INTEGER,
      hpnicfWredYellowMaxProb    INTEGER,
      hpnicfWredRedMinThreshold    INTEGER,
      hpnicfWredRedMaxThreshold    INTEGER,
      hpnicfWredRedMaxProb    INTEGER,
      hpnicfWredExponent    INTEGER
    }

  hpnicfWredIndex OBJECT-TYPE
    SYNTAX      INTEGER(0..3)
    MAX-ACCESS  read-only
    STATUS      current
    DESCRIPTION
      "Index of wred."
    ::= { hpnicfWredEntry 1 }

  hpnicfWredQueueId OBJECT-TYPE
    SYNTAX      INTEGER(0..7)
    MAX-ACCESS  read-only
    STATUS      current
    DESCRIPTION
      "Queue ID."
    ::= { hpnicfWredEntry 2 }

  hpnicfWredGreenMinThreshold OBJECT-TYPE
    SYNTAX      INTEGER(0..65535)
    MAX-ACCESS  read-write
    STATUS      current
    DESCRIPTION
      "The min threshold of Green."
    ::= { hpnicfWredEntry 3 }

  hpnicfWredGreenMaxThreshold OBJECT-TYPE
    SYNTAX      INTEGER(0..65535)
    MAX-ACCESS  read-write
    STATUS      current
    DESCRIPTION
      "The max threshold of Greem."
    ::= { hpnicfWredEntry 4 }

  hpnicfWredGreenMaxProb OBJECT-TYPE
    SYNTAX      INTEGER(1..15)
    MAX-ACCESS  read-write
    STATUS      current
    DESCRIPTION
      "The max prob of Green."
    ::= { hpnicfWredEntry 5 }

  hpnicfWredYellowMinThreshold OBJECT-TYPE
    SYNTAX      INTEGER(0..65535)
    MAX-ACCESS  read-write
    STATUS      current
    DESCRIPTION
      "The min threshold of Yellow."
    ::= { hpnicfWredEntry 6 }

  hpnicfWredYellowMaxThreshold OBJECT-TYPE
    SYNTAX      INTEGER(0..65535)
    MAX-ACCESS  read-write
    STATUS      current
    DESCRIPTION
      "The max threshold of Yellow."
    ::= { hpnicfWredEntry 7 }

  hpnicfWredYellowMaxProb OBJECT-TYPE
    SYNTAX      INTEGER(1..15)
    MAX-ACCESS  read-write
    STATUS      current
    DESCRIPTION
      "The Prob threshold of Yellow."
    ::= { hpnicfWredEntry 8 }

  hpnicfWredRedMinThreshold OBJECT-TYPE
    SYNTAX      INTEGER(0..65535)
    MAX-ACCESS  read-write
    STATUS      current
    DESCRIPTION
      "The min threshold of Red."
    ::= { hpnicfWredEntry 9 }

  hpnicfWredRedMaxThreshold OBJECT-TYPE
    SYNTAX      INTEGER(0..65535)
    MAX-ACCESS  read-write
    STATUS      current
    DESCRIPTION
      "The max threshold of Red."
    ::= { hpnicfWredEntry 10 }

  hpnicfWredRedMaxProb OBJECT-TYPE
    SYNTAX      INTEGER(1..15)
    MAX-ACCESS  read-write
    STATUS      current
    DESCRIPTION
      "The max prob of Red."
    ::= { hpnicfWredEntry 11 }

  hpnicfWredExponent OBJECT-TYPE
    SYNTAX      INTEGER(1..15)
    MAX-ACCESS  read-write
    STATUS      current
    DESCRIPTION
      "Exponent."
    DEFVAL      { 9 }
    ::= { hpnicfWredEntry 12 }

  -- TABLE: hpnicfCosToLocalPrecedenceMapTable ------
  hpnicfCosToLocalPrecedenceMapTable OBJECT-TYPE
    SYNTAX      SEQUENCE OF HpnicfCosToLocalPrecedenceMapEntry
    MAX-ACCESS  not-accessible
    STATUS      current
    DESCRIPTION
      "Table of map of the COS to local-precedence."
    ::= { hpnicfLswQosMibObject 20 }

  hpnicfCosToLocalPrecedenceMapEntry OBJECT-TYPE
    SYNTAX      HpnicfCosToLocalPrecedenceMapEntry
    MAX-ACCESS  not-accessible
    STATUS      current
    DESCRIPTION
      "Configuration information of map of the COS to local precedence."
    INDEX {
              hpnicfCosToLocalPrecedenceMapCosIndex
          }
    ::= { hpnicfCosToLocalPrecedenceMapTable 1 }

  HpnicfCosToLocalPrecedenceMapEntry ::=
    SEQUENCE
    {
      hpnicfCosToLocalPrecedenceMapCosIndex    INTEGER,
      hpnicfCosToLocalPrecedenceMapLocalPrecedenceValue       INTEGER
    }

  hpnicfCosToLocalPrecedenceMapCosIndex OBJECT-TYPE
    SYNTAX      INTEGER(0..7)
    MAX-ACCESS  read-only
    STATUS      current
    DESCRIPTION
      "Index of the map."
    ::= { hpnicfCosToLocalPrecedenceMapEntry 1 }

  hpnicfCosToLocalPrecedenceMapLocalPrecedenceValue OBJECT-TYPE
    SYNTAX      INTEGER(0..7)
    MAX-ACCESS  read-write
    STATUS      current
    DESCRIPTION
      "Value of local precedence."
    ::= { hpnicfCosToLocalPrecedenceMapEntry 2 }

  -- TABLE: hpnicfCosToDropPrecedenceMapTable ------
  hpnicfCosToDropPrecedenceMapTable OBJECT-TYPE
    SYNTAX      SEQUENCE OF HpnicfCosToDropPrecedenceMapEntry
    MAX-ACCESS  not-accessible
    STATUS      current
    DESCRIPTION
      "The table of map of COS to drop-precedence."
    ::= { hpnicfLswQosMibObject 21 }

  hpnicfCosToDropPrecedenceMapEntry OBJECT-TYPE
    SYNTAX      HpnicfCosToDropPrecedenceMapEntry
    MAX-ACCESS  not-accessible
    STATUS      current
    DESCRIPTION
      "Configuration information of the map of the COS to drop-precedence."
    INDEX {
              hpnicfCosToDropPrecedenceMapCosIndex
          }
    ::= { hpnicfCosToDropPrecedenceMapTable 1 }

  HpnicfCosToDropPrecedenceMapEntry ::=
    SEQUENCE
    {
      hpnicfCosToDropPrecedenceMapCosIndex    INTEGER,
      hpnicfCosToDropPrecedenceMapDropPrecedenceValue       INTEGER
    }

  hpnicfCosToDropPrecedenceMapCosIndex OBJECT-TYPE
    SYNTAX      INTEGER(0..7)
    MAX-ACCESS  read-only
    STATUS      current
    DESCRIPTION
      "Index of the map."
    ::= { hpnicfCosToDropPrecedenceMapEntry 1 }

  hpnicfCosToDropPrecedenceMapDropPrecedenceValue OBJECT-TYPE
    SYNTAX      INTEGER(0..2)
    MAX-ACCESS  read-write
    STATUS      current
    DESCRIPTION
      "Value of drop-precedence."
    ::= { hpnicfCosToDropPrecedenceMapEntry 2 }

  -- TABLE: hpnicfDscpMapTable ------
  hpnicfDscpMapTable OBJECT-TYPE
    SYNTAX      SEQUENCE OF HpnicfDscpMapEntry
    MAX-ACCESS  not-accessible
    STATUS      current
    DESCRIPTION
      "Table of dscp map."
    ::= { hpnicfLswQosMibObject 22 }

  hpnicfDscpMapEntry OBJECT-TYPE
    SYNTAX      HpnicfDscpMapEntry
    MAX-ACCESS  not-accessible
    STATUS      current
    DESCRIPTION
      "Configuration information of Dscp map."
    INDEX {
              hpnicfDscpMapConformLevel,
              hpnicfDscpMapDscpIndex
          }
    ::= { hpnicfDscpMapTable 1 }

  HpnicfDscpMapEntry ::=
    SEQUENCE
    {
      hpnicfDscpMapConformLevel    INTEGER,
      hpnicfDscpMapDscpIndex    INTEGER,
      hpnicfDscpMapDscpValue    INTEGER,
      hpnicfDscpMapExpValue    INTEGER,
      hpnicfDscpMapCosValue    INTEGER,
      hpnicfDscpMapLocalPrecedence    INTEGER,
      hpnicfDscpMapDropPrecedence    INTEGER
    }

  hpnicfDscpMapConformLevel OBJECT-TYPE
    SYNTAX      INTEGER(0..2)
    MAX-ACCESS  read-only
    STATUS      current
    DESCRIPTION
      "Conformable level of Dscp-map."
    ::= { hpnicfDscpMapEntry 1 }

  hpnicfDscpMapDscpIndex OBJECT-TYPE
    SYNTAX      INTEGER(0..63)
    MAX-ACCESS  read-only
    STATUS      current
    DESCRIPTION
      "Index of dscp."
    ::= { hpnicfDscpMapEntry 2 }

  hpnicfDscpMapDscpValue OBJECT-TYPE
    SYNTAX      INTEGER(0..63)
    MAX-ACCESS  read-write
    STATUS      current
    DESCRIPTION
      "Value of Dscp."
    ::= { hpnicfDscpMapEntry 3 }

  hpnicfDscpMapExpValue OBJECT-TYPE
    SYNTAX      INTEGER(0..7)
    MAX-ACCESS  read-write
    STATUS      current
    DESCRIPTION
      "Exp value."
    ::= { hpnicfDscpMapEntry 4 }

  hpnicfDscpMapCosValue OBJECT-TYPE
    SYNTAX      INTEGER(0..7)
    MAX-ACCESS  read-write
    STATUS      current
    DESCRIPTION
      "COS value."
    ::= { hpnicfDscpMapEntry 5 }

  hpnicfDscpMapLocalPrecedence OBJECT-TYPE
    SYNTAX      INTEGER(0..7)
    MAX-ACCESS  read-write
    STATUS      current
    DESCRIPTION
      "The precedence of local."
    ::= { hpnicfDscpMapEntry 6 }

  hpnicfDscpMapDropPrecedence OBJECT-TYPE
    SYNTAX      INTEGER(0..2)
    MAX-ACCESS  read-write
    STATUS      current
    DESCRIPTION
      "The precedence of Drop."
    ::= { hpnicfDscpMapEntry 7 }

  -- TABLE: hpnicfExpMapTable ------
  hpnicfExpMapTable OBJECT-TYPE
    SYNTAX      SEQUENCE OF HpnicfExpMapEntry
    MAX-ACCESS  not-accessible
    STATUS      current
    DESCRIPTION
      "The table of Exp-map"
    ::= { hpnicfLswQosMibObject 23 }

  hpnicfExpMapEntry OBJECT-TYPE
    SYNTAX      HpnicfExpMapEntry
    MAX-ACCESS  not-accessible
    STATUS      current
    DESCRIPTION
      "Configuration information of Exp-map."
    INDEX {
              hpnicfExpMapConformLevel,
              hpnicfExpMapExpIndex
          }
    ::= { hpnicfExpMapTable 1 }

  HpnicfExpMapEntry ::=
    SEQUENCE
    {
      hpnicfExpMapConformLevel    INTEGER,
      hpnicfExpMapExpIndex     INTEGER,
      hpnicfExpMapDscpValue    INTEGER,
      hpnicfExpMapExpValue    INTEGER,
      hpnicfExpMapCosValue    INTEGER,
      hpnicfExpMapLocalPrecedence    INTEGER,
      hpnicfExpMapDropPrecedence    INTEGER
    }

  hpnicfExpMapConformLevel OBJECT-TYPE
    SYNTAX      INTEGER(0..2)
    MAX-ACCESS  read-only
    STATUS      current
    DESCRIPTION
      "Conformable level of Exp-map."
    ::= { hpnicfExpMapEntry 1 }

  hpnicfExpMapExpIndex OBJECT-TYPE
    SYNTAX      INTEGER(0..7)
    MAX-ACCESS  read-only
    STATUS      current
    DESCRIPTION
      "Index of Exp."
    ::= { hpnicfExpMapEntry 2 }

  hpnicfExpMapDscpValue OBJECT-TYPE
    SYNTAX      INTEGER(0..63)
    MAX-ACCESS  read-write
    STATUS      current
    DESCRIPTION
      "Dscp value."
    ::= { hpnicfExpMapEntry 3 }

  hpnicfExpMapExpValue OBJECT-TYPE
    SYNTAX      INTEGER(0..7)
    MAX-ACCESS  read-write
    STATUS      current
    DESCRIPTION
      "Exp value."
    ::= { hpnicfExpMapEntry 4 }

  hpnicfExpMapCosValue OBJECT-TYPE
    SYNTAX      INTEGER(0..7)
    MAX-ACCESS  read-write
    STATUS      current
    DESCRIPTION
      "COS Value."
    ::= { hpnicfExpMapEntry 5 }

  hpnicfExpMapLocalPrecedence OBJECT-TYPE
    SYNTAX      INTEGER(0..7)
    MAX-ACCESS  read-write
    STATUS      current
    DESCRIPTION
      "The precedence of local."
    ::= { hpnicfExpMapEntry 6 }

  hpnicfExpMapDropPrecedence OBJECT-TYPE
    SYNTAX      INTEGER(0..2)
    MAX-ACCESS  read-write
    STATUS      current
    DESCRIPTION
      "The precedence of Drop."
    ::= { hpnicfExpMapEntry 7 }

  -- TABLE: hpnicfLocalPrecedenceMapTable ------
  hpnicfLocalPrecedenceMapTable OBJECT-TYPE
    SYNTAX      SEQUENCE OF HpnicfLocalPrecedenceMapEntry
    MAX-ACCESS  not-accessible
    STATUS      current
    DESCRIPTION
      "The table of local-precedence map."
    ::= { hpnicfLswQosMibObject 24 }

  hpnicfLocalPrecedenceMapEntry OBJECT-TYPE
    SYNTAX      HpnicfLocalPrecedenceMapEntry
    MAX-ACCESS  not-accessible
    STATUS      current
    DESCRIPTION
      "Configuraion information of local-precedence map."
    INDEX {
              hpnicfLocalPrecedenceMapConformLevel,
              hpnicfLocalPrecedenceMapLocalPrecedenceIndex
          }
    ::= { hpnicfLocalPrecedenceMapTable 1 }

  HpnicfLocalPrecedenceMapEntry ::=
    SEQUENCE
    {
      hpnicfLocalPrecedenceMapConformLevel    INTEGER,
      hpnicfLocalPrecedenceMapLocalPrecedenceIndex    INTEGER,
      hpnicfLocalPrecedenceMapCosValue       INTEGER
    }

  hpnicfLocalPrecedenceMapConformLevel OBJECT-TYPE
    SYNTAX      INTEGER(0..2)
    MAX-ACCESS  read-only
    STATUS      current
    DESCRIPTION
      "Conformable level of local-precedence map."
    ::= { hpnicfLocalPrecedenceMapEntry 1 }

  hpnicfLocalPrecedenceMapLocalPrecedenceIndex OBJECT-TYPE
    SYNTAX      INTEGER(0..7)
    MAX-ACCESS  read-write
    STATUS      current
    DESCRIPTION
      "Index of local-precedence."
    ::= { hpnicfLocalPrecedenceMapEntry 2 }

  hpnicfLocalPrecedenceMapCosValue OBJECT-TYPE
    SYNTAX      INTEGER(0..7)
    MAX-ACCESS  read-write
    STATUS      current
    DESCRIPTION
      "COS value."
    ::= { hpnicfLocalPrecedenceMapEntry 3 }
--
--
--
  -- TABLE: hpnicfPortWredTable ---------
  hpnicfPortWredTable OBJECT-TYPE
    SYNTAX SEQUENCE OF HpnicfPortWredEntry
    MAX-ACCESS not-accessible
    STATUS current
    DESCRIPTION
      "The table of PortWred."
    ::= { hpnicfLswQosMibObject 25 }


  hpnicfPortWredEntry OBJECT-TYPE
    SYNTAX HpnicfPortWredEntry
    MAX-ACCESS not-accessible
    STATUS current
    DESCRIPTION
      "Configuration information of port Wred."
    INDEX {
              hpnicfPortWredIfIndex,
              hpnicfPortWredQueueID
          }
    ::= { hpnicfPortWredTable 1 }


    HpnicfPortWredEntry ::=
    SEQUENCE
    {
        hpnicfPortWredIfIndex INTEGER,
        hpnicfPortWredQueueID INTEGER,
        hpnicfPortWredQueueStartLength INTEGER,
        hpnicfPortWredQueueProbability INTEGER
    }

  hpnicfPortWredIfIndex OBJECT-TYPE
    SYNTAX INTEGER
    MAX-ACCESS read-only
    STATUS current
    DESCRIPTION
        "ifIndex of port."
    ::= { hpnicfPortWredEntry 1 }


  hpnicfPortWredQueueID OBJECT-TYPE
    SYNTAX  INTEGER(0..7)
    MAX-ACCESS read-only
    STATUS current
    DESCRIPTION
      "ID of port-Wred queue."
    ::= { hpnicfPortWredEntry 2 }


  hpnicfPortWredQueueStartLength OBJECT-TYPE
    SYNTAX  INTEGER(0..2047)
    MAX-ACCESS  read-write
    STATUS current
    DESCRIPTION
      "Queue length."
    ::= { hpnicfPortWredEntry 3 }


  hpnicfPortWredQueueProbability OBJECT-TYPE
    SYNTAX  INTEGER(0..100)
    MAX-ACCESS  read-write
    STATUS current
    DESCRIPTION
      "Probability."
    ::= { hpnicfPortWredEntry 4 }

-- TABLE: hpnicfMirroringGroupTable ---------
  hpnicfMirroringGroupTable OBJECT-TYPE
    SYNTAX      SEQUENCE OF HpnicfMirroringGroupEntry
    MAX-ACCESS  not-accessible
    STATUS      current
    DESCRIPTION
      "The table of MirrorGroup."
    ::= { hpnicfLswQosMibObject 26 }

  hpnicfMirroringGroupEntry OBJECT-TYPE
    SYNTAX      HpnicfMirroringGroupEntry
    MAX-ACCESS  not-accessible
    STATUS      current
    DESCRIPTION
      "Configuration information of MirrorGroup."
    INDEX  {
    	       hpnicfMirroringGroupID
    	   }
    ::= { hpnicfMirroringGroupTable 1 }

  HpnicfMirroringGroupEntry ::=
    SEQUENCE
    {
      hpnicfMirroringGroupID    INTEGER,
      hpnicfMirroringGroupType    INTEGER,
      hpnicfMirroringGroupStatus    INTEGER,
      hpnicfMirroringGroupRowStatus    RowStatus
    }

   hpnicfMirroringGroupID  OBJECT-TYPE
    SYNTAX      INTEGER(1..20)
    MAX-ACCESS  not-accessible
    STATUS      current
    DESCRIPTION
      "GroupID."
    ::= { hpnicfMirroringGroupEntry 1 }

    hpnicfMirroringGroupType  OBJECT-TYPE
    SYNTAX      INTEGER{local(1),remote-source(2),remote-destination(3)}
    MAX-ACCESS  read-create
    STATUS      current
    DESCRIPTION
      "GroupType."
    ::= { hpnicfMirroringGroupEntry 2 }

    hpnicfMirroringGroupStatus  OBJECT-TYPE
    SYNTAX      INTEGER{active(1),inactive(2)}
    MAX-ACCESS  read-only
    STATUS      current
    DESCRIPTION
      "MirroringGroup status."
    ::= { hpnicfMirroringGroupEntry 3 }

    hpnicfMirroringGroupRowStatus  OBJECT-TYPE
    SYNTAX      RowStatus
    MAX-ACCESS  read-create
    STATUS      current
    DESCRIPTION
      "RowStatus, Now support three status: createAndGo, active, destroy."
    ::= { hpnicfMirroringGroupEntry 4 }

  -- TABLE: hpnicfMirroringGroupMirrorTable ---------
  hpnicfMirroringGroupMirrorTable OBJECT-TYPE
    SYNTAX      SEQUENCE OF HpnicfMirroringGroupMirrorEntry
    MAX-ACCESS  not-accessible
    STATUS      current
    DESCRIPTION
      "MirroringGroup mirroring-port information."
    ::= { hpnicfLswQosMibObject 27 }

  hpnicfMirroringGroupMirrorEntry OBJECT-TYPE
    SYNTAX      HpnicfMirroringGroupMirrorEntry
    MAX-ACCESS  not-accessible
    STATUS      current
    DESCRIPTION
      "MirroringGroup mirroring-port information."
    INDEX {
              hpnicfMirroringGroupID
          }
    ::= { hpnicfMirroringGroupMirrorTable 1 }

  HpnicfMirroringGroupMirrorEntry ::=
    SEQUENCE
    {
      hpnicfMirroringGroupMirrorInboundIfIndexList    OCTET STRING,
      hpnicfMirroringGroupMirrorOutboundIfIndexList    OCTET STRING,
      hpnicfMirroringGroupMirrorRowStatus    RowStatus,
      hpnicfMirroringGroupMirrorInTypeList         OCTET STRING,
      hpnicfMirroringGroupMirrorOutTypeList         OCTET STRING
    }

    hpnicfMirroringGroupMirrorInboundIfIndexList  OBJECT-TYPE
    SYNTAX      OCTET STRING
    MAX-ACCESS  read-create
    STATUS      current
    DESCRIPTION
      "Inbound-Mirror ifIndex(for port) and slot number(for board) list.

      Example A describes the relation between values of
      hpnicfMirroringGroupMirrorInboundIfIndexList and hpnicfMirroringGroupMirrorInTypeList.

      Example A:
      hpnicfMirroringGroupMirrorInboundIfIndexList: '00000002 0C000022 00000007'
      hpnicfMirroringGroupMirrorInTypeList:         '00000002 00000001 00000002'

      Every four octets represent an integer value.
      The first four octets of them should be same. Here the value '00000002'
      indicates there are two inbound mirror sources.
      The following every four octets of hpnicfMirroringGroupMirrorInboundIfIndexList
      indicate an ifIndex or a slot number of mirror source. For '0C000022' and
      '00000007' in the value of hpnicfMirroringGroupMirrorInboundIfIndexList above,
      the corresponding value of hpnicfMirroringGroupMirrorInTypeList is '00000001'
      and '00000002'(00000001 means the mirror source is port, 00000002 means the 
      mirror source is board, the meaning reference the object HpnicfMirrorOrMonitorType), 
      then '0C000022' indicates an ifIndex value 201326626(decimal), and '00000007' 
      indicates a slot with number 7(decimal).

      Values with different types(port/board) should be set in separate set operations.
      If one value with port type and one value with board type are set with same
      hpnicfMirroringGroupID separately, the result of get operation for that entry
      will be like the example A above.
      
      If hpnicfMirroringGroupMirrorInTypeList is not supported, the first four octets
      of hpnicfMirroringGroupMirrorInboundIfIndexList also indicates the number of mirror
      source, but the following octets are values for ifIndex(port type).

      hpnicfMirroringGroupMirrorOutboundIfIndexList and hpnicfMirroringGroupMirrorOutTypeList
      are a pair and have the same relations like hpnicfMirroringGroupMirrorInboundIfIndexList
      and hpnicfMirroringGroupMirrorInTypeList pair.
      "
    ::= { hpnicfMirroringGroupMirrorEntry 1 }

    hpnicfMirroringGroupMirrorOutboundIfIndexList  OBJECT-TYPE
    SYNTAX      OCTET STRING
    MAX-ACCESS  read-create
    STATUS      current
    DESCRIPTION
      "Outbound-Mirror ifIndex and slot number list.
      Please refer to the description of hpnicfMirroringGroupMirrorInboundIfIndexList."
    ::= { hpnicfMirroringGroupMirrorEntry 2 }

    hpnicfMirroringGroupMirrorRowStatus  OBJECT-TYPE
    SYNTAX      RowStatus
    MAX-ACCESS  read-create
    STATUS      current
    DESCRIPTION
      "RowStatus, now support three status: createAndGo, active, destroy."
    ::= { hpnicfMirroringGroupMirrorEntry 3 }
    
    hpnicfMirroringGroupMirrorInTypeList  OBJECT-TYPE
    SYNTAX      OCTET STRING 
    MAX-ACCESS  read-create
    STATUS      current
    DESCRIPTION
      "Inbound-Mirror type list.
      Please refer to the description of hpnicfMirroringGroupMirrorInboundIfIndexList."
      
    ::= { hpnicfMirroringGroupMirrorEntry 4 }
    
    hpnicfMirroringGroupMirrorOutTypeList  OBJECT-TYPE
    SYNTAX      OCTET STRING    
    MAX-ACCESS  read-create
    STATUS      current
    DESCRIPTION
      "Outbound-Mirror type list.
      Please refer to the description of hpnicfMirroringGroupMirrorInboundIfIndexList."
    ::= { hpnicfMirroringGroupMirrorEntry 5 }

  -- TABLE: hpnicfMirroringGroupMonitorTable ---------
  hpnicfMirroringGroupMonitorTable OBJECT-TYPE
    SYNTAX      SEQUENCE OF HpnicfMirroringGroupMonitorEntry
    MAX-ACCESS  not-accessible
    STATUS      current
    DESCRIPTION
      "MirroringGroup monitor-port information."
    ::= { hpnicfLswQosMibObject 28 }

  hpnicfMirroringGroupMonitorEntry OBJECT-TYPE
    SYNTAX      HpnicfMirroringGroupMonitorEntry
    MAX-ACCESS  not-accessible
    STATUS      current
    DESCRIPTION
      "MirroringGroup monitor-port information."
    INDEX {
              hpnicfMirroringGroupID
          }
    ::= { hpnicfMirroringGroupMonitorTable 1 }

  HpnicfMirroringGroupMonitorEntry ::=
    SEQUENCE
    {
      hpnicfMirroringGroupMonitorIfIndex    INTEGER,
      hpnicfMirroringGroupMonitorRowStatus    RowStatus,
      hpnicfMirroringGroupMonitorType HpnicfMirrorOrMonitorType
    }

    hpnicfMirroringGroupMonitorIfIndex  OBJECT-TYPE
    SYNTAX      INTEGER
    MAX-ACCESS  read-create
    STATUS      current
    DESCRIPTION
      "If the monitor destination is port, the value means the ifIndex of this port.
      If the monitor destination is board, the value means the slot number of the
      board. Whether the value means ifIndex or slot number references the object
      hpnicfMirroringGroupMonitorType."
    ::= { hpnicfMirroringGroupMonitorEntry 1 }

    hpnicfMirroringGroupMonitorRowStatus  OBJECT-TYPE
    SYNTAX      RowStatus
    MAX-ACCESS  read-create
    STATUS      current
    DESCRIPTION
      "RowStatus, now support three status: createAndGo, active, destroy."
    ::= { hpnicfMirroringGroupMonitorEntry 2 }

    hpnicfMirroringGroupMonitorType  OBJECT-TYPE
    SYNTAX      HpnicfMirrorOrMonitorType
    MAX-ACCESS  read-create
    STATUS      current
    DESCRIPTION
      "Specify whether the monitor destination is port or board. If this object is
      not supported, then the value of hpnicfMirroringGroupMonitorIfIndex means ifIndex."
    ::= { hpnicfMirroringGroupMonitorEntry 3 }

  -- TABLE: hpnicfMirroringGroupReflectorTable ---------
  hpnicfMirroringGroupReflectorTable OBJECT-TYPE
    SYNTAX      SEQUENCE OF HpnicfMirroringGroupReflectorEntry
    MAX-ACCESS  not-accessible
    STATUS      current
    DESCRIPTION
      "MirroringGroup reflector-port information."
    ::= { hpnicfLswQosMibObject 29 }

  hpnicfMirroringGroupReflectorEntry OBJECT-TYPE
    SYNTAX      HpnicfMirroringGroupReflectorEntry
    MAX-ACCESS  not-accessible
    STATUS      current
    DESCRIPTION
      "MirroringGroup reflector-port information."
    INDEX {
              hpnicfMirroringGroupID
          }
    ::= { hpnicfMirroringGroupReflectorTable 1 }

  HpnicfMirroringGroupReflectorEntry ::=
    SEQUENCE
    {
      hpnicfMirroringGroupReflectorIfIndex    INTEGER,
      hpnicfMirroringGroupReflectorRowStatus    RowStatus
    }

  hpnicfMirroringGroupReflectorIfIndex   OBJECT-TYPE
    SYNTAX      INTEGER
    MAX-ACCESS  read-create
    STATUS      current
    DESCRIPTION
      "Only valid for remote-source MirroringGroup."
    ::= { hpnicfMirroringGroupReflectorEntry 1 }

  hpnicfMirroringGroupReflectorRowStatus  OBJECT-TYPE
    SYNTAX      RowStatus
    MAX-ACCESS  read-create
    STATUS      current
    DESCRIPTION
      "RowStatus, now support three status: createAndGo, active, destroy."
    ::= { hpnicfMirroringGroupReflectorEntry 2 }

  -- TABLE: hpnicfMirroringGroupRprobeVlanTable ---------
  hpnicfMirroringGroupRprobeVlanTable OBJECT-TYPE
    SYNTAX      SEQUENCE OF HpnicfMirroringGroupRprobeVlanEntry
    MAX-ACCESS  not-accessible
    STATUS      current
    DESCRIPTION
      "MirroringGroup rprobe-vlan information."
    ::= { hpnicfLswQosMibObject 30 }

  hpnicfMirroringGroupRprobeVlanEntry OBJECT-TYPE
    SYNTAX      HpnicfMirroringGroupRprobeVlanEntry
    MAX-ACCESS  not-accessible
    STATUS      current
    DESCRIPTION
      "MirroringGroup rprobe-vlan information."
    INDEX {
              hpnicfMirroringGroupID
          }
    ::= { hpnicfMirroringGroupRprobeVlanTable 1 }

  HpnicfMirroringGroupRprobeVlanEntry ::=
    SEQUENCE
    {
      hpnicfMirroringGroupRprobeVlanID    INTEGER,
      hpnicfMirroringGroupRprobeVlanRowStatus    RowStatus
    }

  hpnicfMirroringGroupRprobeVlanID   OBJECT-TYPE
    SYNTAX      INTEGER (0..4094)
    MAX-ACCESS  read-create
    STATUS      current
    DESCRIPTION
      "Remote-Probe vlanID.
      0 is invalid value.
      Only valid for remote-source and remote-destination MirroringGroup."
    ::= { hpnicfMirroringGroupRprobeVlanEntry 1 }

  hpnicfMirroringGroupRprobeVlanRowStatus  OBJECT-TYPE
    SYNTAX      RowStatus
    MAX-ACCESS  read-create
    STATUS      current
    DESCRIPTION
      "RowStatus, now support three status: createAndGo, active, destroy."
    ::= { hpnicfMirroringGroupRprobeVlanEntry 2 }

  hpnicfMirroringGroupMirrorMacTable OBJECT-TYPE
    SYNTAX      SEQUENCE OF HpnicfMirroringGroupMirrorMacEntry
    MAX-ACCESS  not-accessible
    STATUS      current
    DESCRIPTION
        "MirroringGroup MAC information."
    ::= { hpnicfLswQosMibObject 31 }

  hpnicfMirroringGroupMirrorMacEntry OBJECT-TYPE
    SYNTAX      HpnicfMirroringGroupMirrorMacEntry
    MAX-ACCESS  not-accessible
    STATUS      current
    DESCRIPTION
        "MirroringGroup MAC information."
    INDEX {
           hpnicfMirroringGroupID,
           hpnicfMirroringGroupMirrorMacSeq
          }
    ::= { hpnicfMirroringGroupMirrorMacTable 1 }

  HpnicfMirroringGroupMirrorMacEntry ::=
    SEQUENCE
    {
       hpnicfMirroringGroupMirrorMacSeq  Integer32,
       hpnicfMirroringGroupMirrorMac  MacAddress,
       hpnicfMirrorMacVlanID   Integer32,
       hpnicfMirroringGroupMirroMacStatus RowStatus
    }

  hpnicfMirroringGroupMirrorMacSeq   OBJECT-TYPE
    SYNTAX      Integer32
    MAX-ACCESS  not-accessible
    STATUS      current
    DESCRIPTION
          "The sequence MAC number of the same group."
    ::= { hpnicfMirroringGroupMirrorMacEntry 1 }

  hpnicfMirroringGroupMirrorMac   OBJECT-TYPE
    SYNTAX      MacAddress
    MAX-ACCESS  read-create
    STATUS      current
    DESCRIPTION
          "The MAC address of the MirroringGroup."
    ::= { hpnicfMirroringGroupMirrorMacEntry 2 }

  hpnicfMirrorMacVlanID   OBJECT-TYPE
    SYNTAX      Integer32(0..4094)
    MAX-ACCESS  read-create
    STATUS      current
    DESCRIPTION
          "The vlan ID of MAC address ."
    ::= { hpnicfMirroringGroupMirrorMacEntry 3 }

  hpnicfMirroringGroupMirroMacStatus   OBJECT-TYPE
    SYNTAX      RowStatus
    MAX-ACCESS  read-create
    STATUS      current
    DESCRIPTION
          "The status of this conceptual row."
    ::= { hpnicfMirroringGroupMirrorMacEntry 4 }

  hpnicfMirroringGroupMirrorVlanTable OBJECT-TYPE
    SYNTAX      SEQUENCE OF HpnicfMirroringGroupMirrorVlanEntry
    MAX-ACCESS  not-accessible
    STATUS      current
    DESCRIPTION
          "MirroringGroup Vlan Information."
    ::= { hpnicfLswQosMibObject 32 }

  hpnicfMirroringGroupMirrorVlanEntry OBJECT-TYPE
    SYNTAX      HpnicfMirroringGroupMirrorVlanEntry
    MAX-ACCESS  not-accessible
    STATUS      current
    DESCRIPTION
          "MirroringGroup Vlan Information."
    INDEX {
           hpnicfMirroringGroupID,
           hpnicfMirroringGroupMirrorVlanSeq
           }
    ::= { hpnicfMirroringGroupMirrorVlanTable 1 }

  HpnicfMirroringGroupMirrorVlanEntry ::=
    SEQUENCE
    {
       hpnicfMirroringGroupMirrorVlanSeq Integer32,
       hpnicfMirroringGroupMirrorVlanID Integer32,
       hpnicfMirroringGroupMirrorVlanDirection INTEGER,
       hpnicfMirroringGroupMirroVlanStatus RowStatus
    }

  hpnicfMirroringGroupMirrorVlanSeq   OBJECT-TYPE
    SYNTAX      Integer32
    MAX-ACCESS  not-accessible
    STATUS      current
    DESCRIPTION
          "The sequence vlan number of the same group."
    ::= { hpnicfMirroringGroupMirrorVlanEntry  1 }

  hpnicfMirroringGroupMirrorVlanID   OBJECT-TYPE
    SYNTAX      Integer32(0..4094)
    MAX-ACCESS  read-create
    STATUS      current
    DESCRIPTION
          "The vlan ID of MirroringGroup."
    ::= { hpnicfMirroringGroupMirrorVlanEntry  2 }

  hpnicfMirroringGroupMirrorVlanDirection   OBJECT-TYPE
    SYNTAX      INTEGER
    {
       inbound(1),
       outbound(2),
       both(3)
    }
    MAX-ACCESS  read-create
    STATUS      current
    DESCRIPTION
          "The vlan direction of MirroringGroup."
    ::= { hpnicfMirroringGroupMirrorVlanEntry  3 }

  hpnicfMirroringGroupMirroVlanStatus   OBJECT-TYPE
    SYNTAX      RowStatus
    MAX-ACCESS  read-create
    STATUS      current
    DESCRIPTION
          "The status of this conceptual row."
    ::= { hpnicfMirroringGroupMirrorVlanEntry  4 }

  hpnicfPortTrustTable OBJECT-TYPE
    SYNTAX      SEQUENCE OF HpnicfPortTrustEntry
    MAX-ACCESS  not-accessible
    STATUS      current
    DESCRIPTION
          "Port trust information."
    ::= { hpnicfLswQosMibObject 33 }

  hpnicfPortTrustEntry OBJECT-TYPE
    SYNTAX      HpnicfPortTrustEntry
    MAX-ACCESS  not-accessible
    STATUS      current
    DESCRIPTION
          "Port trust information."
    INDEX  {
             hpnicfPortTrustIfIndex
           }
     ::= { hpnicfPortTrustTable 1 }

  HpnicfPortTrustEntry ::=
    SEQUENCE
    {
       hpnicfPortTrustIfIndex Integer32,
       hpnicfPortTrustTrustType INTEGER,
       hpnicfPortTrustOvercastType INTEGER,
       hpnicfPortTrustReset INTEGER
    }

  hpnicfPortTrustIfIndex   OBJECT-TYPE
    SYNTAX      Integer32
    MAX-ACCESS  not-accessible
    STATUS      current
    DESCRIPTION
          "ifIndex of the port which port trust is configured."
    ::= { hpnicfPortTrustEntry  1 }

  hpnicfPortTrustTrustType   OBJECT-TYPE
    SYNTAX      INTEGER
    {
        port(1),  -- port untrust
        cos(2),   -- port trust cos
        dscp(3)   -- port trust dscp
    }
    MAX-ACCESS  read-write
    STATUS      current
    DESCRIPTION
          "Trust type of port trust."
    DEFVAL      { port }
    ::= { hpnicfPortTrustEntry  2 }

  hpnicfPortTrustOvercastType   OBJECT-TYPE
    SYNTAX      INTEGER
    {
        noOvercast(1),
        overcastDSCP(2),
        overcastCOS(3)
    }
    MAX-ACCESS  read-write
    STATUS      current
    DESCRIPTION
          "Overcast type of port trust."
    DEFVAL      { noOvercast }
    ::= { hpnicfPortTrustEntry  3 }

    hpnicfPortTrustReset   OBJECT-TYPE
    SYNTAX      INTEGER
    {
       reset(1)
    }
    MAX-ACCESS  read-write
    STATUS      current
    DESCRIPTION
          "This object is used to reset port trust to default value.
          Read operation is meaningless."
    ::= { hpnicfPortTrustEntry  4 }

  hpnicfRemarkVlanIDTable OBJECT-TYPE
    SYNTAX      SEQUENCE OF HpnicfRemarkVlanIDEntry
    MAX-ACCESS  not-accessible
    STATUS      current
    DESCRIPTION
          "Remark vlan ID information."
    ::= { hpnicfLswQosMibObject 34 }

  hpnicfRemarkVlanIDEntry OBJECT-TYPE
    SYNTAX      HpnicfRemarkVlanIDEntry
    MAX-ACCESS  not-accessible
    STATUS      current
    DESCRIPTION
          "Remark vlan ID information."
    INDEX {
              hpnicfRemarkVlanIDAclIndex,
              hpnicfRemarkVlanIDIfIndex,
              hpnicfRemarkVlanIDVlanID,
              hpnicfRemarkVlanIDDirection
          }
    ::= { hpnicfRemarkVlanIDTable 1 }

    HpnicfRemarkVlanIDEntry ::=
    SEQUENCE
    {
       hpnicfRemarkVlanIDAclIndex         Integer32,
       hpnicfRemarkVlanIDIfIndex          Integer32,
       hpnicfRemarkVlanIDVlanID           Integer32,
       hpnicfRemarkVlanIDDirection        INTEGER,
       hpnicfRemarkVlanIDUserAclNum       Integer32,
       hpnicfRemarkVlanIDUserAclRule      Integer32,
       hpnicfRemarkVlanIDIpAclNum         Integer32,
       hpnicfRemarkVlanIDIpAclRule        Integer32,
       hpnicfRemarkVlanIDLinkAclNum       Integer32,
       hpnicfRemarkVlanIDLinkAclRule      Integer32,
       hpnicfRemarkVlanIDRemarkVlanID     Integer32,
       hpnicfRemarkVlanIDPacketType       INTEGER,
       hpnicfRemarkVlanIDRowStatus        RowStatus
    }

  hpnicfRemarkVlanIDAclIndex   OBJECT-TYPE
    SYNTAX      Integer32(0..2999)
    MAX-ACCESS  not-accessible
    STATUS      current
    DESCRIPTION
          "Action identifier, acl index."
    ::= { hpnicfRemarkVlanIDEntry  1 }

  hpnicfRemarkVlanIDIfIndex   OBJECT-TYPE
    SYNTAX      Integer32
    MAX-ACCESS  not-accessible
    STATUS      current
    DESCRIPTION
          "Action identifier, ifIndex."
    ::= { hpnicfRemarkVlanIDEntry  2 }

  hpnicfRemarkVlanIDVlanID   OBJECT-TYPE
    SYNTAX      Integer32(0..4094)
    MAX-ACCESS  not-accessible
    STATUS      current
    DESCRIPTION
          "Action identifier, vlan ID."
    ::= { hpnicfRemarkVlanIDEntry  3 }

  hpnicfRemarkVlanIDDirection   OBJECT-TYPE
    SYNTAX      INTEGER
    {
       invalid(0),
       input(1),
       output(2)
    }
    MAX-ACCESS  not-accessible
    STATUS      current
    DESCRIPTION
          "Action identifier, direction of data stream."
    ::= { hpnicfRemarkVlanIDEntry  4 }

  hpnicfRemarkVlanIDUserAclNum   OBJECT-TYPE
    SYNTAX      Integer32(0|5000..5999|10000..12999)
    MAX-ACCESS  read-create
    STATUS      current
    DESCRIPTION
          "The number of the user acl."
    ::= { hpnicfRemarkVlanIDEntry  5 }

  hpnicfRemarkVlanIDUserAclRule   OBJECT-TYPE
    SYNTAX      Integer32(0..65535)
    MAX-ACCESS  read-create
    STATUS      current
    DESCRIPTION
          "The subitem of the user acl."
    ::= { hpnicfRemarkVlanIDEntry  6 }

  hpnicfRemarkVlanIDIpAclNum   OBJECT-TYPE
    SYNTAX      Integer32(0|2000..3999|10000..12999)
    MAX-ACCESS  read-create
    STATUS      current
    DESCRIPTION
          "The num of the IP acl."
    ::= { hpnicfRemarkVlanIDEntry  7 }

  hpnicfRemarkVlanIDIpAclRule   OBJECT-TYPE
    SYNTAX      Integer32(0..65535)
    MAX-ACCESS  read-create
    STATUS      current
    DESCRIPTION
          "The subitem of the IP acl."
    ::= { hpnicfRemarkVlanIDEntry  8 }

  hpnicfRemarkVlanIDLinkAclNum   OBJECT-TYPE
    SYNTAX      Integer32(0|4000..4999|10000..12999)
    MAX-ACCESS  read-create
    STATUS      current
    DESCRIPTION
          "The num of the link acl."
    ::= { hpnicfRemarkVlanIDEntry  9 }

  hpnicfRemarkVlanIDLinkAclRule   OBJECT-TYPE
    SYNTAX      Integer32(0..65535)
    MAX-ACCESS  read-create
    STATUS      current
    DESCRIPTION
          "The subitem of the link acl."
    ::= { hpnicfRemarkVlanIDEntry  10 }

  hpnicfRemarkVlanIDRemarkVlanID   OBJECT-TYPE
    SYNTAX      Integer32(0..4094)
    MAX-ACCESS  read-create
    STATUS      current
    DESCRIPTION
          "Remark vlan ID."
    ::= { hpnicfRemarkVlanIDEntry 11 }

  hpnicfRemarkVlanIDPacketType   OBJECT-TYPE
    SYNTAX      INTEGER
    {
        all(1),
        tagged(2),
        untagged(3)
    }
    MAX-ACCESS  read-create
    STATUS      current
    DESCRIPTION
          "Packet type of the remarked vlan ID."
    ::= { hpnicfRemarkVlanIDEntry 12 }

  hpnicfRemarkVlanIDRowStatus   OBJECT-TYPE
    SYNTAX      RowStatus
    MAX-ACCESS  read-create
    STATUS      current
    DESCRIPTION
          "The status of this conceptual row. "
    ::= { hpnicfRemarkVlanIDEntry 13 }

  hpnicfCosToDscpMapTable OBJECT-TYPE
    SYNTAX      SEQUENCE OF HpnicfCosToDscpMapEntry
    MAX-ACCESS  not-accessible
    STATUS      current
    DESCRIPTION
          "COS to DSCP map information."
    ::= { hpnicfLswQosMibObject 35 }

  hpnicfCosToDscpMapEntry OBJECT-TYPE
    SYNTAX      HpnicfCosToDscpMapEntry
    MAX-ACCESS  not-accessible
    STATUS      current
    DESCRIPTION
          "COS to DSCP map information."
    INDEX {
             hpnicfCosToDscpMapCosIndex
          }
    ::= { hpnicfCosToDscpMapTable 1 }

  HpnicfCosToDscpMapEntry ::=
    SEQUENCE
    {
      hpnicfCosToDscpMapCosIndex     Integer32,
      hpnicfCosToDscpMapDscpValue    Integer32,
      hpnicfCosToDscpMapReSet        INTEGER
    }

  hpnicfCosToDscpMapCosIndex   OBJECT-TYPE
    SYNTAX    Integer32(0..7)
    MAX-ACCESS  not-accessible
    STATUS      current
    DESCRIPTION
          "COS index of COS to DSCP map."
    ::= { hpnicfCosToDscpMapEntry 1 }

  hpnicfCosToDscpMapDscpValue   OBJECT-TYPE
    SYNTAX      Integer32(0..63)
    MAX-ACCESS  read-write
    STATUS      current
    DESCRIPTION
          "DSCP value of COS to DSCP map."
    ::= { hpnicfCosToDscpMapEntry 2 }

  hpnicfCosToDscpMapReSet   OBJECT-TYPE
    SYNTAX    INTEGER
    {
        reset(1)
    }
    MAX-ACCESS  read-write
    STATUS      current
    DESCRIPTION
          "This object is used to reset COS to DSCP map to default value.
          Read operation is meaningless."
    ::= { hpnicfCosToDscpMapEntry 3 }

  hpnicfDscpToLocalPreMapTable OBJECT-TYPE
    SYNTAX      SEQUENCE OF HpnicfDscpToLocalPreMapEntry
    MAX-ACCESS  not-accessible
    STATUS      current
    DESCRIPTION
          "DSCP to Local-precedence map information."
    ::= { hpnicfLswQosMibObject 36 }

  hpnicfDscpToLocalPreMapEntry OBJECT-TYPE
    SYNTAX      HpnicfDscpToLocalPreMapEntry
    MAX-ACCESS  not-accessible
    STATUS      current
    DESCRIPTION
          "DSCP to Local-precedence map information."
    INDEX {
             hpnicfDscpToLocalPreMapDscpIndex
          }
    ::= { hpnicfDscpToLocalPreMapTable 1 }

  HpnicfDscpToLocalPreMapEntry ::=
    SEQUENCE
    {
      hpnicfDscpToLocalPreMapDscpIndex     Integer32,
      hpnicfDscpToLocalPreMapLocalPreVal   Integer32,
      hpnicfDscpToLocalPreMapReset         INTEGER
    }

  hpnicfDscpToLocalPreMapDscpIndex   OBJECT-TYPE
    SYNTAX      Integer32(0..63)
    MAX-ACCESS  not-accessible
    STATUS      current
    DESCRIPTION
          "DSCP Index of DSCP to Local-precedence map."
    ::= { hpnicfDscpToLocalPreMapEntry 1 }

  hpnicfDscpToLocalPreMapLocalPreVal   OBJECT-TYPE
    SYNTAX      Integer32(0..7)
    MAX-ACCESS  read-write
    STATUS      current
    DESCRIPTION
          "Local-precedence value of DSCP to Local-precedence map."
    ::= { hpnicfDscpToLocalPreMapEntry 2 }

  hpnicfDscpToLocalPreMapReset   OBJECT-TYPE
    SYNTAX      INTEGER
    {
       reset(1)
    }
    MAX-ACCESS  read-write
    STATUS      current
    DESCRIPTION
          "This object is used to reset DSCP to Local-precedence map to default value.
           Read operation is meaningless."
    ::= { hpnicfDscpToLocalPreMapEntry 3 }

  hpnicfDscpToDropPreMapTable OBJECT-TYPE
    SYNTAX      SEQUENCE OF HpnicfDscpToDropPreMapEntry
    MAX-ACCESS  not-accessible
    STATUS      current
    DESCRIPTION
          "DSCP to Drop-precedence map information."
    ::= { hpnicfLswQosMibObject 37 }

  hpnicfDscpToDropPreMapEntry OBJECT-TYPE
    SYNTAX      HpnicfDscpToDropPreMapEntry
    MAX-ACCESS  not-accessible
    STATUS      current
    DESCRIPTION
          "DSCP to Drop-precedence map information."
    INDEX {
             hpnicfDscpToDropPreMapDscpIndex
          }
    ::= { hpnicfDscpToDropPreMapTable 1 }

  HpnicfDscpToDropPreMapEntry ::=
    SEQUENCE
    {
      hpnicfDscpToDropPreMapDscpIndex    Integer32,
      hpnicfDscpToDropPreMapDropPreVal   Integer32,
      hpnicfDscpToDropPreMapReset        INTEGER
    }

  hpnicfDscpToDropPreMapDscpIndex   OBJECT-TYPE
    SYNTAX      Integer32(0..63)
    MAX-ACCESS  not-accessible
    STATUS      current
    DESCRIPTION
          "DSCP Index of DSCP to Drop-precedence map."
    ::= { hpnicfDscpToDropPreMapEntry 1 }

  hpnicfDscpToDropPreMapDropPreVal   OBJECT-TYPE
    SYNTAX      Integer32(0..2)
    MAX-ACCESS  read-write
    STATUS      current
    DESCRIPTION
          "Drop-precedence value of DSCP to Drop-precedence map."
    ::= { hpnicfDscpToDropPreMapEntry 2 }

  hpnicfDscpToDropPreMapReset   OBJECT-TYPE
    SYNTAX      INTEGER
    {
       reset(1)
    }
    MAX-ACCESS  read-write
    STATUS      current
    DESCRIPTION
          "This object is used to reset DSCP to Drop-precedence map to default value.
          Read operation is meaningless."
    ::= { hpnicfDscpToDropPreMapEntry 3 }

  hpnicfDscpToCosMapTable OBJECT-TYPE
    SYNTAX      SEQUENCE OF HpnicfDscpToCosMapEntry
    MAX-ACCESS  not-accessible
    STATUS      current
    DESCRIPTION
          "DSCP to COS map information."
    ::= { hpnicfLswQosMibObject 38 }

  hpnicfDscpToCosMapEntry OBJECT-TYPE
    SYNTAX      HpnicfDscpToCosMapEntry
    MAX-ACCESS  not-accessible
    STATUS      current
    DESCRIPTION
          "DSCP to COS map information."
    INDEX {
             hpnicfDscpToCosMapDscpIndex
          }
    ::= { hpnicfDscpToCosMapTable 1 }

  HpnicfDscpToCosMapEntry ::=
    SEQUENCE
    {
      hpnicfDscpToCosMapDscpIndex   Integer32,
      hpnicfDscpToCosMapCosValue    Integer32,
      hpnicfDscpToCosMapReset       INTEGER
    }

  hpnicfDscpToCosMapDscpIndex   OBJECT-TYPE
    SYNTAX      Integer32(0..63)
    MAX-ACCESS  not-accessible
    STATUS      current
    DESCRIPTION
          "DSCP index of DSCP to COS map."
    ::= { hpnicfDscpToCosMapEntry 1 }

  hpnicfDscpToCosMapCosValue   OBJECT-TYPE
    SYNTAX      Integer32(0..7)
    MAX-ACCESS  read-write
    STATUS      current
    DESCRIPTION
          "COS value of DSCP to COS map."
    ::= { hpnicfDscpToCosMapEntry 2 }

  hpnicfDscpToCosMapReset   OBJECT-TYPE
    SYNTAX      INTEGER
    {
       reset(1)
    }
    MAX-ACCESS  read-write
    STATUS      current
    DESCRIPTION
          "This object is used to reset DSCP to COS map to default value.
          Read operation is meaningless."
    ::= { hpnicfDscpToCosMapEntry 3 }

  hpnicfDscpToDscpMapTable OBJECT-TYPE
    SYNTAX      SEQUENCE OF HpnicfDscpToDscpMapEntry
    MAX-ACCESS  not-accessible
    STATUS      current
    DESCRIPTION
          "DSCP to DSCP map information."
    ::= { hpnicfLswQosMibObject 39 }

    hpnicfDscpToDscpMapEntry OBJECT-TYPE
    SYNTAX      HpnicfDscpToDscpMapEntry
    MAX-ACCESS  not-accessible
    STATUS      current
    DESCRIPTION
          "DSCP to DSCP map information."
    INDEX {
             hpnicfDscpToDscpMapDscpIndex
          }
    ::= { hpnicfDscpToDscpMapTable 1 }

  HpnicfDscpToDscpMapEntry ::=
    SEQUENCE
    {
      hpnicfDscpToDscpMapDscpIndex  Integer32,
      hpnicfDscpToDscpMapDscpValue  Integer32,
      hpnicfDscpToDscpMapReset    INTEGER
    }

  hpnicfDscpToDscpMapDscpIndex   OBJECT-TYPE
    SYNTAX      Integer32(0..63)
    MAX-ACCESS  not-accessible
    STATUS      current
    DESCRIPTION
          "DSCP index of DSCP to DSCP map."
    ::= { hpnicfDscpToDscpMapEntry 1 }

  hpnicfDscpToDscpMapDscpValue   OBJECT-TYPE
    SYNTAX      Integer32(0..63)
    MAX-ACCESS  read-write
    STATUS      current
    DESCRIPTION
          "DSCP value of DSCP to DSCP map."
    ::= { hpnicfDscpToDscpMapEntry 2 }

  hpnicfDscpToDscpMapReset    OBJECT-TYPE
    SYNTAX      INTEGER
    {
       reset(1)
    }
    MAX-ACCESS  read-write
    STATUS      current
    DESCRIPTION
          "This object is used to reset DSCP to DSCP map to default value.
          Read operation is meaningless."
    ::= { hpnicfDscpToDscpMapEntry 3 }

END
