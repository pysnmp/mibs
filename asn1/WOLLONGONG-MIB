WOLLONGONG-MIB DEFINITIONS ::= BEGIN

-- Title:	WOLLONGONG MIB
-- Date:	April 13, 1990
-- By:		Edward Alcoff/TWG <oldera@twg.com>

IMPORTS
	enterprises, TimeTicks, Counter
		FROM RFC1065-SMI
		OBJECT-TYPE FROM SNMPv2-SMI;

wollongong	OBJECT IDENTIFIER ::= { enterprises 6 }

model		OBJECT IDENTIFIER ::=			{  wollongong  1}
vms4		OBJECT IDENTIFIER ::=			{  model 1  }
vms5		OBJECT IDENTIFIER ::=			{  model 2  }
sun3		OBJECT IDENTIFIER ::=			{  model 3  }
sysV386		OBJECT IDENTIFIER ::=			{  model 4  }
att3B2		OBJECT IDENTIFIER ::=			{  model 5  }
ncr		OBJECT IDENTIFIER ::=			{  model 6  }
dos		OBJECT IDENTIFIER ::=			{  model 7  }
dostcp		OBJECT IDENTIFIER ::=			{  dos 1  }
dosroute	OBJECT IDENTIFIER ::=			{  dos 2  }
dosruntime	OBJECT IDENTIFIER ::=			{  dos 3  }
os2		OBJECT IDENTIFIER ::=			{  model 8  }
mac		OBJECT IDENTIFIER ::=			{  model 9  }
proxy		OBJECT IDENTIFIER ::=			{  wollongong 2  }

lANbridgeTab	OBJECT-TYPE
	SYNTAX	SEQUENCE OF LANbridgeEnt
	ACCESS	read-write
	STATUS	optional
DESCRIPTION ""
	::=	{ proxy 1 }


lANbridgeEnt	OBJECT-TYPE
	SYNTAX	LANbridgeEnt
	ACCESS	read-write
	STATUS	optional
DESCRIPTION ""
	::=	{ lANbridgeTab 1 }


	LANbridgeEnt  ::=  SEQUENCE  {
		twgLBUpTime
			TimeTicks,
		twgLBNeigh1
			OCTET STRING,
		twgLBNeigh2
			OCTET STRING,
		twgLBInFrames1
			Counter,
		twgLBInFrames2
			Counter,
		twgLBOutFrames1
			Counter,
		twgLBOutFrames2
			Counter,
		twgLBBadFrames1
			Counter,
		twgLBBadFrames2
			Counter,
		twgLBCollisions
			Counter,
		twgLBInOwnFrames1
			Counter,
		twgLBInOwnFrames2	
			Counter,
		twgLBOutOwnFrames1
			Counter,
		twgLBOutOwnFrames2
			Counter,
		twgLBReboot
			INTEGER,
		twgLBStatus
			INTEGER,
		twgLBState1
			INTEGER,
		twgLBState2
			INTEGER,
		twgLBAddr1
			OCTET STRING
     }

twgLBUpTime	OBJECT-TYPE
	SYNTAX	TimeTicks
	ACCESS	read-only
	STATUS	optional
DESCRIPTION ""
	::=	{ lANbridgeEnt 1 }

twgLBNeigh1	OBJECT-TYPE
	SYNTAX	OCTET STRING
	ACCESS	read-only
	STATUS	optional
DESCRIPTION ""
	::=	{ lANbridgeEnt 2 }

twgLBNeigh2	OBJECT-TYPE
	SYNTAX	OCTET STRING
	ACCESS	read-only
	STATUS	optional
DESCRIPTION ""
	::=	{ lANbridgeEnt 3 }

twgLBInFrames1	OBJECT-TYPE
	SYNTAX	Counter
	ACCESS	read-only
	STATUS	optional
DESCRIPTION ""
	::=	{ lANbridgeEnt 4 }

twgLBInFrames2	OBJECT-TYPE
	SYNTAX	Counter
	ACCESS	read-only
	STATUS	optional
DESCRIPTION ""
	::=	{ lANbridgeEnt 5 }

twgLBOutFrames1	OBJECT-TYPE
	SYNTAX	Counter
	ACCESS	read-only
	STATUS	optional
DESCRIPTION ""
	::=	{ lANbridgeEnt 6 }

twgLBOutFrames2	OBJECT-TYPE
	SYNTAX	Counter
	ACCESS	read-only
	STATUS	optional
DESCRIPTION ""
	::=	{ lANbridgeEnt 7 }

twgLBBadFrames1	OBJECT-TYPE
	SYNTAX	Counter
	ACCESS	read-only
	STATUS	optional
DESCRIPTION ""
	::=	{ lANbridgeEnt 8 }

twgLBBadFrames2	OBJECT-TYPE
	SYNTAX	Counter
	ACCESS	read-only
	STATUS	optional
DESCRIPTION ""
	::=	{ lANbridgeEnt 9 }

twgLBCollisions	OBJECT-TYPE
	SYNTAX	Counter
	ACCESS	read-only
	STATUS	optional
DESCRIPTION ""
	::=	{ lANbridgeEnt 10 }

twgLBInOwnFrames1	OBJECT-TYPE
	SYNTAX	Counter
	ACCESS	read-only
	STATUS	optional
DESCRIPTION ""
	::=	{ lANbridgeEnt 11 }

twgLBInOwnFrames2		OBJECT-TYPE
	SYNTAX	Counter
	ACCESS	read-only
	STATUS	optional
DESCRIPTION ""
	::=	{ lANbridgeEnt 12 }

twgLBOutOwnFrames1	OBJECT-TYPE
	SYNTAX	Counter
	ACCESS	read-only
	STATUS	optional
DESCRIPTION ""
	::=	{ lANbridgeEnt 13 }

twgLBOutOwnFrames2	OBJECT-TYPE
	SYNTAX	Counter
	ACCESS	read-only
	STATUS	optional
DESCRIPTION ""
	::=	{ lANbridgeEnt 14 }

twgLBReboot	OBJECT-TYPE
	SYNTAX	INTEGER
	ACCESS	read-write
	STATUS	optional
DESCRIPTION ""
	::=	{ lANbridgeEnt 15 }

twgLBStatus	OBJECT-TYPE
	SYNTAX	INTEGER
	ACCESS	read-only
	STATUS	optional
DESCRIPTION ""
	::=	{ lANbridgeEnt 16 }

twgLBState1	OBJECT-TYPE
	SYNTAX	INTEGER
	ACCESS	read-only
	STATUS	optional
DESCRIPTION ""
	::=	{ lANbridgeEnt 17 }

twgLBState2	OBJECT-TYPE
	SYNTAX	INTEGER
	ACCESS	read-only
	STATUS	optional
DESCRIPTION ""
	::=	{ lANbridgeEnt 18 }

twgLBAddr1	OBJECT-TYPE
	SYNTAX	OCTET STRING
	ACCESS	read-only
	STATUS	optional
DESCRIPTION ""
	::=	{ lANbridgeEnt 19 }

END
