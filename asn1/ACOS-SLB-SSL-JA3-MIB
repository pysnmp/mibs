ACOS-SLB-SSL-JA3-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		slbSslJa3Module MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "slbSslJa3Module OID for ACOS"
				::=  {  acosSchema 314 }

sslJa3		 OBJECT IDENTIFIER ::= { slbSslJa3Module 1}

sslJa3OperRecordTable OBJECT-TYPE
	 SYNTAX SEQUENCE OF SslJa3OperRecordEntry
	 MAX-ACCESS not-accessible
	 STATUS current
	 DESCRIPTION
		 "Show SSL JA3 from object 'slb.ssl-ja3'"
	::= {sslJa3 2}

sslJa3OperRecordEntry OBJECT-TYPE
	SYNTAX SslJa3OperRecordEntry
	MAX-ACCESS not-accessible
	STATUS current
	DESCRIPTION
		"The sslJa3OperRecord entry:record"
	INDEX {
		sslJa3OperRecordSlotId,
		sslJa3OperRecordRecordListId
	}
	::= { sslJa3OperRecordTable 1}

SslJa3OperRecordEntry ::=
	SEQUENCE {
		sslJa3OperRecordSlotId Integer32,
		sslJa3OperRecordRecordListId Integer32,
		sslJa3OperRecordAddrV4	DisplayString,
		sslJa3OperRecordAddrV6	DisplayString,
		sslJa3OperRecordAmount	Integer32
	}

sslJa3OperRecordSlotId OBJECT-TYPE
	SYNTAX Integer32
	MAX-ACCESS read-only
	STATUS current
	DESCRIPTION
		""
	::= { sslJa3OperRecordEntry 1}

sslJa3OperRecordRecordListId OBJECT-TYPE
	SYNTAX Integer32
	MAX-ACCESS read-only
	STATUS current
	DESCRIPTION
		""
	::= { sslJa3OperRecordEntry 2}

sslJa3OperRecordAddrV4 OBJECT-TYPE
	SYNTAX DisplayString
	MAX-ACCESS read-only
	STATUS current
	DESCRIPTION
		"addr-v4"
	::= { sslJa3OperRecordEntry 3}

sslJa3OperRecordAddrV6 OBJECT-TYPE
	SYNTAX DisplayString
	MAX-ACCESS read-only
	STATUS current
	DESCRIPTION
		"addr-v6"
	::= { sslJa3OperRecordEntry 4}

sslJa3OperRecordAmount OBJECT-TYPE
	SYNTAX Integer32
	MAX-ACCESS read-only
	STATUS current
	DESCRIPTION
		"amount"
	::= { sslJa3OperRecordEntry 5}

END
