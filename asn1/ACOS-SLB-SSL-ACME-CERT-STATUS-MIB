ACOS-SLB-SSL-ACME-CERT-STATUS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		slbSslAcmeCertStatusModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "slbSslAcmeCertStatusModule OID for ACOS"
				::=  {  acosSchema 297 }

sslAcmeCertStatus		 OBJECT IDENTIFIER ::= { slbSslAcmeCertStatusModule 1}

sslAcmeCertStatusOperAcmeCertsTable OBJECT-TYPE
	 SYNTAX SEQUENCE OF SslAcmeCertStatusOperAcmeCertsEntry
	 MAX-ACCESS not-accessible
	 STATUS current
	 DESCRIPTION
		 " from object 'slb.ssl-acme-cert-status'"
	::= {sslAcmeCertStatus 2}

sslAcmeCertStatusOperAcmeCertsEntry OBJECT-TYPE
	SYNTAX SslAcmeCertStatusOperAcmeCertsEntry
	MAX-ACCESS not-accessible
	STATUS current
	DESCRIPTION
		"The sslAcmeCertStatusOperAcmeCerts entry:acme-certs"
	INDEX {
		sslAcmeCertStatusOperAcmeCertsSlotId,
		sslAcmeCertStatusOperAcmeCertsAcmeCertsListId
	}
	::= { sslAcmeCertStatusOperAcmeCertsTable 1}

SslAcmeCertStatusOperAcmeCertsEntry ::=
	SEQUENCE {
		sslAcmeCertStatusOperAcmeCertsSlotId Integer32,
		sslAcmeCertStatusOperAcmeCertsAcmeCertsListId Integer32,
		sslAcmeCertStatusOperAcmeCertsName	DisplayString,
		sslAcmeCertStatusOperAcmeCertsStatus	DisplayString,
		sslAcmeCertStatusOperAcmeCertsRenew	DisplayString,
		sslAcmeCertStatusOperAcmeCertsRotated	Integer32,
		sslAcmeCertStatusOperAcmeCertsLastEnrollRenewStatus	DisplayString
	}

sslAcmeCertStatusOperAcmeCertsSlotId OBJECT-TYPE
	SYNTAX Integer32
	MAX-ACCESS read-only
	STATUS current
	DESCRIPTION
		""
	::= { sslAcmeCertStatusOperAcmeCertsEntry 1}

sslAcmeCertStatusOperAcmeCertsAcmeCertsListId OBJECT-TYPE
	SYNTAX Integer32
	MAX-ACCESS read-only
	STATUS current
	DESCRIPTION
		""
	::= { sslAcmeCertStatusOperAcmeCertsEntry 2}

sslAcmeCertStatusOperAcmeCertsName OBJECT-TYPE
	SYNTAX DisplayString
	MAX-ACCESS read-only
	STATUS current
	DESCRIPTION
		"name"
	::= { sslAcmeCertStatusOperAcmeCertsEntry 3}

sslAcmeCertStatusOperAcmeCertsStatus OBJECT-TYPE
	SYNTAX DisplayString
	MAX-ACCESS read-only
	STATUS current
	DESCRIPTION
		"status"
	::= { sslAcmeCertStatusOperAcmeCertsEntry 4}

sslAcmeCertStatusOperAcmeCertsRenew OBJECT-TYPE
	SYNTAX DisplayString
	MAX-ACCESS read-only
	STATUS current
	DESCRIPTION
		"renew"
	::= { sslAcmeCertStatusOperAcmeCertsEntry 5}

sslAcmeCertStatusOperAcmeCertsRotated OBJECT-TYPE
	SYNTAX Integer32
	MAX-ACCESS read-only
	STATUS current
	DESCRIPTION
		"rotated"
	::= { sslAcmeCertStatusOperAcmeCertsEntry 6}

sslAcmeCertStatusOperAcmeCertsLastEnrollRenewStatus OBJECT-TYPE
	SYNTAX DisplayString
	MAX-ACCESS read-only
	STATUS current
	DESCRIPTION
		"last-enroll-renew-status"
	::= { sslAcmeCertStatusOperAcmeCertsEntry 7}

END
