ACOS-FW-STATUS-MIB DEFINITIONS ::= BEGIN
	IMPORTS
		DisplayString, PhysAddress
		FROM SNMPv2-TC
	InetAddressType
		FROM INET-ADDRESS-MIB
	acosSchema
		FROM A10-AX-MIB
	MODULE-IDENTITY, OBJECT-TYPE, Counter32, Integer32, Counter64, OBJECT-IDENTITY, NOTIFICATION-TYPE
		FROM SNMPv2-SMI;
		fwStatusModule MODULE-IDENTITY
				LAST-UPDATED	"200705071327Z"
				ORGANIZATION	"A10 Networks, Inc."
				CONTACT-INFO	"Address: A10 Networks, Inc.
							  2300 Orchard Parkway
							  San Jose, CA 95131
						 Phone:   +1-888-822-7210 (USA/Canada)
						          +1-408-325-8676 (International)
						 E-mail:  support@A10Networks.com"

				DESCRIPTION	 "fwStatusModule OID for ACOS"
				::=  {  acosSchema 487 }

status		 OBJECT IDENTIFIER ::= { fwStatusModule 1}

statusOperTable OBJECT-TYPE
	 SYNTAX SEQUENCE OF StatusOperEntry
	 MAX-ACCESS not-accessible
	 STATUS current
	 DESCRIPTION
		 "Firewall status from object 'fw.status'"
	::= {status 2}

statusOperEntry OBJECT-TYPE
	SYNTAX StatusOperEntry
	MAX-ACCESS not-accessible
	STATUS current
	DESCRIPTION
		"The statusOper entry"
	INDEX {
		statusOperSlotId
	}
	::= { statusOperTable 1 }

StatusOperEntry ::=
	SEQUENCE {
		statusOperSlotId Integer32,
		statusOperCurrentActiveRuleSet	 DisplayString,
		statusOperPreviousSuccessfulCompilationAttempt	 DisplayString,
		statusOperPreviousSuccessfulCompilationDuration	 DisplayString,
		statusOperMostRecentCompilationAttempt	 DisplayString,
		statusOperMostRecentCompilationStatus	 DisplayString,
		statusOperInternal	 DisplayString
	}

statusOperSlotId OBJECT-TYPE
	 SYNTAX Integer32
	 MAX-ACCESS read-only
	 STATUS current
	 DESCRIPTION
		 ""
	::= { statusOperEntry 1 }

statusOperCurrentActiveRuleSet OBJECT-TYPE
	 SYNTAX DisplayString
	 MAX-ACCESS read-only
	 STATUS current
	 DESCRIPTION
		 "current-active-rule-set"
	::= { statusOperEntry 2 }

statusOperPreviousSuccessfulCompilationAttempt OBJECT-TYPE
	 SYNTAX DisplayString
	 MAX-ACCESS read-only
	 STATUS current
	 DESCRIPTION
		 "previous-successful-compilation-attempt"
	::= { statusOperEntry 3 }

statusOperPreviousSuccessfulCompilationDuration OBJECT-TYPE
	 SYNTAX DisplayString
	 MAX-ACCESS read-only
	 STATUS current
	 DESCRIPTION
		 "previous-successful-compilation-duration"
	::= { statusOperEntry 4 }

statusOperMostRecentCompilationAttempt OBJECT-TYPE
	 SYNTAX DisplayString
	 MAX-ACCESS read-only
	 STATUS current
	 DESCRIPTION
		 "most-recent-compilation-attempt"
	::= { statusOperEntry 5 }

statusOperMostRecentCompilationStatus OBJECT-TYPE
	 SYNTAX DisplayString
	 MAX-ACCESS read-only
	 STATUS current
	 DESCRIPTION
		 "most-recent-compilation-status"
	::= { statusOperEntry 6 }

statusOperInternal OBJECT-TYPE
	 SYNTAX DisplayString
	 MAX-ACCESS read-only
	 STATUS current
	 DESCRIPTION
		 "internal"
	::= { statusOperEntry 7 }

END
