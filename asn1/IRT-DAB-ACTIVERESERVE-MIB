--
-- IRT-DAB-ACTIVERESERVE-MIB.my
-- MIB generated by MG-SOFT Visual MIB Builder Version 6.0  Build 88
-- Friday, May 04, 2007 at 17:04:49
--

	IRT-DAB-ACTIVERESERVE-MIB DEFINITIONS ::= BEGIN
 
		IMPORTS
			eventTimeStamp, eventPriority, eventCounter, mibRelease			
				FROM IRT-COMMONVARBINDS-MIB			
			dab, Input1Input2, SelectManualAuto, SelectOnOff, LocalRemote, 
			FaultOK, ReadyNotReady, ExecutedNotExecuted, PresentNotPresent, WarningOK, 
			OkNotOk, MuteOk, SFNMFN			
				FROM IRT-TRANSMITTER-SMI-MIB			
			OBJECT-GROUP, MODULE-COMPLIANCE, NOTIFICATION-GROUP			
				FROM SNMPv2-CONF			
			sysDescr, sysName, sysLocation			
				FROM SNMPv2-MIB			
			Unsigned32, OBJECT-TYPE, MODULE-IDENTITY, NOTIFICATION-TYPE			
				FROM SNMPv2-SMI			
			DisplayString, TruthValue			
				FROM SNMPv2-TC;
	
	
		-- 1.3.6.1.4.1.19831.1.1.2.2
		dabActiveReserve MODULE-IDENTITY 
			LAST-UPDATED "200705041400Z"		-- May 04, 2007 at 14:00 GMT
			ORGANIZATION 
				"IRT for WORKING-GROUP-TC-MIB"
			CONTACT-INFO 
				"Contact-info.
				
				Andreas Metz
				
				Institut fuer Rundfunktechnik GmbH
				Broadcast Networks and Servers (SN)
				
				Floriansmuehlstr.60
				80939 Munich
				Germany
				
				Phone: +49 89 32399 325
				Fax: +49 89 32399 354
				"
			DESCRIPTION 
				"Description.
				
				branch definition
				
				1st level
				
				events               OBJECT IDENTIFIER ::= { dabActiveReserve 0 }
				dabARGeneral         OBJECT IDENTIFIER ::= { dabActiveReserve 1 }
				dabARAmplifierA      OBJECT IDENTIFIER ::= { dabActiveReserve 2 }
				dabARAmplifierB      OBJECT IDENTIFIER ::= { dabActiveReserve 3 }
				dabARExciterA        OBJECT IDENTIFIER ::= { dabActiveReserve 4 }
				dabARExciterB        OBJECT IDENTIFIER ::= { dabActiveReserve 5 }
				dabAREventEnable     OBJECT IDENTIFIER ::= { dabActiveReserve 6 }
				dabAREventPriority   OBJECT IDENTIFIER ::= { dabActiveReserve 7 }
				groups               OBJECT IDENTIFIER ::= { dabActiveReserve 8 }
				
				2nd level
				
				dabAREventEnableGeneral     OBJECT IDENTIFIER ::= { dabAREventEnable 1 }
				dabAREventEnableAmplifierA  OBJECT IDENTIFIER ::= { dabAREventEnable 2 }
				dabAREventEnableAmplifierB  OBJECT IDENTIFIER ::= { dabAREventEnable 3 }
				dabAREventEnableExciterA    OBJECT IDENTIFIER ::= { dabAREventEnable 4 }
				dabAREventEnableExciterB    OBJECT IDENTIFIER ::= { dabAREventEnable 5 }
				
				dabAREventPriorityGeneral     OBJECT IDENTIFIER ::= { dabAREventPriority 1 }
				dabAREventPriorityAmplifierA  OBJECT IDENTIFIER ::= { dabAREventPriority 2 }
				dabAREventPriorityAmplifierB  OBJECT IDENTIFIER ::= { dabAREventPriority 3 }
				dabAREventPriorityExciterA    OBJECT IDENTIFIER ::= { dabAREventPriority 4 }
				dabAREventPriorityExciterB    OBJECT IDENTIFIER ::= { dabAREventPriority 5 }
				
				end branch"
			REVISION "200705041400Z"		-- May 04, 2007 at 14:00 GMT
			DESCRIPTION 
				"change SFNMode, LocalMode (description only) and Module-COMPLIANCE
				change numbering: OIDs 1.3.6.1.4.1.19831.1.1.2.2.7.1.13-19 and 1.3.6.1.4.1.19831.1.1.2.2.6.1.13-19!
				"
			REVISION "200612201400Z"		-- December 20, 2006 at 14:00 GMT
			DESCRIPTION 
				"corrections"
			REVISION "200609211400Z"		-- September 21, 2006 at 14:00 GMT
			DESCRIPTION 
				"Adding Compliance Statement"
			REVISION "200609191400Z"		-- September 19, 2006 at 14:00 GMT
			DESCRIPTION 
				"Correcting Imports"
			REVISION "200609071400Z"		-- September 07, 2006 at 14:00 GMT
			DESCRIPTION 
				"Relocation of the TC-MIB from the standard OID area at IEC into the private OID area of the IRT"
			::= { dab 2 }

		
	
	
--
-- Node definitions
--
	
-- dab active reserve events
		-- 1.3.6.1.4.1.19831.1.1.2.2.0
		dabEventsAR OBJECT IDENTIFIER ::= { dabActiveReserve 0 }

		
		-- 1.3.6.1.4.1.19831.1.1.2.2.0.1
		dabARInputPreselectionEvent NOTIFICATION-TYPE
			OBJECTS { sysDescr, sysName, sysLocation, eventTimeStamp, eventPriority, 
				eventCounter, dabARInputPreselection }
			STATUS current
			DESCRIPTION 
				"Description. dabARInputPreselection notification"
			::= { dabEventsAR 1 }

		
		-- 1.3.6.1.4.1.19831.1.1.2.2.0.2
		dabARInputAutomaticEvent NOTIFICATION-TYPE
			OBJECTS { sysDescr, sysName, sysLocation, eventTimeStamp, eventPriority, 
				eventCounter, dabARInputAutomatic }
			STATUS current
			DESCRIPTION 
				"Description. dabARInputAutomatic notification"
			::= { dabEventsAR 2 }

		
		-- 1.3.6.1.4.1.19831.1.1.2.2.0.3
		dabARPreselectionExciterEvent NOTIFICATION-TYPE
			OBJECTS { sysDescr, sysName, sysLocation, eventTimeStamp, eventPriority, 
				eventCounter, dabARPreselectionExciter }
			STATUS current
			DESCRIPTION 
				"Description. dabARPreselectionExciter notification"
			::= { dabEventsAR 3 }

		
		-- 1.3.6.1.4.1.19831.1.1.2.2.0.4
		dabARPreselectionAmplifierEvent NOTIFICATION-TYPE
			OBJECTS { sysDescr, sysName, sysLocation, eventTimeStamp, eventPriority, 
				eventCounter, dabARPreselectionAmplifier }
			STATUS current
			DESCRIPTION 
				"Description. dabARPreselectionAmplifier notification"
			::= { dabEventsAR 4 }

		
		-- 1.3.6.1.4.1.19831.1.1.2.2.0.5
		dabARTransmitterOpModeEvent NOTIFICATION-TYPE
			OBJECTS { sysDescr, sysName, sysLocation, eventTimeStamp, eventPriority, 
				eventCounter, dabARTransmitterOpMode }
			STATUS current
			DESCRIPTION 
				"Description. dabARTransmitterOpMode notification"
			::= { dabEventsAR 5 }

		
		-- 1.3.6.1.4.1.19831.1.1.2.2.0.6
		dabARReserveControlEvent NOTIFICATION-TYPE
			OBJECTS { sysDescr, sysName, sysLocation, eventTimeStamp, eventPriority, 
				eventCounter, dabARReserveControl }
			STATUS current
			DESCRIPTION 
				"Description. dabARReserveControl notification"
			::= { dabEventsAR 6 }

		
		-- 1.3.6.1.4.1.19831.1.1.2.2.0.7
		dabARResetFaultEvent NOTIFICATION-TYPE
			OBJECTS { sysDescr, sysName, sysLocation, eventTimeStamp, eventPriority, 
				eventCounter, dabARResetFault }
			STATUS obsolete
			DESCRIPTION 
				"Notification is inactive!
				
				Description. dabARResetFaultEvent notification"
			::= { dabEventsAR 7 }

		
		-- 1.3.6.1.4.1.19831.1.1.2.2.0.8
		dabARActiveAmplifierEvent NOTIFICATION-TYPE
			OBJECTS { sysDescr, sysName, sysLocation, eventTimeStamp, eventPriority, 
				eventCounter, dabARActiveAmplifier }
			STATUS current
			DESCRIPTION 
				"Description. dabARActiveAmplifier notification"
			::= { dabEventsAR 8 }

		
		-- 1.3.6.1.4.1.19831.1.1.2.2.0.9
		dabARActiveExciterEvent NOTIFICATION-TYPE
			OBJECTS { sysDescr, sysName, sysLocation, eventTimeStamp, eventPriority, 
				eventCounter, dabARActiveExciter }
			STATUS current
			DESCRIPTION 
				"Description. dabARActiveExciter notification"
			::= { dabEventsAR 9 }

		
		-- 1.3.6.1.4.1.19831.1.1.2.2.0.10
		dabARLocalModeEvent NOTIFICATION-TYPE
			OBJECTS { sysDescr, sysName, sysLocation, eventTimeStamp, eventPriority, 
				eventCounter, dabARLocalMode }
			STATUS current
			DESCRIPTION 
				"Description. dabARLocalMode notification"
			::= { dabEventsAR 10 }

		
		-- 1.3.6.1.4.1.19831.1.1.2.2.0.11
		dabARControlUnitFaultEvent NOTIFICATION-TYPE
			OBJECTS { sysDescr, sysName, sysLocation, eventTimeStamp, eventPriority, 
				eventCounter, dabARControlUnitFault }
			STATUS current
			DESCRIPTION 
				"Description. dabARControlUnitFault notification"
			::= { dabEventsAR 11 }

		
		-- 1.3.6.1.4.1.19831.1.1.2.2.0.12
		dabARExciterSwitchOverModeEvent NOTIFICATION-TYPE
			OBJECTS { sysDescr, sysName, sysLocation, eventTimeStamp, eventPriority, 
				eventCounter, dabARExciterSwitchOverMode }
			STATUS current
			DESCRIPTION 
				"Description. dabARExciterSwitchOverMode notification"
			::= { dabEventsAR 12 }

		
		-- 1.3.6.1.4.1.19831.1.1.2.2.0.13
		dabARExciterSwitchOverReadyEvent NOTIFICATION-TYPE
			OBJECTS { sysDescr, sysName, sysLocation, eventTimeStamp, eventPriority, 
				eventCounter, dabARExciterSwitchOverReady }
			STATUS current
			DESCRIPTION 
				"Description. dabARExciterSwitchOverReady notification"
			::= { dabEventsAR 13 }

		
		-- 1.3.6.1.4.1.19831.1.1.2.2.0.14
		dabARExciterSwitchOverExecutedEvent NOTIFICATION-TYPE
			OBJECTS { sysDescr, sysName, sysLocation, eventTimeStamp, eventPriority, 
				eventCounter, dabARExciterSwitchOverExecuted }
			STATUS current
			DESCRIPTION 
				"Description. dabARExciterSwitchOverExecuted notification"
			::= { dabEventsAR 14 }

		
		-- 1.3.6.1.4.1.19831.1.1.2.2.0.15
		dabARExciterSwitchOverFaultEvent NOTIFICATION-TYPE
			OBJECTS { sysDescr, sysName, sysLocation, eventTimeStamp, eventPriority, 
				eventCounter, dabARExciterSwitchOverFault }
			STATUS current
			DESCRIPTION 
				"Description. dabARExciterSwitchOverFault notification"
			::= { dabEventsAR 15 }

		
		-- 1.3.6.1.4.1.19831.1.1.2.2.0.16
		dabARAmplifierSwitchOverModeEvent NOTIFICATION-TYPE
			OBJECTS { sysDescr, sysName, sysLocation, eventTimeStamp, eventPriority, 
				eventCounter, dabARAmplifierSwitchOverMode }
			STATUS current
			DESCRIPTION 
				"Description. dabARAmplifierSwitchOverMode notification"
			::= { dabEventsAR 16 }

		
		-- 1.3.6.1.4.1.19831.1.1.2.2.0.17
		dabARAmplifierSwitchOverReadyEvent NOTIFICATION-TYPE
			OBJECTS { sysDescr, sysName, sysLocation, eventTimeStamp, eventPriority, 
				eventCounter, dabARAmplifierSwitchOverReady }
			STATUS current
			DESCRIPTION 
				"Description. dabARAmplifierSwitchOverReady notification"
			::= { dabEventsAR 17 }

		
		-- 1.3.6.1.4.1.19831.1.1.2.2.0.18
		dabARAmplifierSwitchOverExecutedEvent NOTIFICATION-TYPE
			OBJECTS { sysDescr, sysName, sysLocation, eventTimeStamp, eventPriority, 
				eventCounter, dabARAmplifierSwitchOverExecuted }
			STATUS current
			DESCRIPTION 
				"Description. dabARAmplifierSwitchOverExecuted notification"
			::= { dabEventsAR 18 }

		
		-- 1.3.6.1.4.1.19831.1.1.2.2.0.19
		dabARAmplifierSwitchOverFaultEvent NOTIFICATION-TYPE
			OBJECTS { sysDescr, sysName, sysLocation, eventTimeStamp, eventPriority, 
				eventCounter, dabARAmplifierSwitchOverFault }
			STATUS current
			DESCRIPTION 
				"Description. dabARAmplifierSwitchOverFault notification"
			::= { dabEventsAR 19 }

		
		-- 1.3.6.1.4.1.19831.1.1.2.2.0.20
		dabARAmplifierARFPresentEvent NOTIFICATION-TYPE
			OBJECTS { sysDescr, sysName, sysLocation, eventTimeStamp, eventPriority, 
				eventCounter, dabARAmplifierARFPresent }
			STATUS current
			DESCRIPTION 
				"Description. dabARAmplifierARFPresent notification"
			::= { dabEventsAR 20 }

		
		-- 1.3.6.1.4.1.19831.1.1.2.2.0.21
		dabARAmplifierAFaultEvent NOTIFICATION-TYPE
			OBJECTS { sysDescr, sysName, sysLocation, eventTimeStamp, eventPriority, 
				eventCounter, dabARAmplifierAFault }
			STATUS current
			DESCRIPTION 
				"Description. dabARAmplifierAFault notification"
			::= { dabEventsAR 21 }

		
		-- 1.3.6.1.4.1.19831.1.1.2.2.0.22
		dabARAmplifierAWarningEvent NOTIFICATION-TYPE
			OBJECTS { sysDescr, sysName, sysLocation, eventTimeStamp, eventPriority, 
				eventCounter, dabARAmplifierAWarning }
			STATUS current
			DESCRIPTION 
				"Description. dabARAmplifierAWarning notification"
			::= { dabEventsAR 22 }

		
		-- 1.3.6.1.4.1.19831.1.1.2.2.0.23
		dabARAmplifierBRFPresentEvent NOTIFICATION-TYPE
			OBJECTS { sysDescr, sysName, sysLocation, eventTimeStamp, eventPriority, 
				eventCounter, dabARAmplifierBRFPresent }
			STATUS current
			DESCRIPTION 
				"Description. dabARAmplifierBRFPresent notification"
			::= { dabEventsAR 23 }

		
		-- 1.3.6.1.4.1.19831.1.1.2.2.0.24
		dabARAmplifierBFaultEvent NOTIFICATION-TYPE
			OBJECTS { sysDescr, sysName, sysLocation, eventTimeStamp, eventPriority, 
				eventCounter, dabARAmplifierBFault }
			STATUS current
			DESCRIPTION 
				"Description. dabARAmplifierBFault notification"
			::= { dabEventsAR 24 }

		
		-- 1.3.6.1.4.1.19831.1.1.2.2.0.25
		dabARAmplifierBWarningEvent NOTIFICATION-TYPE
			OBJECTS { sysDescr, sysName, sysLocation, eventTimeStamp, eventPriority, 
				eventCounter, dabARAmplifierBWarning }
			STATUS current
			DESCRIPTION 
				"Description. dabARAmplifierBWarning notification"
			::= { dabEventsAR 25 }

		
		-- 1.3.6.1.4.1.19831.1.1.2.2.0.26
		dabARExciterAInput1OKEvent NOTIFICATION-TYPE
			OBJECTS { sysDescr, sysName, sysLocation, eventTimeStamp, eventPriority, 
				eventCounter, dabARExciterAInput1OK }
			STATUS current
			DESCRIPTION 
				"Description. dabARExciterAInput1OK notification"
			::= { dabEventsAR 26 }

		
		-- 1.3.6.1.4.1.19831.1.1.2.2.0.27
		dabARExciterAInput2OKEvent NOTIFICATION-TYPE
			OBJECTS { sysDescr, sysName, sysLocation, eventTimeStamp, eventPriority, 
				eventCounter, dabARExciterAInput2OK }
			STATUS current
			DESCRIPTION 
				"Description. dabARExciterAInput2OK notification"
			::= { dabEventsAR 27 }

		
		-- 1.3.6.1.4.1.19831.1.1.2.2.0.28
		dabARExciterALocalModeEvent NOTIFICATION-TYPE
			OBJECTS { sysDescr, sysName, sysLocation, eventTimeStamp, eventPriority, 
				eventCounter, dabARExciterALocalMode }
			STATUS current
			DESCRIPTION 
				"Description. dabARExciterALocalMode notification"
			::= { dabEventsAR 28 }

		
		-- 1.3.6.1.4.1.19831.1.1.2.2.0.29
		dabARExciterAFaultEvent NOTIFICATION-TYPE
			OBJECTS { sysDescr, sysName, sysLocation, eventTimeStamp, eventPriority, 
				eventCounter, dabARExciterAFault }
			STATUS current
			DESCRIPTION 
				"Description. dabARExciterAFault notification"
			::= { dabEventsAR 29 }

		
		-- 1.3.6.1.4.1.19831.1.1.2.2.0.30
		dabARExciterAWarningEvent NOTIFICATION-TYPE
			OBJECTS { sysDescr, sysName, sysLocation, eventTimeStamp, eventPriority, 
				eventCounter, dabARExciterAWarning }
			STATUS current
			DESCRIPTION 
				"Description. dabARExciterAWarning notification"
			::= { dabEventsAR 30 }

		
		-- 1.3.6.1.4.1.19831.1.1.2.2.0.31
		dabARExciterAActiveInputEvent NOTIFICATION-TYPE
			OBJECTS { sysDescr, sysName, sysLocation, eventTimeStamp, eventPriority, 
				eventCounter, dabARExciterAActiveInput }
			STATUS current
			DESCRIPTION 
				"Description. dabARExciterAActiveInput notification"
			::= { dabEventsAR 31 }

		
		-- 1.3.6.1.4.1.19831.1.1.2.2.0.32
		dabARExciterASFNModeEvent NOTIFICATION-TYPE
			OBJECTS { sysDescr, sysName, sysLocation, eventTimeStamp, eventPriority, 
				eventCounter, dabARExciterASFNMode }
			STATUS current
			DESCRIPTION 
				"Description. dabARExciterASFNMode notification"
			::= { dabEventsAR 32 }

		
		-- 1.3.6.1.4.1.19831.1.1.2.2.0.33
		dabARExciterARefFaultEvent NOTIFICATION-TYPE
			OBJECTS { sysDescr, sysName, sysLocation, eventTimeStamp, eventPriority, 
				eventCounter, dabARExciterARefFault }
			STATUS current
			DESCRIPTION 
				"Description. dabARExciterARefFault notification"
			::= { dabEventsAR 33 }

		
		-- 1.3.6.1.4.1.19831.1.1.2.2.0.34
		dabARExciterAMuteEvent NOTIFICATION-TYPE
			OBJECTS { sysDescr, sysName, sysLocation, eventTimeStamp, eventPriority, 
				eventCounter, dabARExciterAMute }
			STATUS current
			DESCRIPTION 
				"Description. dabARExciterAMute notification"
			::= { dabEventsAR 34 }

		
		-- 1.3.6.1.4.1.19831.1.1.2.2.0.35
		dabARExciterAWarningTimeStampEvent NOTIFICATION-TYPE
			OBJECTS { sysDescr, sysName, sysLocation, eventTimeStamp, eventPriority, 
				eventCounter, dabARExciterAWarningTimeStamp }
			STATUS current
			DESCRIPTION 
				"Description. dabARExciterAWarningTomeStamp notification"
			::= { dabEventsAR 35 }

		
		-- 1.3.6.1.4.1.19831.1.1.2.2.0.36
		dabARExciterBInput1OKEvent NOTIFICATION-TYPE
			OBJECTS { sysDescr, sysName, sysLocation, eventTimeStamp, eventPriority, 
				eventCounter, dabARExciterBInput1OK }
			STATUS current
			DESCRIPTION 
				"Description. dabARExciterBInput1OK notification"
			::= { dabEventsAR 36 }

		
		-- 1.3.6.1.4.1.19831.1.1.2.2.0.37
		dabARExciterBInput2OKEvent NOTIFICATION-TYPE
			OBJECTS { sysDescr, sysName, sysLocation, eventTimeStamp, eventPriority, 
				eventCounter, dabARExciterBInput2OK }
			STATUS current
			DESCRIPTION 
				"Description. dabARExciterBInput2OK notification"
			::= { dabEventsAR 37 }

		
		-- 1.3.6.1.4.1.19831.1.1.2.2.0.38
		dabARExciterBLocalModeEvent NOTIFICATION-TYPE
			OBJECTS { sysDescr, sysName, sysLocation, eventTimeStamp, eventPriority, 
				eventCounter, dabARExciterBLocalMode }
			STATUS current
			DESCRIPTION 
				"Description. dabARExciterBLocalMode  notification"
			::= { dabEventsAR 38 }

		
		-- 1.3.6.1.4.1.19831.1.1.2.2.0.39
		dabARExciterBFaultEvent NOTIFICATION-TYPE
			OBJECTS { sysDescr, sysName, sysLocation, eventTimeStamp, eventPriority, 
				eventCounter, dabARExciterBFault }
			STATUS current
			DESCRIPTION 
				"Description. dabARExciterBFault notification"
			::= { dabEventsAR 39 }

		
		-- 1.3.6.1.4.1.19831.1.1.2.2.0.40
		dabARExciterBWarningEvent NOTIFICATION-TYPE
			OBJECTS { sysDescr, sysName, sysLocation, eventTimeStamp, eventPriority, 
				eventCounter, dabARExciterBWarning }
			STATUS current
			DESCRIPTION 
				"Description. dabARExciterBWarning notification"
			::= { dabEventsAR 40 }

		
		-- 1.3.6.1.4.1.19831.1.1.2.2.0.41
		dabARExciterBActiveInputEvent NOTIFICATION-TYPE
			OBJECTS { sysDescr, sysName, sysLocation, eventTimeStamp, eventPriority, 
				eventCounter, dabARExciterBActiveInput }
			STATUS current
			DESCRIPTION 
				"Description. dabARExciterBActiveInput notification"
			::= { dabEventsAR 41 }

		
		-- 1.3.6.1.4.1.19831.1.1.2.2.0.42
		dabARExciterBSFNModeEvent NOTIFICATION-TYPE
			OBJECTS { sysDescr, sysName, sysLocation, eventTimeStamp, eventPriority, 
				eventCounter, dabARExciterBSFNMode }
			STATUS current
			DESCRIPTION 
				"Description. dabARExciterBSFNMode notification"
			::= { dabEventsAR 42 }

		
		-- 1.3.6.1.4.1.19831.1.1.2.2.0.43
		dabARExciterBRefFaultEvent NOTIFICATION-TYPE
			OBJECTS { sysDescr, sysName, sysLocation, eventTimeStamp, eventPriority, 
				eventCounter, dabARExciterBRefFault }
			STATUS current
			DESCRIPTION 
				"Description. dabARExciterBRefFault notification"
			::= { dabEventsAR 43 }

		
		-- 1.3.6.1.4.1.19831.1.1.2.2.0.44
		dabARExciterBMuteEvent NOTIFICATION-TYPE
			OBJECTS { sysDescr, sysName, sysLocation, eventTimeStamp, eventPriority, 
				eventCounter, dabARExciterBMute }
			STATUS current
			DESCRIPTION 
				"Description. dabARExciterBMute notification"
			::= { dabEventsAR 44 }

		
		-- 1.3.6.1.4.1.19831.1.1.2.2.0.45
		dabARExciterBWarningTimeStampEvent NOTIFICATION-TYPE
			OBJECTS { sysDescr, sysName, sysLocation, eventTimeStamp, eventPriority, 
				eventCounter, dabARExciterBWarningTimeStamp }
			STATUS current
			DESCRIPTION 
				"Description. dabARExciterBWarningTimeStamp notification"
			::= { dabEventsAR 45 }

		
-- dab active reserve general
		-- 1.3.6.1.4.1.19831.1.1.2.2.1
		dabARGeneral OBJECT IDENTIFIER ::= { dabActiveReserve 1 }

		
		-- 1.3.6.1.4.1.19831.1.1.2.2.1.1
		dabARInputPreselection OBJECT-TYPE
			SYNTAX Input1Input2
			MAX-ACCESS read-write
			STATUS current
			DESCRIPTION
				"Preselection input of aktive reserve 
				
				(0) undefined
				(1) Input 1
				(2) Input 2"
			::= { dabARGeneral 1 }

		
		-- 1.3.6.1.4.1.19831.1.1.2.2.1.2
		dabARInputAutomatic OBJECT-TYPE
			SYNTAX SelectManualAuto
			MAX-ACCESS read-write
			STATUS current
			DESCRIPTION
				"Input selection mode of aktive reserve: manual or automatic
				
				(0) undefined
				(1) manual 
				(2) automatic"
			::= { dabARGeneral 2 }

		
		-- 1.3.6.1.4.1.19831.1.1.2.2.1.3
		dabARPreselectionExciter OBJECT-TYPE
			SYNTAX INTEGER
				{
				undefined(0),
				exciterA(1),
				exciterB(2)
				}
			MAX-ACCESS read-write
			STATUS current
			DESCRIPTION
				"Aktive reserve. Preselection of the exciter 
				
				"
			::= { dabARGeneral 3 }

		
		-- 1.3.6.1.4.1.19831.1.1.2.2.1.4
		dabARPreselectionAmplifier OBJECT-TYPE
			SYNTAX INTEGER
				{
				undefined(0),
				amplifierA(1),
				amplifierB(2),
				amplifierAB(3),
				amplifierABtoDummiload(4)
				}
			MAX-ACCESS read-write
			STATUS current
			DESCRIPTION
				"Aktive reserve. Preselection amplifier 
				
				"
			::= { dabARGeneral 4 }

		
		-- 1.3.6.1.4.1.19831.1.1.2.2.1.5
		dabARTransmitterOpMode OBJECT-TYPE
			SYNTAX SelectOnOff
			MAX-ACCESS read-write
			STATUS current
			DESCRIPTION
				"General transmitter control of aktive reserve
				
				(0) undefined
				(1) ON
				(2) OFF"
			::= { dabARGeneral 5 }

		
		-- 1.3.6.1.4.1.19831.1.1.2.2.1.6
		dabARReserveControl OBJECT-TYPE
			SYNTAX SelectOnOff
			MAX-ACCESS read-write
			STATUS current
			DESCRIPTION
				"Reserve control of aktive reserve
				
				(0) undefined
				(1) ON 
				(2) OFF "
			::= { dabARGeneral 6 }

		
		-- 1.3.6.1.4.1.19831.1.1.2.2.1.7
		dabARResetFault OBJECT-TYPE
			SYNTAX Unsigned32
			MAX-ACCESS read-write
			STATUS obsolete
			DESCRIPTION
				"Massage is inactive!
				
				Active Reserve. Reset fault: trigger for reset the sum fault
				
				<1>
				
				(1) reset sum fault
				"
			::= { dabARGeneral 7 }

		
		-- 1.3.6.1.4.1.19831.1.1.2.2.1.8
		dabARActiveAmplifier OBJECT-TYPE
			SYNTAX INTEGER
				{
				undefined(0),
				amplifierA(1),
				amplifierB(2),
				amplifierAB(3),
				amplifierABtoDummiload(4)
				}
			MAX-ACCESS read-only
			STATUS current
			DESCRIPTION
				"Active amplifier  of aktive reserve
				
				"
			::= { dabARGeneral 8 }

		
		-- 1.3.6.1.4.1.19831.1.1.2.2.1.9
		dabARActiveExciter OBJECT-TYPE
			SYNTAX INTEGER
				{
				undefined(0),
				exciterA(1),
				exciterB(2)
				}
			MAX-ACCESS read-only
			STATUS current
			DESCRIPTION
				"Active exciter of aktive reserve
				
				"
			::= { dabARGeneral 9 }

		
		-- 1.3.6.1.4.1.19831.1.1.2.2.1.10
		dabARLocalMode OBJECT-TYPE
			SYNTAX LocalRemote
			MAX-ACCESS read-only
			STATUS current
			DESCRIPTION
				"Active reserve. Local mode
				
				(0) undefined
				(1) local
				(2) remote"
			::= { dabARGeneral 10 }

		
		-- 1.3.6.1.4.1.19831.1.1.2.2.1.11
		dabARControlUnitFault OBJECT-TYPE
			SYNTAX FaultOK
			UNITS " "
			MAX-ACCESS read-only
			STATUS current
			DESCRIPTION
				"Aktive reserve. State of the control unit
				
				(0) undefined
				(1) fault
				(2) ok"
			::= { dabARGeneral 11 }

		
		-- 1.3.6.1.4.1.19831.1.1.2.2.1.12
		dabARExciterSwitchOverMode OBJECT-TYPE
			SYNTAX SelectManualAuto
			MAX-ACCESS read-write
			STATUS current
			DESCRIPTION
				"Aktive reserve. Exciter switch over mode: manual or automatic
				
				(0) undefined
				(1) manual 
				(2) automatic"
			::= { dabARGeneral 12 }

		
		-- 1.3.6.1.4.1.19831.1.1.2.2.1.13
		dabARExciterSwitchOverReady OBJECT-TYPE
			SYNTAX ReadyNotReady
			MAX-ACCESS read-only
			STATUS current
			DESCRIPTION
				"Aktive reserve. State of the exciter switch over unit
				
				(0) undefined
				(1) ready
				(2) not ready"
			::= { dabARGeneral 13 }

		
		-- 1.3.6.1.4.1.19831.1.1.2.2.1.14
		dabARExciterSwitchOverExecuted OBJECT-TYPE
			SYNTAX ExecutedNotExecuted
			MAX-ACCESS read-only
			STATUS current
			DESCRIPTION
				"Aktive reserve. Shows if the exciter switch over unit it has executed
				
				(0) undefined
				(1) executed
				(2) not executed"
			::= { dabARGeneral 14 }

		
		-- 1.3.6.1.4.1.19831.1.1.2.2.1.15
		dabARExciterSwitchOverFault OBJECT-TYPE
			SYNTAX FaultOK
			MAX-ACCESS read-only
			STATUS current
			DESCRIPTION
				"Aktive reserve. Fault state of the exciter switch over unit
				
				(0) undefined
				(1) faulty
				(2) ok"
			::= { dabARGeneral 15 }

		
		-- 1.3.6.1.4.1.19831.1.1.2.2.1.16
		dabARAmplifierSwitchOverMode OBJECT-TYPE
			SYNTAX SelectManualAuto
			MAX-ACCESS read-write
			STATUS current
			DESCRIPTION
				"Active reserve. Amplifier switch over mode: manual or automatic
				
				(0) undefined
				(1) manual
				(2) automatic"
			::= { dabARGeneral 16 }

		
		-- 1.3.6.1.4.1.19831.1.1.2.2.1.17
		dabARAmplifierSwitchOverReady OBJECT-TYPE
			SYNTAX ReadyNotReady
			MAX-ACCESS read-only
			STATUS current
			DESCRIPTION
				"Active reserve. State of the amplifier switch over unit
				
				(0) undefined
				(1) ready
				(2) not ready"
			::= { dabARGeneral 17 }

		
		-- 1.3.6.1.4.1.19831.1.1.2.2.1.18
		dabARAmplifierSwitchOverExecuted OBJECT-TYPE
			SYNTAX ExecutedNotExecuted
			MAX-ACCESS read-only
			STATUS current
			DESCRIPTION
				"Active reserve. Shows if the amplifier switch over unit it has executed
				
				(0) undefined
				(1) executed
				(2) not executed"
			::= { dabARGeneral 18 }

		
		-- 1.3.6.1.4.1.19831.1.1.2.2.1.19
		dabARAmplifierSwitchOverFault OBJECT-TYPE
			SYNTAX FaultOK
			MAX-ACCESS read-only
			STATUS current
			DESCRIPTION
				"Active reserve. Fault state of the amplifier switch over unit
				
				(0) undefined
				(1) faulty
				(2) ok"
			::= { dabARGeneral 19 }

		
-- dab active reserve amplifier A
		-- 1.3.6.1.4.1.19831.1.1.2.2.2
		dabARAmplifierA OBJECT IDENTIFIER ::= { dabActiveReserve 2 }

		
		-- 1.3.6.1.4.1.19831.1.1.2.2.2.1
		dabARAmplifierARFPresent OBJECT-TYPE
			SYNTAX PresentNotPresent
			MAX-ACCESS read-only
			STATUS current
			DESCRIPTION
				"Active reserve. Describes if the output power of the amplifier A is present
				
				(0) undefined
				(1) present
				(2) not present"
			::= { dabARAmplifierA 1 }

		
		-- 1.3.6.1.4.1.19831.1.1.2.2.2.2
		dabARAmplifierAFault OBJECT-TYPE
			SYNTAX FaultOK
			MAX-ACCESS read-only
			STATUS current
			DESCRIPTION
				"Active reserve. Fault state of amplifier A
				
				(0) undefined
				(1) fault
				(2) ok"
			::= { dabARAmplifierA 2 }

		
		-- 1.3.6.1.4.1.19831.1.1.2.2.2.3
		dabARAmplifierAWarning OBJECT-TYPE
			SYNTAX WarningOK
			MAX-ACCESS read-only
			STATUS current
			DESCRIPTION
				"Active reserve. Warning state of amplifier A
				
				(0) undefined
				(1) warning
				(2) ok"
			::= { dabARAmplifierA 3 }

		
-- dab active reserve amplifier B
		-- 1.3.6.1.4.1.19831.1.1.2.2.3
		dabARAmplifierB OBJECT IDENTIFIER ::= { dabActiveReserve 3 }

		
		-- 1.3.6.1.4.1.19831.1.1.2.2.3.1
		dabARAmplifierBRFPresent OBJECT-TYPE
			SYNTAX PresentNotPresent
			MAX-ACCESS read-only
			STATUS current
			DESCRIPTION
				"Active reserve. Describes if the output power of the amplifier B is present
				
				(0) undefined
				(1) present
				(2) not present"
			::= { dabARAmplifierB 1 }

		
		-- 1.3.6.1.4.1.19831.1.1.2.2.3.2
		dabARAmplifierBFault OBJECT-TYPE
			SYNTAX FaultOK
			MAX-ACCESS read-only
			STATUS current
			DESCRIPTION
				"Active reserve. Fault state of amplifier B
				
				(0) undefined
				(1) fault
				(2) ok"
			::= { dabARAmplifierB 2 }

		
		-- 1.3.6.1.4.1.19831.1.1.2.2.3.3
		dabARAmplifierBWarning OBJECT-TYPE
			SYNTAX WarningOK
			MAX-ACCESS read-only
			STATUS current
			DESCRIPTION
				"Active reserve. Warning state of amplifier B
				
				(0) undefined
				(1) warning
				(2) ok"
			::= { dabARAmplifierB 3 }

		
-- dab active reserve excister A
		-- 1.3.6.1.4.1.19831.1.1.2.2.4
		dabARExciterA OBJECT IDENTIFIER ::= { dabActiveReserve 4 }

		
		-- 1.3.6.1.4.1.19831.1.1.2.2.4.1
		dabARExciterAInput1OK OBJECT-TYPE
			SYNTAX OkNotOk
			MAX-ACCESS read-only
			STATUS current
			DESCRIPTION
				"Active reserve. Describes if the input signal at the input 1 of exiter A is ok
				
				(0) undefined
				(1) signal ok
				(2) signal is not ok "
			::= { dabARExciterA 1 }

		
		-- 1.3.6.1.4.1.19831.1.1.2.2.4.2
		dabARExciterAInput2OK OBJECT-TYPE
			SYNTAX OkNotOk
			MAX-ACCESS read-only
			STATUS current
			DESCRIPTION
				"Active reserve. Describes if the input signal at the input 2 of exiter A is ok
				
				(0) undefined
				(1) signal ok
				(2) signal is not ok "
			::= { dabARExciterA 2 }

		
		-- 1.3.6.1.4.1.19831.1.1.2.2.4.3
		dabARExciterALocalMode OBJECT-TYPE
			SYNTAX LocalRemote
			MAX-ACCESS read-only
			STATUS current
			DESCRIPTION
				"Active reserve. State of the local mode of exciter A
				
				(0) undefined
				(1) local
				(2) remote"
			::= { dabARExciterA 3 }

		
		-- 1.3.6.1.4.1.19831.1.1.2.2.4.4
		dabARExciterAFault OBJECT-TYPE
			SYNTAX FaultOK
			MAX-ACCESS read-only
			STATUS current
			DESCRIPTION
				"Active reserve. State of the exciter A
				
				(0) undefined
				(1) fault
				(2) ok"
			::= { dabARExciterA 4 }

		
		-- 1.3.6.1.4.1.19831.1.1.2.2.4.5
		dabARExciterAWarning OBJECT-TYPE
			SYNTAX WarningOK
			MAX-ACCESS read-only
			STATUS current
			DESCRIPTION
				"Active reserve. Warning state of the exciter A
				
				(0) undefined
				(1) warning
				(2) ok"
			::= { dabARExciterA 5 }

		
		-- 1.3.6.1.4.1.19831.1.1.2.2.4.6
		dabARExciterAActiveInput OBJECT-TYPE
			SYNTAX INTEGER
				{
				undefined(0),
				input1(1),
				input2(2),
				seamless(3),
				hmHierarchicalModulation(4)
				}
			MAX-ACCESS read-only
			STATUS current
			DESCRIPTION
				"Active reserve. Active input of the exciter A 
				
				"
			::= { dabARExciterA 6 }

		
		-- 1.3.6.1.4.1.19831.1.1.2.2.4.7
		dabARExciterASFNMode OBJECT-TYPE
			SYNTAX SFNMFN
			MAX-ACCESS read-only
			STATUS current
			DESCRIPTION
				"Active reserve. SFN mode of exciter A
				
				(0) undefined
				(1) SFN
				(2) MFN"
			::= { dabARExciterA 7 }

		
		-- 1.3.6.1.4.1.19831.1.1.2.2.4.8
		dabARExciterARefFault OBJECT-TYPE
			SYNTAX FaultOK
			MAX-ACCESS read-only
			STATUS current
			DESCRIPTION
				"Active reserve. Fault state of the GPS input or the reference frequency of exciter A
				
				(0) undefined
				(1) fault
				(2) ok"
			::= { dabARExciterA 8 }

		
		-- 1.3.6.1.4.1.19831.1.1.2.2.4.9
		dabARExciterAMute OBJECT-TYPE
			SYNTAX MuteOk
			MAX-ACCESS read-only
			STATUS current
			DESCRIPTION
				"Active reserve. Mute state of exciter A
				
				(0) undefined
				(1) mute
				(2) ok"
			::= { dabARExciterA 9 }

		
		-- 1.3.6.1.4.1.19831.1.1.2.2.4.10
		dabARExciterAWarningTimeStamp OBJECT-TYPE
			SYNTAX WarningOK
			MAX-ACCESS read-only
			STATUS current
			DESCRIPTION
				"Active reserve. Time stamp warning of exciter A
				
				(0) undefined
				(1) warning
				(2) ok"
			::= { dabARExciterA 10 }

		
-- dab active reserve excister B
		-- 1.3.6.1.4.1.19831.1.1.2.2.5
		dabARExciterB OBJECT IDENTIFIER ::= { dabActiveReserve 5 }

		
		-- 1.3.6.1.4.1.19831.1.1.2.2.5.1
		dabARExciterBInput1OK OBJECT-TYPE
			SYNTAX OkNotOk
			MAX-ACCESS read-only
			STATUS current
			DESCRIPTION
				"Active reserve. Describes if the input signal at the input 1 of exciter B is ok
				
				(0) undefined
				(1) signal ok
				(2) signal is not ok "
			::= { dabARExciterB 1 }

		
		-- 1.3.6.1.4.1.19831.1.1.2.2.5.2
		dabARExciterBInput2OK OBJECT-TYPE
			SYNTAX OkNotOk
			MAX-ACCESS read-only
			STATUS current
			DESCRIPTION
				"Active reserve. Describes if the input signal at the input 2 of exciter B is ok
				
				(0) undefined
				(1) signal ok
				(2) signal is not ok "
			::= { dabARExciterB 2 }

		
		-- 1.3.6.1.4.1.19831.1.1.2.2.5.3
		dabARExciterBLocalMode OBJECT-TYPE
			SYNTAX LocalRemote
			MAX-ACCESS read-only
			STATUS current
			DESCRIPTION
				"Active reserve. State of the local mode of exciter B
				
				(0) undefined
				(1) local
				(2) remote"
			::= { dabARExciterB 3 }

		
		-- 1.3.6.1.4.1.19831.1.1.2.2.5.4
		dabARExciterBFault OBJECT-TYPE
			SYNTAX FaultOK
			MAX-ACCESS read-only
			STATUS current
			DESCRIPTION
				"Active reserve. Fault state of the exciter B
				
				(0) undefined
				(1) fault
				(2) ok"
			::= { dabARExciterB 4 }

		
		-- 1.3.6.1.4.1.19831.1.1.2.2.5.5
		dabARExciterBWarning OBJECT-TYPE
			SYNTAX WarningOK
			MAX-ACCESS read-only
			STATUS current
			DESCRIPTION
				"Active reserve. Warning state of the exciter B
				
				(0) undefined
				(1) warning
				(2) ok"
			::= { dabARExciterB 5 }

		
		-- 1.3.6.1.4.1.19831.1.1.2.2.5.6
		dabARExciterBActiveInput OBJECT-TYPE
			SYNTAX INTEGER
				{
				undefined(0),
				input1(1),
				input2(2),
				seamless(3),
				hmHierarchicalModulation(4)
				}
			MAX-ACCESS read-only
			STATUS current
			DESCRIPTION
				"Active reserve. Active input of the exciter B 
				
				"
			::= { dabARExciterB 6 }

		
		-- 1.3.6.1.4.1.19831.1.1.2.2.5.7
		dabARExciterBSFNMode OBJECT-TYPE
			SYNTAX SFNMFN
			MAX-ACCESS read-only
			STATUS current
			DESCRIPTION
				"Active reserve. SFN mode of exciter B
				
				(0) undefined
				(1) SFN
				(2) MFN"
			::= { dabARExciterB 7 }

		
		-- 1.3.6.1.4.1.19831.1.1.2.2.5.8
		dabARExciterBMute OBJECT-TYPE
			SYNTAX MuteOk
			MAX-ACCESS read-only
			STATUS current
			DESCRIPTION
				"Active reserve. Mute state of exciter B
				
				(0) undefined
				(1) mute
				(2) ok"
			::= { dabARExciterB 8 }

		
		-- 1.3.6.1.4.1.19831.1.1.2.2.5.9
		dabARExciterBRefFault OBJECT-TYPE
			SYNTAX FaultOK
			MAX-ACCESS read-only
			STATUS current
			DESCRIPTION
				"Active reserve. Fault state of the GPS input or the reference frequency of exciter B
				
				(0) undefined
				(1) fault
				(2) ok"
			::= { dabARExciterB 9 }

		
		-- 1.3.6.1.4.1.19831.1.1.2.2.5.10
		dabARExciterBWarningTimeStamp OBJECT-TYPE
			SYNTAX WarningOK
			MAX-ACCESS read-only
			STATUS current
			DESCRIPTION
				"Active reserve. Time stamp warning of exciter B
				
				(0) undefined
				(1) warning
				(2) ok"
			::= { dabARExciterB 10 }

		
-- dab active reserve event enable
		-- 1.3.6.1.4.1.19831.1.1.2.2.6
		dabAREventEnable OBJECT IDENTIFIER ::= { dabActiveReserve 6 }

		
-- dab active reserve general:  switch for Event
		-- 1.3.6.1.4.1.19831.1.1.2.2.6.1
		dabAREventEnableGeneral OBJECT IDENTIFIER ::= { dabAREventEnable 1 }

		
		-- 1.3.6.1.4.1.19831.1.1.2.2.6.1.1
		dabARInputPreselectionEnable OBJECT-TYPE
			SYNTAX TruthValue
			MAX-ACCESS read-write
			STATUS current
			DESCRIPTION
				"Description.Enable/Disable switch for dabARInputPreselection event"
			::= { dabAREventEnableGeneral 1 }

		
		-- 1.3.6.1.4.1.19831.1.1.2.2.6.1.2
		dabARInputAutomaticEnable OBJECT-TYPE
			SYNTAX TruthValue
			MAX-ACCESS read-write
			STATUS current
			DESCRIPTION
				"Description.Enable/Disable switch for dabARInputAutomatic event"
			::= { dabAREventEnableGeneral 2 }

		
		-- 1.3.6.1.4.1.19831.1.1.2.2.6.1.3
		dabARPreselectionExciterEnable OBJECT-TYPE
			SYNTAX TruthValue
			MAX-ACCESS read-write
			STATUS current
			DESCRIPTION
				"Description.Enable/Disable switch for dabARPreselectionExciter event"
			::= { dabAREventEnableGeneral 3 }

		
		-- 1.3.6.1.4.1.19831.1.1.2.2.6.1.4
		dabARPreselectionAmplifierEnable OBJECT-TYPE
			SYNTAX TruthValue
			MAX-ACCESS read-write
			STATUS current
			DESCRIPTION
				"Description.Enable/Disable switch for dabARPreselectionAmplifier event"
			::= { dabAREventEnableGeneral 4 }

		
		-- 1.3.6.1.4.1.19831.1.1.2.2.6.1.5
		dabARTransmitterOpModeEnable OBJECT-TYPE
			SYNTAX TruthValue
			MAX-ACCESS read-write
			STATUS current
			DESCRIPTION
				"Description.Enable/Disable switch for dabARTransmitterOpMode event"
			::= { dabAREventEnableGeneral 5 }

		
		-- 1.3.6.1.4.1.19831.1.1.2.2.6.1.6
		dabARReserveControlEnable OBJECT-TYPE
			SYNTAX TruthValue
			MAX-ACCESS read-write
			STATUS current
			DESCRIPTION
				"Description.Enable/Disable switch for dabARReserveControl event"
			::= { dabAREventEnableGeneral 6 }

		
		-- 1.3.6.1.4.1.19831.1.1.2.2.6.1.7
		dabARResetFaultEnable OBJECT-TYPE
			SYNTAX TruthValue
			MAX-ACCESS read-write
			STATUS obsolete
			DESCRIPTION
				"Massage is inactive!
				
				Description.Enable/Disable switch for dabARResetFault event"
			::= { dabAREventEnableGeneral 7 }

		
		-- 1.3.6.1.4.1.19831.1.1.2.2.6.1.8
		dabARActiveAmplifierEnable OBJECT-TYPE
			SYNTAX TruthValue
			MAX-ACCESS read-write
			STATUS current
			DESCRIPTION
				"Description.Enable/Disable switch for dabARActiveAmplifier event"
			::= { dabAREventEnableGeneral 8 }

		
		-- 1.3.6.1.4.1.19831.1.1.2.2.6.1.9
		dabARActiveExciterEnable OBJECT-TYPE
			SYNTAX TruthValue
			MAX-ACCESS read-write
			STATUS current
			DESCRIPTION
				"Description.Enable/Disable switch for dabARActiveExciter event"
			::= { dabAREventEnableGeneral 9 }

		
		-- 1.3.6.1.4.1.19831.1.1.2.2.6.1.10
		dabARLocalModeEnable OBJECT-TYPE
			SYNTAX TruthValue
			MAX-ACCESS read-write
			STATUS current
			DESCRIPTION
				"Description.Enable/Disable switch for dabARLocalMode event"
			::= { dabAREventEnableGeneral 10 }

		
		-- 1.3.6.1.4.1.19831.1.1.2.2.6.1.11
		dabARControlUnitFaultEnable OBJECT-TYPE
			SYNTAX TruthValue
			MAX-ACCESS read-write
			STATUS current
			DESCRIPTION
				"Description.Enable/Disable switch for dabARControlUnitFault event"
			::= { dabAREventEnableGeneral 11 }

		
		-- 1.3.6.1.4.1.19831.1.1.2.2.6.1.12
		dabARExciterSwitchOverModeEnable OBJECT-TYPE
			SYNTAX TruthValue
			MAX-ACCESS read-write
			STATUS current
			DESCRIPTION
				"Description.Enable/Disable switch for dabARExciterSwitchOverMode event"
			::= { dabAREventEnableGeneral 12 }

		
		-- 1.3.6.1.4.1.19831.1.1.2.2.6.1.13
		dabARExciterSwitchOverReadyEnable OBJECT-TYPE
			SYNTAX TruthValue
			MAX-ACCESS read-write
			STATUS current
			DESCRIPTION
				"Description.Enable/Disable switch for dabARExciterSwitchOverReady event"
			::= { dabAREventEnableGeneral 13 }

		
		-- 1.3.6.1.4.1.19831.1.1.2.2.6.1.14
		dabARExciterSwitchOverExecutedEnable OBJECT-TYPE
			SYNTAX TruthValue
			MAX-ACCESS read-write
			STATUS current
			DESCRIPTION
				"Description.Enable/Disable switch for dabARExciterSwitchOverExecuted event"
			::= { dabAREventEnableGeneral 14 }

		
		-- 1.3.6.1.4.1.19831.1.1.2.2.6.1.15
		dabARExciterSwitchOverFaultEnable OBJECT-TYPE
			SYNTAX TruthValue
			MAX-ACCESS read-write
			STATUS current
			DESCRIPTION
				"Description.Enable/Disable switch for dabARExciterSwitchOverFault event"
			::= { dabAREventEnableGeneral 15 }

		
		-- 1.3.6.1.4.1.19831.1.1.2.2.6.1.16
		dabARAmplifierSwitchOverModeEnable OBJECT-TYPE
			SYNTAX TruthValue
			MAX-ACCESS read-write
			STATUS current
			DESCRIPTION
				"Description.Enable/Disable switch for dabARAmplifierSwitchOverMode event"
			::= { dabAREventEnableGeneral 16 }

		
		-- 1.3.6.1.4.1.19831.1.1.2.2.6.1.17
		dabARAmplifierSwitchOverReadyEnable OBJECT-TYPE
			SYNTAX TruthValue
			MAX-ACCESS read-write
			STATUS current
			DESCRIPTION
				"Description.Enable/Disable switch for dabARAmplifierSwitchOverReady event"
			::= { dabAREventEnableGeneral 17 }

		
		-- 1.3.6.1.4.1.19831.1.1.2.2.6.1.18
		dabARAmplifierSwitchOverExecutedEnable OBJECT-TYPE
			SYNTAX TruthValue
			MAX-ACCESS read-write
			STATUS current
			DESCRIPTION
				"Description.Enable/Disable switch for  dabARAmplifierSwitchOverExecuted event"
			::= { dabAREventEnableGeneral 18 }

		
		-- 1.3.6.1.4.1.19831.1.1.2.2.6.1.19
		dabARAmplifierSwitchOverFaultEnable OBJECT-TYPE
			SYNTAX TruthValue
			MAX-ACCESS read-write
			STATUS current
			DESCRIPTION
				"Description.Enable/Disable switch for dabARAmplifierSwitchOverFault event"
			::= { dabAREventEnableGeneral 19 }

		
-- dab active reserve amplifier A:  switch for Event
		-- 1.3.6.1.4.1.19831.1.1.2.2.6.2
		dabAREventEnableAmplifierA OBJECT IDENTIFIER ::= { dabAREventEnable 2 }

		
		-- 1.3.6.1.4.1.19831.1.1.2.2.6.2.1
		dabARAmplifierARFPresentEnable OBJECT-TYPE
			SYNTAX TruthValue
			MAX-ACCESS read-write
			STATUS current
			DESCRIPTION
				"Description.Enable/Disable switch for dabARAmplifierARFPresent event"
			::= { dabAREventEnableAmplifierA 1 }

		
		-- 1.3.6.1.4.1.19831.1.1.2.2.6.2.2
		dabARAmplifierAFaultEnable OBJECT-TYPE
			SYNTAX TruthValue
			MAX-ACCESS read-write
			STATUS current
			DESCRIPTION
				"Description.Enable/Disable switch for dabARAmplifierAFault event"
			::= { dabAREventEnableAmplifierA 2 }

		
		-- 1.3.6.1.4.1.19831.1.1.2.2.6.2.3
		dabARAmplifierAWarningEnable OBJECT-TYPE
			SYNTAX TruthValue
			MAX-ACCESS read-write
			STATUS current
			DESCRIPTION
				"Description.Enable/Disable switch for dabARAmplifierAWarning event"
			::= { dabAREventEnableAmplifierA 3 }

		
-- dab active reserve amplifier B:  switch for Event
		-- 1.3.6.1.4.1.19831.1.1.2.2.6.3
		dabAREventEnableAmplifierB OBJECT IDENTIFIER ::= { dabAREventEnable 3 }

		
		-- 1.3.6.1.4.1.19831.1.1.2.2.6.3.1
		dabARAmplifierBRFPresentEnable OBJECT-TYPE
			SYNTAX TruthValue
			MAX-ACCESS read-write
			STATUS current
			DESCRIPTION
				"Description.Enable/Disable switch for dabARAmplifierBRFPresent event"
			::= { dabAREventEnableAmplifierB 1 }

		
		-- 1.3.6.1.4.1.19831.1.1.2.2.6.3.2
		dabARAmplifierBFaultEnable OBJECT-TYPE
			SYNTAX TruthValue
			MAX-ACCESS read-write
			STATUS current
			DESCRIPTION
				"Description.Enable/Disable switch for dabARAmplifierBFault event"
			::= { dabAREventEnableAmplifierB 2 }

		
		-- 1.3.6.1.4.1.19831.1.1.2.2.6.3.3
		dabARAmplifierBWarningEnable OBJECT-TYPE
			SYNTAX TruthValue
			MAX-ACCESS read-write
			STATUS current
			DESCRIPTION
				"Description.Enable/Disable switch for dabARAmplifierBWarning event"
			::= { dabAREventEnableAmplifierB 3 }

		
-- dab active reserve exciter A:  switch for event
		-- 1.3.6.1.4.1.19831.1.1.2.2.6.4
		dabAREventEnableExciterA OBJECT IDENTIFIER ::= { dabAREventEnable 4 }

		
		-- 1.3.6.1.4.1.19831.1.1.2.2.6.4.1
		dabARExciterAInput1OKEnable OBJECT-TYPE
			SYNTAX TruthValue
			MAX-ACCESS read-write
			STATUS current
			DESCRIPTION
				"Description.Enable/Disable switch for dabARExciterAInput1OK event"
			::= { dabAREventEnableExciterA 1 }

		
		-- 1.3.6.1.4.1.19831.1.1.2.2.6.4.2
		dabARExciterAInput2OKEnable OBJECT-TYPE
			SYNTAX TruthValue
			MAX-ACCESS read-write
			STATUS current
			DESCRIPTION
				"Description.Enable/Disable switch for dabARExciterAInput2OK event"
			::= { dabAREventEnableExciterA 2 }

		
		-- 1.3.6.1.4.1.19831.1.1.2.2.6.4.3
		dabARExciterALocalModeEnable OBJECT-TYPE
			SYNTAX TruthValue
			MAX-ACCESS read-write
			STATUS current
			DESCRIPTION
				"Description.Enable/Disable switch for dabARExciterALocalMode event"
			::= { dabAREventEnableExciterA 3 }

		
		-- 1.3.6.1.4.1.19831.1.1.2.2.6.4.4
		dabARExciterAFaultEnable OBJECT-TYPE
			SYNTAX TruthValue
			MAX-ACCESS read-write
			STATUS current
			DESCRIPTION
				"Description.Enable/Disable switch for dabARExciterAFault event"
			::= { dabAREventEnableExciterA 4 }

		
		-- 1.3.6.1.4.1.19831.1.1.2.2.6.4.5
		dabARExciterAWarningEnable OBJECT-TYPE
			SYNTAX TruthValue
			MAX-ACCESS read-write
			STATUS current
			DESCRIPTION
				"Description.Enable/Disable switch for dabARExciterAWarning event"
			::= { dabAREventEnableExciterA 5 }

		
		-- 1.3.6.1.4.1.19831.1.1.2.2.6.4.6
		dabARExciterAActiveInputEnable OBJECT-TYPE
			SYNTAX TruthValue
			MAX-ACCESS read-write
			STATUS current
			DESCRIPTION
				"Description.Enable/Disable switch for dabARExciterAActiveInput event"
			::= { dabAREventEnableExciterA 6 }

		
		-- 1.3.6.1.4.1.19831.1.1.2.2.6.4.7
		dabARExciterASFNModeEnable OBJECT-TYPE
			SYNTAX TruthValue
			MAX-ACCESS read-write
			STATUS current
			DESCRIPTION
				"Description.Enable/Disable switch for dabARExciterASFNMode event"
			::= { dabAREventEnableExciterA 7 }

		
		-- 1.3.6.1.4.1.19831.1.1.2.2.6.4.8
		dabARExciterARefFaultEnable OBJECT-TYPE
			SYNTAX TruthValue
			MAX-ACCESS read-write
			STATUS current
			DESCRIPTION
				"Description.Enable/Disable switch for dabARExciterARefFault event"
			::= { dabAREventEnableExciterA 8 }

		
		-- 1.3.6.1.4.1.19831.1.1.2.2.6.4.9
		dabARExciterAMuteEnable OBJECT-TYPE
			SYNTAX TruthValue
			MAX-ACCESS read-write
			STATUS current
			DESCRIPTION
				"Description.Enable/Disable switch for dabARExciterAMute event"
			::= { dabAREventEnableExciterA 9 }

		
		-- 1.3.6.1.4.1.19831.1.1.2.2.6.4.10
		dabARExciterAWarningTimeStampEnable OBJECT-TYPE
			SYNTAX TruthValue
			MAX-ACCESS read-write
			STATUS current
			DESCRIPTION
				"Description.Enable/Disable switch for dabARExciterAWarningTimeStamp event"
			::= { dabAREventEnableExciterA 10 }

		
-- dab active reserve exciter B: switch event
		-- 1.3.6.1.4.1.19831.1.1.2.2.6.5
		dabAREventEnableExciterB OBJECT IDENTIFIER ::= { dabAREventEnable 5 }

		
		-- 1.3.6.1.4.1.19831.1.1.2.2.6.5.1
		dabARExciterBInput1OKEnable OBJECT-TYPE
			SYNTAX TruthValue
			MAX-ACCESS read-write
			STATUS current
			DESCRIPTION
				"Description.Enable/Disable switch for dabARExciterBInput1OK event"
			::= { dabAREventEnableExciterB 1 }

		
		-- 1.3.6.1.4.1.19831.1.1.2.2.6.5.2
		dabARExciterBInput2OKEnable OBJECT-TYPE
			SYNTAX TruthValue
			MAX-ACCESS read-write
			STATUS current
			DESCRIPTION
				"Description.Enable/Disable switch for dabARExciterBInput2OK event"
			::= { dabAREventEnableExciterB 2 }

		
		-- 1.3.6.1.4.1.19831.1.1.2.2.6.5.3
		dabARExciterBLocalModeEnable OBJECT-TYPE
			SYNTAX TruthValue
			MAX-ACCESS read-write
			STATUS current
			DESCRIPTION
				"Description.Enable/Disable switch for dabARExciterBLocalMode event"
			::= { dabAREventEnableExciterB 3 }

		
		-- 1.3.6.1.4.1.19831.1.1.2.2.6.5.4
		dabARExciterBFaultEnable OBJECT-TYPE
			SYNTAX TruthValue
			MAX-ACCESS read-write
			STATUS current
			DESCRIPTION
				"Description.Enable/Disable switch for dabARExciterBFault event"
			::= { dabAREventEnableExciterB 4 }

		
		-- 1.3.6.1.4.1.19831.1.1.2.2.6.5.5
		dabARExciterBWarningEnable OBJECT-TYPE
			SYNTAX TruthValue
			MAX-ACCESS read-write
			STATUS current
			DESCRIPTION
				"Description.Enable/Disable switch for dabARExciterBWarning event"
			::= { dabAREventEnableExciterB 5 }

		
		-- 1.3.6.1.4.1.19831.1.1.2.2.6.5.6
		dabARExciterBActiveInputEnable OBJECT-TYPE
			SYNTAX TruthValue
			MAX-ACCESS read-write
			STATUS current
			DESCRIPTION
				"Description.Enable/Disable switch for dabARExciterBActiveInput event"
			::= { dabAREventEnableExciterB 6 }

		
		-- 1.3.6.1.4.1.19831.1.1.2.2.6.5.7
		dabARExciterBSFNModeEnable OBJECT-TYPE
			SYNTAX TruthValue
			MAX-ACCESS read-write
			STATUS current
			DESCRIPTION
				"Description.Enable/Disable switch for dabARExciterBSFNMode event"
			::= { dabAREventEnableExciterB 7 }

		
		-- 1.3.6.1.4.1.19831.1.1.2.2.6.5.8
		dabARExciterBMuteEnable OBJECT-TYPE
			SYNTAX TruthValue
			MAX-ACCESS read-write
			STATUS current
			DESCRIPTION
				"Description.Enable/Disable switch for dabARExciterBMute event"
			::= { dabAREventEnableExciterB 8 }

		
		-- 1.3.6.1.4.1.19831.1.1.2.2.6.5.9
		dabARExciterBRefFaultEnable OBJECT-TYPE
			SYNTAX TruthValue
			MAX-ACCESS read-write
			STATUS current
			DESCRIPTION
				"Description.Enable/Disable switch for dabARExciterBRefFault event"
			::= { dabAREventEnableExciterB 9 }

		
		-- 1.3.6.1.4.1.19831.1.1.2.2.6.5.10
		dabARExciterBWarningTimeStampEnable OBJECT-TYPE
			SYNTAX TruthValue
			MAX-ACCESS read-write
			STATUS current
			DESCRIPTION
				"Description.Enable/Disable switch for dabARExciterBWarningTimeStamp event"
			::= { dabAREventEnableExciterB 10 }

		
-- dab active reserve event priority
		-- 1.3.6.1.4.1.19831.1.1.2.2.7
		dabAREventPriority OBJECT IDENTIFIER ::= { dabActiveReserve 7 }

		
-- dab active reserve event priority general
		-- 1.3.6.1.4.1.19831.1.1.2.2.7.1
		dabAREventPriorityGeneral OBJECT IDENTIFIER ::= { dabAREventPriority 1 }

		
		-- 1.3.6.1.4.1.19831.1.1.2.2.7.1.1
		dabARInputPreselectionPriority OBJECT-TYPE
			SYNTAX Unsigned32
			MAX-ACCESS read-write
			STATUS current
			DESCRIPTION
				"Description.Priority for dabARInputPreselection event"
			::= { dabAREventPriorityGeneral 1 }

		
		-- 1.3.6.1.4.1.19831.1.1.2.2.7.1.2
		dabARInputAutomaticPriority OBJECT-TYPE
			SYNTAX Unsigned32
			MAX-ACCESS read-write
			STATUS current
			DESCRIPTION
				"Description.Priority for dabARInputAutomatic event"
			::= { dabAREventPriorityGeneral 2 }

		
		-- 1.3.6.1.4.1.19831.1.1.2.2.7.1.3
		dabARPreselectionExciterPriority OBJECT-TYPE
			SYNTAX Unsigned32
			MAX-ACCESS read-write
			STATUS current
			DESCRIPTION
				"Description.Priority for dabARPreselectionExciter event"
			::= { dabAREventPriorityGeneral 3 }

		
		-- 1.3.6.1.4.1.19831.1.1.2.2.7.1.4
		dabARPreselectionAmplifierPriority OBJECT-TYPE
			SYNTAX Unsigned32
			MAX-ACCESS read-write
			STATUS current
			DESCRIPTION
				"Description.Priority for dabARPreselectionAmplifier event"
			::= { dabAREventPriorityGeneral 4 }

		
		-- 1.3.6.1.4.1.19831.1.1.2.2.7.1.5
		dabARTransmitterOpModePriority OBJECT-TYPE
			SYNTAX Unsigned32
			MAX-ACCESS read-write
			STATUS current
			DESCRIPTION
				"Description.Priority for dabARTransmitterOpMode event"
			::= { dabAREventPriorityGeneral 5 }

		
		-- 1.3.6.1.4.1.19831.1.1.2.2.7.1.6
		dabARReserveControlPriority OBJECT-TYPE
			SYNTAX Unsigned32
			MAX-ACCESS read-write
			STATUS current
			DESCRIPTION
				"Description.Priority for dabARReserveControl event"
			::= { dabAREventPriorityGeneral 6 }

		
		-- 1.3.6.1.4.1.19831.1.1.2.2.7.1.7
		dabARResetFaultPriority OBJECT-TYPE
			SYNTAX Unsigned32
			MAX-ACCESS read-write
			STATUS obsolete
			DESCRIPTION
				"Massage is inactive!
				
				Description.Priority for dabARResetFault event"
			::= { dabAREventPriorityGeneral 7 }

		
		-- 1.3.6.1.4.1.19831.1.1.2.2.7.1.8
		dabARActiveAmplifierPriority OBJECT-TYPE
			SYNTAX Unsigned32
			MAX-ACCESS read-write
			STATUS current
			DESCRIPTION
				"Description.Priority for dabARActiveAmplifier event"
			::= { dabAREventPriorityGeneral 8 }

		
		-- 1.3.6.1.4.1.19831.1.1.2.2.7.1.9
		dabARActiveExciterPriority OBJECT-TYPE
			SYNTAX Unsigned32
			MAX-ACCESS read-write
			STATUS current
			DESCRIPTION
				"Description.Priority for dabARActiveExciter event"
			::= { dabAREventPriorityGeneral 9 }

		
		-- 1.3.6.1.4.1.19831.1.1.2.2.7.1.10
		dabARLocalModePriority OBJECT-TYPE
			SYNTAX Unsigned32
			MAX-ACCESS read-write
			STATUS current
			DESCRIPTION
				"Description.Priority for dabARLocalMode event"
			::= { dabAREventPriorityGeneral 10 }

		
		-- 1.3.6.1.4.1.19831.1.1.2.2.7.1.11
		dabARControlUnitFaultPriority OBJECT-TYPE
			SYNTAX Unsigned32
			MAX-ACCESS read-write
			STATUS current
			DESCRIPTION
				"Description.Priority for dabARControlUnitFault event"
			::= { dabAREventPriorityGeneral 11 }

		
		-- 1.3.6.1.4.1.19831.1.1.2.2.7.1.12
		dabARExciterSwitchOverModePriority OBJECT-TYPE
			SYNTAX Unsigned32
			MAX-ACCESS read-write
			STATUS current
			DESCRIPTION
				"Description.Priority for dabARExciterSwitchOverMode event"
			::= { dabAREventPriorityGeneral 12 }

		
		-- 1.3.6.1.4.1.19831.1.1.2.2.7.1.13
		dabARExciterSwitchOverReadyPriority OBJECT-TYPE
			SYNTAX Unsigned32
			MAX-ACCESS read-write
			STATUS current
			DESCRIPTION
				"Description.Priority for dabARExciterSwitchOverReady event"
			::= { dabAREventPriorityGeneral 13 }

		
		-- 1.3.6.1.4.1.19831.1.1.2.2.7.1.14
		dabARExciterSwitchOverExecutedPriority OBJECT-TYPE
			SYNTAX Unsigned32
			MAX-ACCESS read-write
			STATUS current
			DESCRIPTION
				"Description.Priority for dabARExciterSwitchOverExecuted event"
			::= { dabAREventPriorityGeneral 14 }

		
		-- 1.3.6.1.4.1.19831.1.1.2.2.7.1.15
		dabARExciterSwitchOverFaultPriority OBJECT-TYPE
			SYNTAX Unsigned32
			MAX-ACCESS read-write
			STATUS current
			DESCRIPTION
				"Description.Priority for dabARExciterSwitchOverFault event"
			::= { dabAREventPriorityGeneral 15 }

		
		-- 1.3.6.1.4.1.19831.1.1.2.2.7.1.16
		dabARAmplifierSwitchOverModePriority OBJECT-TYPE
			SYNTAX Unsigned32
			MAX-ACCESS read-write
			STATUS current
			DESCRIPTION
				"Description.Priority for dabARAmplifierSwitchOverMode event"
			::= { dabAREventPriorityGeneral 16 }

		
		-- 1.3.6.1.4.1.19831.1.1.2.2.7.1.17
		dabARAmplifierSwitchOverReadyPriority OBJECT-TYPE
			SYNTAX Unsigned32
			MAX-ACCESS read-write
			STATUS current
			DESCRIPTION
				"Description.Priority for dabARAmplifierSwitchOverReady event"
			::= { dabAREventPriorityGeneral 17 }

		
		-- 1.3.6.1.4.1.19831.1.1.2.2.7.1.18
		dabARAmplifierSwitchOverExecutedPriority OBJECT-TYPE
			SYNTAX Unsigned32
			MAX-ACCESS read-write
			STATUS current
			DESCRIPTION
				"Description.Priority for dabARAmplifierSwitchOverExecuted event"
			::= { dabAREventPriorityGeneral 18 }

		
		-- 1.3.6.1.4.1.19831.1.1.2.2.7.1.19
		dabARAmplifierSwitchOverFaultPriority OBJECT-TYPE
			SYNTAX Unsigned32
			MAX-ACCESS read-write
			STATUS current
			DESCRIPTION
				"Description.Priority for dabARAmplifierSwitchOverFault event"
			::= { dabAREventPriorityGeneral 19 }

		
-- dab active reserve  event priority amplifier A
		-- 1.3.6.1.4.1.19831.1.1.2.2.7.2
		dabAREventPriorityAmplifierA OBJECT IDENTIFIER ::= { dabAREventPriority 2 }

		
		-- 1.3.6.1.4.1.19831.1.1.2.2.7.2.1
		dabARAmplifierARFPresentPriority OBJECT-TYPE
			SYNTAX Unsigned32
			MAX-ACCESS read-write
			STATUS current
			DESCRIPTION
				"Description.Priority for dabARAmplifierARFPresent event"
			::= { dabAREventPriorityAmplifierA 1 }

		
		-- 1.3.6.1.4.1.19831.1.1.2.2.7.2.2
		dabARAmplifierAFaultPriority OBJECT-TYPE
			SYNTAX Unsigned32
			MAX-ACCESS read-write
			STATUS current
			DESCRIPTION
				"Description.Priority for dabARAmplifierAFault event"
			::= { dabAREventPriorityAmplifierA 2 }

		
		-- 1.3.6.1.4.1.19831.1.1.2.2.7.2.3
		dabARAmplifierAWarningPriority OBJECT-TYPE
			SYNTAX Unsigned32
			MAX-ACCESS read-write
			STATUS current
			DESCRIPTION
				"Description.Priority for dabARAmplifierAWarning event"
			::= { dabAREventPriorityAmplifierA 3 }

		
-- dab active reserve event priority amplifier B
		-- 1.3.6.1.4.1.19831.1.1.2.2.7.3
		dabAREventPriorityAmplifierB OBJECT IDENTIFIER ::= { dabAREventPriority 3 }

		
		-- 1.3.6.1.4.1.19831.1.1.2.2.7.3.1
		dabARAmplifierBRFPresentPriority OBJECT-TYPE
			SYNTAX Unsigned32
			MAX-ACCESS read-write
			STATUS current
			DESCRIPTION
				"Description.Priority for dabARAmplifierBRFPresent event"
			::= { dabAREventPriorityAmplifierB 1 }

		
		-- 1.3.6.1.4.1.19831.1.1.2.2.7.3.2
		dabARAmplifierBFaultPriority OBJECT-TYPE
			SYNTAX Unsigned32
			MAX-ACCESS read-write
			STATUS current
			DESCRIPTION
				"Description.Priority for dabARAmplifierBFault event"
			::= { dabAREventPriorityAmplifierB 2 }

		
		-- 1.3.6.1.4.1.19831.1.1.2.2.7.3.3
		dabARAmplifierBWarningPriority OBJECT-TYPE
			SYNTAX Unsigned32
			MAX-ACCESS read-write
			STATUS current
			DESCRIPTION
				"Description.Priority for dabARAmplifierBWarning event"
			::= { dabAREventPriorityAmplifierB 3 }

		
-- dab active reserve event priority exciter A
		-- 1.3.6.1.4.1.19831.1.1.2.2.7.4
		dabAREventPriorityExciterA OBJECT IDENTIFIER ::= { dabAREventPriority 4 }

		
		-- 1.3.6.1.4.1.19831.1.1.2.2.7.4.1
		dabARExciterAInput1OKPriority OBJECT-TYPE
			SYNTAX Unsigned32
			MAX-ACCESS read-write
			STATUS current
			DESCRIPTION
				"Description.Priority for dabARExciterAInput1OK event"
			::= { dabAREventPriorityExciterA 1 }

		
		-- 1.3.6.1.4.1.19831.1.1.2.2.7.4.2
		dabARExciterAInput2OKPriority OBJECT-TYPE
			SYNTAX Unsigned32
			MAX-ACCESS read-write
			STATUS current
			DESCRIPTION
				"Description.Priority for dabARExciterAInput2OK event"
			::= { dabAREventPriorityExciterA 2 }

		
		-- 1.3.6.1.4.1.19831.1.1.2.2.7.4.3
		dabARExciterALocalModePriority OBJECT-TYPE
			SYNTAX Unsigned32
			MAX-ACCESS read-write
			STATUS current
			DESCRIPTION
				"Description.Priority for dabARExciterALocalMode event"
			::= { dabAREventPriorityExciterA 3 }

		
		-- 1.3.6.1.4.1.19831.1.1.2.2.7.4.4
		dabARExciterAFaultPriority OBJECT-TYPE
			SYNTAX Unsigned32
			MAX-ACCESS read-write
			STATUS current
			DESCRIPTION
				"Description.Priority for dabARExciterAFault event"
			::= { dabAREventPriorityExciterA 4 }

		
		-- 1.3.6.1.4.1.19831.1.1.2.2.7.4.5
		dabARExciterAWarningPriority OBJECT-TYPE
			SYNTAX Unsigned32
			MAX-ACCESS read-write
			STATUS current
			DESCRIPTION
				"Description.Priority for dabARExciterAWarning event"
			::= { dabAREventPriorityExciterA 5 }

		
		-- 1.3.6.1.4.1.19831.1.1.2.2.7.4.6
		dabARExciterAActiveInputPriority OBJECT-TYPE
			SYNTAX Unsigned32
			MAX-ACCESS read-write
			STATUS current
			DESCRIPTION
				"Description.Priority for dabARExciterAActiveInput event"
			::= { dabAREventPriorityExciterA 6 }

		
		-- 1.3.6.1.4.1.19831.1.1.2.2.7.4.7
		dabARExciterASFNModePriority OBJECT-TYPE
			SYNTAX Unsigned32
			MAX-ACCESS read-write
			STATUS current
			DESCRIPTION
				"Description.Priority for dabARExciterASFNMode event"
			::= { dabAREventPriorityExciterA 7 }

		
		-- 1.3.6.1.4.1.19831.1.1.2.2.7.4.8
		dabARExciterARefFaultPriority OBJECT-TYPE
			SYNTAX Unsigned32
			MAX-ACCESS read-write
			STATUS current
			DESCRIPTION
				"Description.Priority for Event dabARExciterARefFault event"
			::= { dabAREventPriorityExciterA 8 }

		
		-- 1.3.6.1.4.1.19831.1.1.2.2.7.4.9
		dabARExciterAMutePriority OBJECT-TYPE
			SYNTAX Unsigned32
			MAX-ACCESS read-write
			STATUS current
			DESCRIPTION
				"Description.Priority for dabARExciterAMute event"
			::= { dabAREventPriorityExciterA 9 }

		
		-- 1.3.6.1.4.1.19831.1.1.2.2.7.4.10
		dabARExciterAWarningTimeStampPriority OBJECT-TYPE
			SYNTAX Unsigned32
			MAX-ACCESS read-write
			STATUS current
			DESCRIPTION
				"Description.Priority for dabARExciterAWarningTimeStamp event"
			::= { dabAREventPriorityExciterA 10 }

		
-- dab active reserve event priority exciter B
		-- 1.3.6.1.4.1.19831.1.1.2.2.7.5
		dabAREventPriorityExciterB OBJECT IDENTIFIER ::= { dabAREventPriority 5 }

		
		-- 1.3.6.1.4.1.19831.1.1.2.2.7.5.1
		dabARExciterBInput1OKPriority OBJECT-TYPE
			SYNTAX Unsigned32
			MAX-ACCESS read-write
			STATUS current
			DESCRIPTION
				"Description.Priority for dabARExciterBInput1OK event"
			::= { dabAREventPriorityExciterB 1 }

		
		-- 1.3.6.1.4.1.19831.1.1.2.2.7.5.2
		dabARExciterBInput2OKPriority OBJECT-TYPE
			SYNTAX Unsigned32
			MAX-ACCESS read-write
			STATUS current
			DESCRIPTION
				"Description.Priority for dabARExciterBInput2OK event"
			::= { dabAREventPriorityExciterB 2 }

		
		-- 1.3.6.1.4.1.19831.1.1.2.2.7.5.3
		dabARExciterBLocalModePriority OBJECT-TYPE
			SYNTAX Unsigned32
			MAX-ACCESS read-write
			STATUS current
			DESCRIPTION
				"Description.Priority for dabARExciterBLocalMode event"
			::= { dabAREventPriorityExciterB 3 }

		
		-- 1.3.6.1.4.1.19831.1.1.2.2.7.5.4
		dabARExciterBFaultPriority OBJECT-TYPE
			SYNTAX Unsigned32
			MAX-ACCESS read-write
			STATUS current
			DESCRIPTION
				"Description.Priority for dabARExciterBFault event"
			::= { dabAREventPriorityExciterB 4 }

		
		-- 1.3.6.1.4.1.19831.1.1.2.2.7.5.5
		dabARExciterBWarningPriority OBJECT-TYPE
			SYNTAX Unsigned32
			MAX-ACCESS read-write
			STATUS current
			DESCRIPTION
				"Description.Priority for dabARExciterBWarning event"
			::= { dabAREventPriorityExciterB 5 }

		
		-- 1.3.6.1.4.1.19831.1.1.2.2.7.5.6
		dabARExciterBActiveInputPriority OBJECT-TYPE
			SYNTAX Unsigned32
			MAX-ACCESS read-write
			STATUS current
			DESCRIPTION
				"Description.Priority for dabARExciterBActiveInput event"
			::= { dabAREventPriorityExciterB 6 }

		
		-- 1.3.6.1.4.1.19831.1.1.2.2.7.5.7
		dabARExciterBSFNModePriority OBJECT-TYPE
			SYNTAX Unsigned32
			MAX-ACCESS read-write
			STATUS current
			DESCRIPTION
				"Description.Priority for dabARExciterBSFNMode event"
			::= { dabAREventPriorityExciterB 7 }

		
		-- 1.3.6.1.4.1.19831.1.1.2.2.7.5.8
		dabARExciterBMutePriority OBJECT-TYPE
			SYNTAX Unsigned32
			MAX-ACCESS read-write
			STATUS current
			DESCRIPTION
				"Description.Priority for dabARExciterBMute event"
			::= { dabAREventPriorityExciterB 8 }

		
		-- 1.3.6.1.4.1.19831.1.1.2.2.7.5.9
		dabARExciterBRefFaultPriority OBJECT-TYPE
			SYNTAX Unsigned32
			MAX-ACCESS read-write
			STATUS current
			DESCRIPTION
				"Description.Priority for dabARExciterBRefFault event"
			::= { dabAREventPriorityExciterB 9 }

		
		-- 1.3.6.1.4.1.19831.1.1.2.2.7.5.10
		dabARExciterBWarningTimeStampPriority OBJECT-TYPE
			SYNTAX Unsigned32
			MAX-ACCESS read-write
			STATUS current
			DESCRIPTION
				"Description.Priority for dabARExciterBWarningTimeStamp event"
			::= { dabAREventPriorityExciterB 10 }

		
		-- 1.3.6.1.4.1.19831.1.1.2.2.8
		groupsAR OBJECT IDENTIFIER ::= { dabActiveReserve 8 }

		
		-- 1.3.6.1.4.1.19831.1.1.2.2.8.1
		objectGroupAR OBJECT-GROUP
			OBJECTS { dabARInputPreselection, dabARInputAutomatic, dabARPreselectionExciter, dabARPreselectionAmplifier, dabARTransmitterOpMode, 
				dabARReserveControl, dabARActiveAmplifier, dabARActiveExciter, dabARLocalMode, dabARControlUnitFault, 
				dabARExciterSwitchOverMode, dabARExciterSwitchOverReady, dabARExciterSwitchOverExecuted, dabARExciterSwitchOverFault, dabARAmplifierSwitchOverMode, 
				dabARAmplifierSwitchOverReady, dabARAmplifierSwitchOverExecuted, dabARAmplifierSwitchOverFault, dabARAmplifierARFPresent, dabARAmplifierAFault, 
				dabARAmplifierAWarning, dabARAmplifierBRFPresent, dabARAmplifierBFault, dabARAmplifierBWarning, dabARExciterAInput1OK, 
				dabARExciterAInput2OK, dabARExciterALocalMode, dabARExciterAFault, dabARExciterAWarning, dabARExciterAActiveInput, 
				dabARExciterASFNMode, dabARExciterARefFault, dabARExciterAMute, dabARExciterAWarningTimeStamp, dabARExciterBInput1OK, 
				dabARExciterBInput2OK, dabARExciterBLocalMode, dabARExciterBFault, dabARExciterBWarning, dabARExciterBActiveInput, 
				dabARExciterBSFNMode, dabARExciterBMute, dabARExciterBRefFault, dabARExciterBWarningTimeStamp, dabARInputPreselectionEnable, 
				dabARInputAutomaticEnable, dabARPreselectionExciterEnable, dabARPreselectionAmplifierEnable, dabARTransmitterOpModeEnable, dabARReserveControlEnable, 
				dabARActiveAmplifierEnable, dabARActiveExciterEnable, dabARLocalModeEnable, dabARControlUnitFaultEnable, dabARExciterSwitchOverModeEnable, 
				dabARExciterSwitchOverExecutedEnable, dabARExciterSwitchOverFaultEnable, dabARAmplifierSwitchOverModeEnable, dabARAmplifierSwitchOverReadyEnable, dabARAmplifierSwitchOverExecutedEnable, 
				dabARAmplifierSwitchOverFaultEnable, dabARExciterSwitchOverReadyEnable, dabARAmplifierARFPresentEnable, dabARAmplifierAFaultEnable, dabARAmplifierAWarningEnable, 
				dabARAmplifierBRFPresentEnable, dabARAmplifierBFaultEnable, dabARAmplifierBWarningEnable, dabARExciterAInput1OKEnable, dabARExciterAInput2OKEnable, 
				dabARExciterALocalModeEnable, dabARExciterAFaultEnable, dabARExciterAWarningEnable, dabARExciterAActiveInputEnable, dabARExciterASFNModeEnable, 
				dabARExciterARefFaultEnable, dabARExciterAMuteEnable, dabARExciterAWarningTimeStampEnable, dabARExciterBInput1OKEnable, dabARExciterBInput2OKEnable, 
				dabARExciterBLocalModeEnable, dabARExciterBFaultEnable, dabARExciterBWarningEnable, dabARExciterBActiveInputEnable, dabARExciterBSFNModeEnable, 
				dabARExciterBMuteEnable, dabARExciterBRefFaultEnable, dabARExciterBWarningTimeStampEnable, dabARInputPreselectionPriority, dabARInputAutomaticPriority, 
				dabARPreselectionExciterPriority, dabARPreselectionAmplifierPriority, dabARTransmitterOpModePriority, dabARReserveControlPriority, dabARActiveAmplifierPriority, 
				dabARActiveExciterPriority, dabARLocalModePriority, dabARControlUnitFaultPriority, dabARExciterSwitchOverModePriority, dabARExciterSwitchOverExecutedPriority, 
				dabARExciterSwitchOverFaultPriority, dabARAmplifierSwitchOverModePriority, dabARAmplifierSwitchOverReadyPriority, dabARAmplifierSwitchOverExecutedPriority, dabARAmplifierSwitchOverFaultPriority, 
				dabARExciterSwitchOverReadyPriority, dabARAmplifierARFPresentPriority, dabARAmplifierAFaultPriority, dabARAmplifierAWarningPriority, dabARAmplifierBRFPresentPriority, 
				dabARAmplifierBFaultPriority, dabARAmplifierBWarningPriority, dabARExciterAInput1OKPriority, dabARExciterAInput2OKPriority, dabARExciterALocalModePriority, 
				dabARExciterAFaultPriority, dabARExciterAWarningPriority, dabARExciterAActiveInputPriority, dabARExciterASFNModePriority, dabARExciterARefFaultPriority, 
				dabARExciterAMutePriority, dabARExciterAWarningTimeStampPriority, dabARExciterBInput1OKPriority, dabARExciterBInput2OKPriority, dabARExciterBFaultPriority, 
				dabARExciterBWarningPriority, dabARExciterBActiveInputPriority, dabARExciterBSFNModePriority, dabARExciterBMutePriority, dabARExciterBRefFaultPriority, 
				dabARExciterBWarningTimeStampPriority, dabARExciterBLocalModePriority }
			STATUS current
			DESCRIPTION 
				"Description. active reserve: object group"
			::= { groupsAR 1 }

		
		-- 1.3.6.1.4.1.19831.1.1.2.2.8.2
		eventGroupAR NOTIFICATION-GROUP
			NOTIFICATIONS { dabARInputPreselectionEvent, dabARInputAutomaticEvent, dabARPreselectionExciterEvent, dabARPreselectionAmplifierEvent, dabARTransmitterOpModeEvent, 
				dabARReserveControlEvent, dabARActiveAmplifierEvent, dabARActiveExciterEvent, dabARLocalModeEvent, dabARControlUnitFaultEvent, 
				dabARExciterSwitchOverModeEvent, dabARExciterSwitchOverReadyEvent, dabARExciterSwitchOverExecutedEvent, dabARExciterSwitchOverFaultEvent, dabARAmplifierSwitchOverModeEvent, 
				dabARAmplifierSwitchOverReadyEvent, dabARAmplifierSwitchOverExecutedEvent, dabARAmplifierSwitchOverFaultEvent, dabARAmplifierARFPresentEvent, dabARAmplifierAFaultEvent, 
				dabARAmplifierAWarningEvent, dabARAmplifierBRFPresentEvent, dabARAmplifierBFaultEvent, dabARAmplifierBWarningEvent, dabARExciterAInput1OKEvent, 
				dabARExciterAInput2OKEvent, dabARExciterALocalModeEvent, dabARExciterAFaultEvent, dabARExciterAWarningEvent, dabARExciterAActiveInputEvent, 
				dabARExciterASFNModeEvent, dabARExciterARefFaultEvent, dabARExciterAMuteEvent, dabARExciterAWarningTimeStampEvent, dabARExciterBInput1OKEvent, 
				dabARExciterBInput2OKEvent, dabARExciterBLocalModeEvent, dabARExciterBFaultEvent, dabARExciterBWarningEvent, dabARExciterBActiveInputEvent, 
				dabARExciterBSFNModeEvent, dabARExciterBRefFaultEvent, dabARExciterBMuteEvent, dabARExciterBWarningTimeStampEvent }
			STATUS current
			DESCRIPTION 
				"Description. events"
			::= { groupsAR 2 }

		
		-- 1.3.6.1.4.1.19831.1.1.2.2.8.3
		objectGroupARobsolete OBJECT-GROUP
			OBJECTS { dabARResetFault, dabARResetFaultEnable, dabARResetFaultPriority }
			STATUS obsolete
			DESCRIPTION 
				"Description. Inactive objects"
			::= { groupsAR 3 }

		
		-- 1.3.6.1.4.1.19831.1.1.2.2.8.4
		eventGroupARobsolete NOTIFICATION-GROUP
			NOTIFICATIONS { dabARResetFaultEvent }
			STATUS obsolete
			DESCRIPTION 
				" Description.Inactive events"
			::= { groupsAR 4 }

		
		-- 1.3.6.1.4.1.19831.1.1.2.2.10
		complianceAR OBJECT IDENTIFIER ::= { dabActiveReserve 10 }

		
		-- 1.3.6.1.4.1.19831.1.1.2.2.10.1
		dabActiveReserveCompliance MODULE-COMPLIANCE
			STATUS current
			DESCRIPTION 
				"Compliance Statement"
			MODULE -- this module
				MANDATORY-GROUPS { objectGroupAR, eventGroupAR }
			::= { complianceAR 1 }

		
	
	END

--
-- IRT-DAB-ACTIVERESERVE-MIB.my
--
